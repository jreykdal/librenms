-- *****************************************************************************
-- *****************************************************************************
-- **
-- **  COPYRIGHT      (c) 2008 Rohde & Schwarz GmbH & Co. KG
-- **                          Muehldorfstrasse 15
-- **    R & S                 D-81671 Muenchen
-- **
-- *****************************************************************************
-- **
-- **  MODULE         RS-XX8000-MEDIAFLO-TX-MIB
-- **  
-- **  DESCRIPTION    Rohde & Schwarz SNMP
-- **
-- **  HISTORY        
-- **  2008-08-26 ks - rfProbesNetCCURfProbe1, rfProbesNetCCURfProbe2 read-only
-- **                - cmdTxParametersetReSave obsolete
-- **  2008-09-15 sr - new rackTable
-- **                - new txRackRfWarning, txRackRfFault, txRackReflectionWarning,
-- **                      txRackReflectionFault
-- **                - new groupIndependentRacks
-- **  2008-10-08 sr - cmdExcFrequency range up to 1500 MHz
-- **  2008-12-12 sr - rfProbeConfigurationLabel obsolete
-- **                - txRackExtCoolingWarning renamed to txRackGpiWarning
-- **                - txRackExtCoolingFault renamed to txRackGpiFault
-- **  2009-01-07 sr - rfProbeCalibrationSetGain, rfProbeCalibrationSetOffset
-- **  2009-03-30 ks - txRackProbeNotCalibrated added
-- **                - txParamSetSubDeviceDiffers obsoleted
-- **  2009-05-28 ks - information for additional (external) power supply added
-- **                - txRackRfOn, txRackRfOk, txRackTemperatureWarning added
-- **  2009-06-26 ks - consideration of face-lift configuration in module compliances
-- **                - measured values for power supply added
-- **                - conditional groupDummyLoadRF added
-- **  2009-07-16 ks - additional values for reserve concept 'backup exciter'
-- **  2009-09-10 ks - cmdTxSystemMode added
-- **                - traps for TX mode switch over added
-- **  2009-10-08 ks - txRackOvervoltProtectWarning added
-- **  2009-11-13 ks - ostRackAmpDeltaPhase, ostRackAmpCmdDeltaPhase added
-- **  2009-11-26 ks - cmdExcOutputPower, cmdExcRfFailLimit, cmdExcRfWarningLimit added
-- **  2009-11-30 ks - cmdExcMonitoringOutput added
-- **  2009-12-07 ks - excStatusNominalPower added
-- **  2010-01-12 ks - excStatusVSWR added
-- **  2010-01-29 ks - txNetCCUBoardTemperatureFault deprecated,
-- **                  txNetCCUBoardTemperatureWarning added
-- **                  excPrecExtendedGroupDelay added
-- **  2010-05-21 ks - cmdTxRfSwitch added
-- **  2011-03-01 ks - Amplifier status for Sx801 added.
-- **  2011-05-12 ks - cmdExcFailDelayMode, excStatusFailDelay added
-- **  2012-08-31 ks - sx801AmplifierTable measured values added
-- **
-- *****************************************************************************
-- *****************************************************************************

    RS-XX8000-MEDIAFLO-TX-MIB DEFINITIONS ::= BEGIN
 
        IMPORTS
            rsXx8000, eventAlarmPriority, eventAlarmClass, eventEvent, indexAB, 
            indexRack, indexAmplifier, rsXx8000MibModule, EventPriority, EventClass, 
            EventState, IndexAB, IndexRack, IndexAmplifier, Trigger, 
            SwitchOnOff, TvStandard, FloatingPoint, ProdInfoModuleNameTv, ReadableString, 
            LogbookMaxEntryNumber, LogbookEntrySlope, LogbookEntryMessagesNetCCU, LogbookEntryMessagesExcTv, LogbookEntryMessagesOST, 
            EventMaxEntryNumber, EventMask, Sx801AmplifierState, FailDelayMode, FailDelayStatus            
                FROM RS-XX8000-COMMON-MIB            
            OBJECT-GROUP, MODULE-COMPLIANCE, NOTIFICATION-GROUP            
                FROM SNMPv2-CONF            
            Integer32, OBJECT-TYPE, MODULE-IDENTITY, OBJECT-IDENTITY, NOTIFICATION-TYPE            
                FROM SNMPv2-SMI            
            TruthValue, DateAndTime, TEXTUAL-CONVENTION            
                FROM SNMPv2-TC;
    
    
        rsXx8000MediaFloMibModule MODULE-IDENTITY 
            LAST-UPDATED "201208310800Z"		-- August 31, 2012 at 08:00 GMT
            ORGANIZATION 
                "Rohde&Schwarz GmbH & Co. KG"
            CONTACT-INFO 
                "Torsten Huebscher
                Department 7TS2
                Broadcasting Division
                Muehldorfstrasse 15
                81671 Munich, Germany
                torsten.huebscher@rohde-schwarz.com"
            DESCRIPTION 
                "This MIB defines transmitting systems from Rohde & Schwarz.
                
                Use this MIB if your system meets the following requirements:
                - series XX8000 (NetCCU800),
                - MediaFLO,
                - transmitter reserve concept SingleTx, DualDrive,
                  Active Reserve or Passive Reserve.
                
                The following MIBs are related to this:
                - RS-COMMON-MIB         - mandatory for this MIB
                - RS-XX8000-COMMON-MIB  - mandatory for this MIB"
            REVISION "201208310800Z"		-- August 31, 2012 at 08:00 GMT
            DESCRIPTION 
                "sx801AmplifierTable measured values added"
            REVISION "201105120800Z"		-- May 12, 2011 at 08:00 GMT
            DESCRIPTION 
                "cmdExcFailDelayMode, excStatusFailDelay added"
            REVISION "201103010800Z"		-- March 01, 2011 at 08:00 GMT
            DESCRIPTION 
                "Amplifier status for Sx801 added."
            REVISION "201005210800Z"		-- May 21, 2010 at 08:00 GMT
            DESCRIPTION 
                "cmdTxRfSwitch added"
            REVISION "201001290800Z"		-- January 29, 2010 at 08:00 GMT
            DESCRIPTION 
                "txNetCCUBoardTemperatureFault deprecated,
                txNetCCUBoardTemperatureWarning added,
                excPrecExtendedGroupDelay added"
            REVISION "201001120800Z"		-- January 12, 2010 at 08:00 GMT
            DESCRIPTION 
                "excStatusVSWR added"
            REVISION "200911260800Z"		-- November 26, 2009 at 08:00 GMT
            DESCRIPTION 
                "cmdExcOutputPower, cmdExcRfFailLimit, cmdExcRfWarningLimit,
                cmdExcMonitoringOutput, excStatusNominalPower added"
            REVISION "200911130800Z"		-- November 13, 2009 at 08:00 GMT
            DESCRIPTION 
                "ostRackAmpDeltaPhase, ostRackAmpCmdDeltaPhase added"
            REVISION "200910080800Z"		-- October 08, 2009 at 08:00 GMT
            DESCRIPTION 
                "txRackOvervoltProtectWarning added"
            REVISION "200909100800Z"		-- September 10, 2009 at 08:00 GMT
            DESCRIPTION 
                "cmdTxSystemMode added
                traps for TX mode switch over added"
            REVISION "200907160800Z"		-- July 16, 2009 at 08:00 GMT
            DESCRIPTION 
                "additional values for reserve concept 'backup exciter'"
            REVISION "200906260800Z"		-- June 26, 2009 at 08:00 GMT
            DESCRIPTION 
                "consideration of face-lift configuration in module compliances,
                measured values for power supply added,
                conditional groupDummyLoadRF added"
            REVISION "200905280900Z"		-- May 28, 2009 at 09:00 GMT
            DESCRIPTION 
                "information for additional (external) power supply added
                txRackRfOn, txRackRfOk, txRackTemperatureWarning added"
            REVISION "200903300900Z"		-- March 30, 2009 at 09:00 GMT
            DESCRIPTION 
                "txRackProbeNotCalibrated added"
            REVISION "200901290930Z"		-- January 29, 2009 at 09:30 GMT
            DESCRIPTION 
                "MODULE COMPLIANCE rsXx8000MFloReEquip"
            REVISION "200901070930Z"		-- January 07, 2009 at 09:30 GMT
            DESCRIPTION 
                "rfProbeCalibrationSetGain, rfProbeCalibrationSetOffset"
            REVISION "200812121430Z"		-- December 12, 2008 at 14:30 GMT
            DESCRIPTION 
                "rfProbeConfigurationLabel obsolete
                txRackExtCoolingWarning renamed to txRackGpiWarning
                txRackExtCoolingFault renamed to txRackGpiFault"
            REVISION "200810081100Z"		-- October 08, 2008 at 11:00 GMT
            DESCRIPTION 
                "cmdExcFrequency range up to 1500 MHz"
            REVISION "200809151500Z"		-- September 15, 2008 at 15:00 GMT
            DESCRIPTION 
                "new rackTable
                new txRackRfWarning, txRackRfFault, txRackReflectionWarning,
                    txRackReflectionFault
                new groupIndependentRacks"
            REVISION "200808260900Z"		-- August 26, 2008 at 09:00 GMT
            DESCRIPTION 
                "- rfProbesNetCCURfProbe1, rfProbesNetCCURfProbe2 read-only
                - cmdTxParametersetReSave obsolete"
            REVISION "200806130830Z"		-- June 13, 2008 at 08:30 GMT
            DESCRIPTION 
                "new TC LogbookFrame
                add logbookFrameNetCCU,
                    logbookFrameExciterA,
                    logbookFrameExciterB,
                    logbookFrameOutputstageA,
                    logbookFrameOutputstageB
                new cmdLoisInsertion,
                    cmdExcPidWOIS,
                    cmdExcPidWCC,
                    cmdExcPidWCON,
                    cmdExcPidLOIS,
                    cmdExcPidLCC,
                    cmdExcPidLCON,
                    excStatusPacketRateWOIS,
                    excStatusPacketRateWCC,
                    excStatusPacketRateWCON,
                    excStatusPacketRateLOIS,
                    excStatusPacketRateLCC,
                    excStatusPacketRateLCON
                rename excStatusMTIPacketMissCounter to excStatusMTISeqErrorCounter
                remove cmdExcLocalAreaPid,
                       cmdExcWideAreaPid,
                       excStatusLocalAreaPacketRate,
                       excStatusWideAreaPacketRate
                change range of cmdExcNetworkGeogrDelay to +-221500"
            REVISION "200804231030Z"		-- April 23, 2008 at 10:30 GMT
            DESCRIPTION 
                "use LogbookEntryMessagesExcTv,
                remove txExcFloModWarning,
                add txExcFloModSumWarning,
                    txExcFloModSumError,
                    txExcFloModSFNBufferWarning,
                    txExcFloModError,
                    txExcFloModMemoryError,
                    txExcFloModParameterUpdate"
            REVISION "200804151000Z"		-- April 15, 2008 at 10:00 GMT
            DESCRIPTION 
                "remove excStatusOfdmSymbol,
                add productInfoFloModVersion, 
                correct excPrecLinMaxGroupDelayRipple from INTEGER to Integer32"
            REVISION "200803311100Z"		-- March 31, 2008 at 11:00 GMT
            DESCRIPTION 
                "change range of cmdTxDelayTimeExcAutomatic and 
                cmdTxDelayTimeOstAutomatic to 1..60."
            REVISION "200801221100Z"		-- January 22, 2008 at 11:00 GMT
            DESCRIPTION 
                "sr - initial version."
            ::= { rsXx8000MibModule 24 }

        
    
--
-- Textual conventions
--
    
        LogbookFrame ::= TEXTUAL-CONVENTION
            DISPLAY-HINT 
                "4d 0ae0an0at0ar0ai0ae0as0a,0a 0af0ai0ar0as0at0a:0a 4d 1d 1d 4d 2d-1d-1d,1d:1d:1d,1a1d:1d0d"
            STATUS current
            DESCRIPTION 
                "A binary data structure for a complete logbook. 
                All fields are integers in big endian order.
                The DISPLAY-HINT ends after the first logbook entry. 
                
                field  octets  contents            range    description
                -----  ------  --------            -----    -----------
                  1     1-4    nr of entries       0..255   number of entries in the logbook
                
                the first entry (if nr of entries > 0):
                  2     5-8    number              1..255   a decreasing number from max 255 
                  3     9      type                1..3     see TC EventClass
                  4     10     slope               1..2     see TC LogbookEntrySlope
                  5     11-14  message ID                   see TC's LogbookEntryMessages...
                  6     15-16  year
                  7     17     month               1..12
                  8     18     day                 1..31
                  9     19     hour                0..23
                 10     20     minute              0..59
                 11     21     second              0..59
                 12     22     direction from UTC  '+','-'  ASCII characters 2Bh and 2Dh
                 13     23     hours from UTC      0..14
                 14     24     minutes from UTC    0..59
                 
                the second entry (if nr of entries > 1):
                 15-27  25-44  ...
                
                the next entries (if nr of entries > 2):
                 28...   45...
                "
            SYNTAX OCTET STRING (SIZE (4..5104))

    
--
-- Node definitions
--
    
        rsXx8000MediaFloTx OBJECT-IDENTITY
            STATUS current
            DESCRIPTION 
                "Xx8000 MediaFLO transmitter."
            ::= { rsXx8000 24 }

        
-- *****************************************************************************
-- **          object definitions
-- *****************************************************************************
        rsXx8000MediaFloTxObjs OBJECT IDENTIFIER ::= { rsXx8000MediaFloTx 1 }

        
-- commands *************************
        commandsTxTable OBJECT-TYPE
            SYNTAX SEQUENCE OF CommandsTxEntry
            MAX-ACCESS not-accessible
            STATUS current
            DESCRIPTION
                "This table contains important commands for the transmitter."
            ::= { rsXx8000MediaFloTxObjs 1 }

        
        commandsTxEntry OBJECT-TYPE
            SYNTAX CommandsTxEntry
            MAX-ACCESS not-accessible
            STATUS current
            DESCRIPTION
                "An entry for a designated device."
            INDEX { cmdDeviceIdx }
            ::= { commandsTxTable 1 }

        
        CommandsTxEntry ::=
            SEQUENCE { 
                cmdTxResetSumFault
                    Trigger,
                cmdTxParametersetLoad
                    Integer32,
                cmdTxParametersetSave
                    Integer32,
                cmdTxParametersetReSave
                    Trigger,
                cmdTxOperationModeProgram
                    SwitchOnOff,
                cmdTxOperationModeReserve
                    SwitchOnOff,
                cmdTxOpModeExcAutomatic
                    SwitchOnOff,
                cmdTxOpModeOstAutomatic
                    SwitchOnOff,
                cmdTxPreselectExciter
                    INTEGER,
                cmdTxPreselectOutputstage
                    INTEGER,
                cmdTxDelayTimeExcAutomatic
                    Integer32,
                cmdTxDelayTimeOstAutomatic
                    Integer32,
                cmdTxRfSwitch
                    INTEGER,
                cmdTxSystemMode
                    TvStandard,
                cmdTxProgramExciterPrio
                    SwitchOnOff,
                cmdTxChangeOver
                    Trigger,
                cmdTxSwitchPosition
                    INTEGER,
                cmdDeviceIdx
                    IndexAB,
                cmdExcTransmitterId
                    Integer32,
                cmdExcInfrastructureId
                    Integer32,
                cmdExcLocalTimeOffset
                    FloatingPoint,
                cmdExcDstIndicator
                    SwitchOnOff,
                cmdExcBandwidth
                    INTEGER,
                cmdLoisInsertion
                    SwitchOnOff,
                cmdExcPreselectInput
                    INTEGER,
                cmdExcAutoswitch
                    SwitchOnOff,
                cmdExcTypeOfLossOfInput
                    INTEGER,
                cmdExcInputFailDelayTime
                    Integer32,
                cmdExcOnInputFail
                    INTEGER,
                cmdExcNetworkGeogrDelay
                    Integer32,
                cmdExcClockRegulation
                    SwitchOnOff,
                cmdExcDeviationReset
                    SwitchOnOff,
                cmdExcDeviationLimit
                    Integer32,
                cmdExcPosPilotLength
                    INTEGER,
                cmdExcNationalLength
                    Integer32,
                cmdExcWideAreaId
                    Integer32,
                cmdExcLocalAreaId
                    Integer32,
                cmdExcClearErrors
                    Trigger,
                cmdExcClearResets
                    Trigger,
                cmdExcCoreReset
                    Trigger,
                cmdExcTestMode
                    INTEGER,
                cmdExcFrequency
                    Integer32,
                cmdExcReference
                    INTEGER,
                cmdExcOcxoAdjust
                    FloatingPoint,
                cmdExcRfOutput
                    SwitchOnOff,
                cmdExcRfOutputRegulation
                    SwitchOnOff,
                cmdExcRfOutputManualRfLevel
                    FloatingPoint,
                cmdExcRfOutputAttenuation
                    Integer32,
                cmdExcRfOutputRfSlope
                    FloatingPoint,
                cmdExcRfOutputModulationSlope
                    FloatingPoint,
                cmdExcRfIqAdjustStart
                    INTEGER,
                cmdExcRfIqAdjustTestsignal
                    SwitchOnOff,
                cmdExcRfIqAdjustBiasCoarseI
                    Integer32,
                cmdExcRfIqAdjustBiasCoarseQ
                    Integer32,
                cmdExcRfIqAdjustBiasFineI
                    Integer32,
                cmdExcRfIqAdjustBiasFineQ
                    Integer32,
                cmdExcRfIqAdjustGainI
                    Integer32,
                cmdExcRfIqAdjustGainQ
                    Integer32,
                cmdExcRfIqAdjustPhase
                    FloatingPoint,
                cmdExcMuteOnPPSFail
                    INTEGER,
                cmdExcMuteOnReferenceFail
                    INTEGER,
                cmdExcRefFailDelayTime
                    Integer32,
                cmdExcPidWOIS
                    Integer32,
                cmdExcPidWCC
                    Integer32,
                cmdExcPidWCON
                    Integer32,
                cmdExcPidLOIS
                    Integer32,
                cmdExcPidLCC
                    Integer32,
                cmdExcPidLCON
                    Integer32,
                cmdExcRfWarningLimit
                    FloatingPoint,
                cmdExcRfFailLimit
                    FloatingPoint,
                cmdExcOutputPower
                    FloatingPoint,
                cmdOstRefVoltageVision
                    FloatingPoint,
                cmdOstMaxOutletTempThreshold
                    Integer32,
                cmdExcMonitoringOutput
                    INTEGER,
                cmdExcFailDelayMode
                    FailDelayMode
             }

        cmdTxResetSumFault OBJECT-TYPE
            SYNTAX Trigger
            MAX-ACCESS read-write
            STATUS current
            DESCRIPTION
                "Reset all faults (in all modules) of the transmitter.
                
                You reset a designated transmitter (NetCCU, Exciters, Outputstages).
                An equivalent would be pressing RESET at this transmitters frontpanel.
                
                A GET will always return idle(1).
                A SET idle(1) will return NO_ERROR without doing anything."
            ::= { commandsTxEntry 1 }

        
        cmdTxParametersetLoad OBJECT-TYPE
            SYNTAX Integer32 (1..8)
            MAX-ACCESS read-write
            STATUS current
            DESCRIPTION
                "This loads the desired parameter set."
            ::= { commandsTxEntry 2 }

        
        cmdTxParametersetSave OBJECT-TYPE
            SYNTAX Integer32 (1..8)
            MAX-ACCESS read-write
            STATUS current
            DESCRIPTION
                "This saves the current settings to a designated parameter set."
            ::= { commandsTxEntry 3 }

        
        cmdTxParametersetReSave OBJECT-TYPE
            SYNTAX Trigger
            MAX-ACCESS read-write
            STATUS obsolete
            DESCRIPTION
                "This saves the changes to the current parameter set."
            ::= { commandsTxEntry 4 }

        
        cmdTxOperationModeProgram OBJECT-TYPE
            SYNTAX SwitchOnOff
            MAX-ACCESS read-write
            STATUS current
            DESCRIPTION
                "This switches the program path of the transmitter on/off."
            ::= { commandsTxEntry 5 }

        
        cmdTxOperationModeReserve OBJECT-TYPE
            SYNTAX SwitchOnOff
            MAX-ACCESS read-write
            STATUS current
            DESCRIPTION
                "This switches the reserve path of the transmitter on/off."
            ::= { commandsTxEntry 6 }

        
        cmdTxOpModeExcAutomatic OBJECT-TYPE
            SYNTAX SwitchOnOff
            MAX-ACCESS read-write
            STATUS current
            DESCRIPTION
                "This switches the exciter automatic on/off."
            ::= { commandsTxEntry 7 }

        
        cmdTxOpModeOstAutomatic OBJECT-TYPE
            SYNTAX SwitchOnOff
            MAX-ACCESS read-write
            STATUS current
            DESCRIPTION
                "This switches the outputstage automatic on/off.
                
                This paramter is only available for systems with an automatic output switch."
            ::= { commandsTxEntry 8 }

        
        cmdTxPreselectExciter OBJECT-TYPE
            SYNTAX INTEGER
                {
                exciterA(1),
                exciterB(2)
                }
            MAX-ACCESS read-write
            STATUS current
            DESCRIPTION
                "This sets exciterA or exciterB to program path (antenna) of the transmitter."
            ::= { commandsTxEntry 9 }

        
        cmdTxPreselectOutputstage OBJECT-TYPE
            SYNTAX INTEGER
                {
                outputstageA(1),
                outputstageB(2),
                bothToAntenna(3),
                bothToDummyLoad(4)
                }
            MAX-ACCESS read-write
            STATUS current
            DESCRIPTION
                "This sets 
                - outputstageA or 
                - outputstageB or
                - both
                to program path (antenna) of the transmitter,
                or it sets both to dummyload.
                
                The settings bothToAntenna(3) and bothToDummyLoad(4) are only settable 
                for ActiveReserve systems.
                
                This paramter is only available for systems with an automatic output switch."
            ::= { commandsTxEntry 10 }

        
        cmdTxDelayTimeExcAutomatic OBJECT-TYPE
            SYNTAX Integer32 (1..60)
            UNITS "seconds"
            MAX-ACCESS read-write
            STATUS current
            DESCRIPTION
                "This sets the exciter automatic delay time."
            ::= { commandsTxEntry 11 }

        
        cmdTxDelayTimeOstAutomatic OBJECT-TYPE
            SYNTAX Integer32 (1..60)
            UNITS "seconds"
            MAX-ACCESS read-write
            STATUS current
            DESCRIPTION
                "This sets the outputstage automatic delay time.
                
                This paramter is only available for systems with an automatic output switch."
            ::= { commandsTxEntry 12 }

        
        cmdTxRfSwitch OBJECT-TYPE
            SYNTAX INTEGER
                {
                antenna(1),
                dummyLoad(2)
                }
            MAX-ACCESS read-write
            STATUS current
            DESCRIPTION
                "RF switch for single-ended systems."
            ::= { commandsTxEntry 13 }

        
        cmdTxSystemMode OBJECT-TYPE
            SYNTAX TvStandard
            MAX-ACCESS read-write
            STATUS current
            DESCRIPTION
                "This object gives you the possibility of switching the TV standard
                of a whole system with NetCCU with only one command.
                Not applicable for N+1 or NTx systems.
                The value 'test' cannot be written."
            ::= { commandsTxEntry 15 }

        
        cmdTxProgramExciterPrio OBJECT-TYPE
            SYNTAX SwitchOnOff
            MAX-ACCESS read-write
            STATUS current
            DESCRIPTION
                "Enables/Disables priority usage of program exciter"
            ::= { commandsTxEntry 20 }

        
        cmdTxChangeOver OBJECT-TYPE
            SYNTAX Trigger
            MAX-ACCESS read-write
            STATUS current
            DESCRIPTION
                "Performs a change over"
            ::= { commandsTxEntry 21 }

        
        cmdTxSwitchPosition OBJECT-TYPE
            SYNTAX INTEGER
                {
                undefined(1),
                controlExcOnAmp(2),
                programExcOnAmp(3)
                }
            MAX-ACCESS read-only
            STATUS current
            DESCRIPTION
                "Shows the actual switch position.
                The program exciter is connected to input 1 (RF IN 1),
                the control exciter is connected to input 2 (RF IN 2) of the base amplifier."
            ::= { commandsTxEntry 22 }

        
        cmdDeviceIdx OBJECT-TYPE
            SYNTAX IndexAB
            MAX-ACCESS not-accessible
            STATUS current
            DESCRIPTION
                "This column is used to show parameters for both exiters, if you have 
                dualdrive transmitters."
            ::= { commandsTxEntry 30 }

        
--    exciter    
        cmdExcTransmitterId OBJECT-TYPE
            SYNTAX Integer32 (0..65535)
            MAX-ACCESS read-write
            STATUS current
            DESCRIPTION
                "The unique transmitter ID."
            ::= { commandsTxEntry 31 }

        
        cmdExcInfrastructureId OBJECT-TYPE
            SYNTAX Integer32 (0..65535)
            MAX-ACCESS read-write
            STATUS current
            DESCRIPTION
                "The network sets this field to the identifier 
                assigned to the local-area infrastructure."
            ::= { commandsTxEntry 32 }

        
        cmdExcLocalTimeOffset OBJECT-TYPE
            SYNTAX FloatingPoint
            UNITS "hour"
            MAX-ACCESS read-write
            STATUS current
            DESCRIPTION
                "The local time offset in increments of 0.5 hours (-12.0 ... 14.0)."
            ::= { commandsTxEntry 33 }

        
        cmdExcDstIndicator OBJECT-TYPE
            SYNTAX SwitchOnOff
            MAX-ACCESS read-write
            STATUS current
            DESCRIPTION
                "The switch for daylight saving time."
            ::= { commandsTxEntry 34 }

        
        cmdExcBandwidth OBJECT-TYPE
            SYNTAX INTEGER
                {
                mhz5(1),
                mhz6(2),
                mhz7(3),
                mhz8(4)
                }
            MAX-ACCESS read-write
            STATUS current
            DESCRIPTION
                "The bandwidth."
            ::= { commandsTxEntry 35 }

        
        cmdLoisInsertion OBJECT-TYPE
            SYNTAX SwitchOnOff
            MAX-ACCESS read-write
            STATUS current
            DESCRIPTION
                "Enables insertion of Infrastructure ID, Local Time Offset, and Daylight Savings 
                indicator into the LOIS SystemParameters message."
            ::= { commandsTxEntry 36 }

        
        cmdExcPreselectInput OBJECT-TYPE
            SYNTAX INTEGER
                {
                input1(1),
                input2(2)
                }
            MAX-ACCESS read-write
            STATUS current
            DESCRIPTION
                "In case of a prioritisation of a certain input it can selected here. When both
                inputs are equivalent this parameter only takes effect when switching on the input
                automatic."
            ::= { commandsTxEntry 38 }

        
        cmdExcAutoswitch OBJECT-TYPE
            SYNTAX SwitchOnOff
            MAX-ACCESS read-write
            STATUS current
            DESCRIPTION
                "Activates the input automatic. If a loss of input signal is detected on the
                current input the reserve input will be used instead."
            ::= { commandsTxEntry 39 }

        
        cmdExcTypeOfLossOfInput OBJECT-TYPE
            SYNTAX INTEGER
                {
                warning(1),
                fault(2)
                }
            MAX-ACCESS read-write
            STATUS current
            DESCRIPTION
                "If WARNING is selected only a warning is produced when input signal gets lost. If
                FAULT is choosen an additional sum error is produced after the fail delay time.
                This will cause a switchover to a reserve exciter."
            ::= { commandsTxEntry 40 }

        
        cmdExcInputFailDelayTime OBJECT-TYPE
            SYNTAX Integer32 (0..600)
            UNITS "Seconds"
            MAX-ACCESS read-write
            STATUS current
            DESCRIPTION
                "The time between detecting a loss of input signal and displaying a failure."
            ::= { commandsTxEntry 41 }

        
        cmdExcOnInputFail OBJECT-TYPE
            SYNTAX INTEGER
                {
                noMute(1),
                mute(2)
                }
            MAX-ACCESS read-write
            STATUS current
            DESCRIPTION
                "Select if the exciter mutes if input signal on the active channel is not detected
                or not ok."
            ::= { commandsTxEntry 42 }

        
        cmdExcNetworkGeogrDelay OBJECT-TYPE
            SYNTAX Integer32 (-221500..221500)
            UNITS "Nanoseconds"
            MAX-ACCESS read-write
            STATUS current
            DESCRIPTION
                "The latency associated with the geographic separation of transmitters."
            ::= { commandsTxEntry 46 }

        
        cmdExcClockRegulation OBJECT-TYPE
            SYNTAX SwitchOnOff
            MAX-ACCESS read-write
            STATUS current
            DESCRIPTION
                "The switch for clock regulation."
            ::= { commandsTxEntry 47 }

        
        cmdExcDeviationReset OBJECT-TYPE
            SYNTAX SwitchOnOff
            MAX-ACCESS read-write
            STATUS current
            DESCRIPTION
                "The switch for deviation reset."
            ::= { commandsTxEntry 48 }

        
        cmdExcDeviationLimit OBJECT-TYPE
            SYNTAX Integer32 (500..1000000)
            UNITS "Nanoseconds"
            MAX-ACCESS read-write
            STATUS current
            DESCRIPTION
                "The deviation limit."
            ::= { commandsTxEntry 49 }

        
        cmdExcPosPilotLength OBJECT-TYPE
            SYNTAX INTEGER
                {
                length02(1),
                length06(2),
                length10(3),
                length14(4)
                }
            MAX-ACCESS read-write
            STATUS current
            DESCRIPTION
                "The length of position pilot."
            ::= { commandsTxEntry 51 }

        
        cmdExcNationalLength OBJECT-TYPE
            SYNTAX Integer32 (0..391)
            MAX-ACCESS read-write
            STATUS current
            DESCRIPTION
                "The national length."
            ::= { commandsTxEntry 52 }

        
        cmdExcWideAreaId OBJECT-TYPE
            SYNTAX Integer32 (0..15)
            MAX-ACCESS read-write
            STATUS current
            DESCRIPTION
                "The Wide Area ID for the receiver."
            ::= { commandsTxEntry 53 }

        
        cmdExcLocalAreaId OBJECT-TYPE
            SYNTAX Integer32 (0..15)
            MAX-ACCESS read-write
            STATUS current
            DESCRIPTION
                "The Local Area ID for the receiver."
            ::= { commandsTxEntry 54 }

        
        cmdExcClearErrors OBJECT-TYPE
            SYNTAX Trigger
            MAX-ACCESS read-write
            STATUS current
            DESCRIPTION
                "Reset error counters of modulator."
            ::= { commandsTxEntry 60 }

        
        cmdExcClearResets OBJECT-TYPE
            SYNTAX Trigger
            MAX-ACCESS read-write
            STATUS current
            DESCRIPTION
                "Reset the counter of modulator resets."
            ::= { commandsTxEntry 61 }

        
        cmdExcCoreReset OBJECT-TYPE
            SYNTAX Trigger
            MAX-ACCESS read-write
            STATUS current
            DESCRIPTION
                "Restart the modulator core."
            ::= { commandsTxEntry 62 }

        
        cmdExcTestMode OBJECT-TYPE
            SYNTAX INTEGER
                {
                off(1),
                singleCarrier(2),
                prbs(3),
                nullTdm1(4)
                }
            MAX-ACCESS read-write
            STATUS current
            DESCRIPTION
                "Enable the test mode and allow to filter some sub carriers."
            ::= { commandsTxEntry 63 }

        
        cmdExcFrequency OBJECT-TYPE
            SYNTAX Integer32 (47000000..1500000000)
            UNITS "Hertz"
            MAX-ACCESS read-write
            STATUS current
            DESCRIPTION
                "Adjusts the RF frequency."
            ::= { commandsTxEntry 66 }

        
        cmdExcReference OBJECT-TYPE
            SYNTAX INTEGER
                {
                intern(1),
                extern5Mhz(2),
                extern10Mhz(3),
                extern1PPS(4)
                }
            MAX-ACCESS read-write
            STATUS current
            DESCRIPTION
                "The Source of the reference signal."
            ::= { commandsTxEntry 67 }

        
        cmdExcOcxoAdjust OBJECT-TYPE
            SYNTAX FloatingPoint
            MAX-ACCESS read-write
            STATUS current
            DESCRIPTION
                "Adjusts the internal reference (0 ... 65535)."
            ::= { commandsTxEntry 68 }

        
        cmdExcRfOutput OBJECT-TYPE
            SYNTAX SwitchOnOff
            MAX-ACCESS read-write
            STATUS current
            DESCRIPTION
                "Turns on/switches off the output signal. This switch takes the same effect as the 
                switch on the frontpanel of the exciter."
            ::= { commandsTxEntry 70 }

        
        cmdExcRfOutputRegulation OBJECT-TYPE
            SYNTAX SwitchOnOff
            MAX-ACCESS read-write
            STATUS current
            DESCRIPTION
                "Turns on/switches off the automatic output level regulation."
            ::= { commandsTxEntry 71 }

        
        cmdExcRfOutputManualRfLevel OBJECT-TYPE
            SYNTAX FloatingPoint
            UNITS "Percent"
            MAX-ACCESS read-write
            STATUS current
            DESCRIPTION
                "Adjusts the RF level (0.0 ... 100.0). The value relates to an attenuation 
                of 0 dB."
            ::= { commandsTxEntry 72 }

        
        cmdExcRfOutputAttenuation OBJECT-TYPE
            SYNTAX Integer32 (0..9)
            UNITS "dB"
            MAX-ACCESS read-write
            STATUS current
            DESCRIPTION
                "Activates internal attenuators to reduce the output level of the exciter.
                Adjustable in steps of 3 dB only."
            ::= { commandsTxEntry 73 }

        
        cmdExcRfOutputRfSlope OBJECT-TYPE
            SYNTAX FloatingPoint
            UNITS "Percent"
            MAX-ACCESS read-write
            STATUS current
            DESCRIPTION
                "Adjusts a slope in the RF signal (-50.0 ... 50.0)."
            ::= { commandsTxEntry 74 }

        
        cmdExcRfOutputModulationSlope OBJECT-TYPE
            SYNTAX FloatingPoint
            UNITS "Percent"
            MAX-ACCESS read-write
            STATUS current
            DESCRIPTION
                "Modulation slope (-50.0 ... 50.0)."
            ::= { commandsTxEntry 75 }

        
        cmdExcRfIqAdjustStart OBJECT-TYPE
            SYNTAX INTEGER
                {
                break(1),
                start(2)
                }
            MAX-ACCESS read-write
            STATUS current
            DESCRIPTION
                "Starts the automatic IQ adjustment. It works for the current used local 1 
                frequency and lasts up to 5 minutes. In this time the output will be muted. During 
                the adjustment no transmitter parameter shall be changed. Break will stop the 
                automatic immediately. The IQ modulator looses its adjustment!
                Read values mean idle(1) and started(2)."
            ::= { commandsTxEntry 77 }

        
        cmdExcRfIqAdjustTestsignal OBJECT-TYPE
            SYNTAX SwitchOnOff
            MAX-ACCESS read-write
            STATUS current
            DESCRIPTION
                "Generates a test signal to adjust the IQ modulation. It is necessary to 
                disconnect the rf-cable to the output stages."
            ::= { commandsTxEntry 78 }

        
        cmdExcRfIqAdjustBiasCoarseI OBJECT-TYPE
            SYNTAX Integer32 (-1023..1023)
            MAX-ACCESS read-write
            STATUS current
            DESCRIPTION
                "Adjusts the offset for I in huge steps."
            ::= { commandsTxEntry 79 }

        
        cmdExcRfIqAdjustBiasCoarseQ OBJECT-TYPE
            SYNTAX Integer32 (-1023..1023)
            MAX-ACCESS read-write
            STATUS current
            DESCRIPTION
                "Adjusts the offset for Q in huge steps."
            ::= { commandsTxEntry 80 }

        
        cmdExcRfIqAdjustBiasFineI OBJECT-TYPE
            SYNTAX Integer32 (-32767..32767)
            MAX-ACCESS read-write
            STATUS current
            DESCRIPTION
                "Adjusts the offset for I in small steps."
            ::= { commandsTxEntry 81 }

        
        cmdExcRfIqAdjustBiasFineQ OBJECT-TYPE
            SYNTAX Integer32 (-32767..32767)
            MAX-ACCESS read-write
            STATUS current
            DESCRIPTION
                "Adjusts the offset for Q in small steps."
            ::= { commandsTxEntry 82 }

        
        cmdExcRfIqAdjustGainI OBJECT-TYPE
            SYNTAX Integer32 (0..255)
            MAX-ACCESS read-write
            STATUS current
            DESCRIPTION
                "Adjusts the gain for I in small steps."
            ::= { commandsTxEntry 83 }

        
        cmdExcRfIqAdjustGainQ OBJECT-TYPE
            SYNTAX Integer32 (0..255)
            MAX-ACCESS read-write
            STATUS current
            DESCRIPTION
                "Adjusts the gain for Q in small steps."
            ::= { commandsTxEntry 84 }

        
        cmdExcRfIqAdjustPhase OBJECT-TYPE
            SYNTAX FloatingPoint
            MAX-ACCESS read-write
            STATUS current
            DESCRIPTION
                "Adjusts the phase between I and Q (-14.000 ... 14.000)."
            ::= { commandsTxEntry 85 }

        
        cmdExcMuteOnPPSFail OBJECT-TYPE
            SYNTAX INTEGER
                {
                off(1),
                onlyAtStartup(2),
                afterFailDelayTime(3)
                }
            MAX-ACCESS read-write
            STATUS current
            DESCRIPTION
                "Select the behaviour if the external second pulse is not available."
            ::= { commandsTxEntry 88 }

        
        cmdExcMuteOnReferenceFail OBJECT-TYPE
            SYNTAX INTEGER
                {
                off(1),
                onlyAtStartup(2),
                afterFailDelayTime(3)
                }
            MAX-ACCESS read-write
            STATUS current
            DESCRIPTION
                "Select the behaviour if the external reference is not available."
            ::= { commandsTxEntry 89 }

        
        cmdExcRefFailDelayTime OBJECT-TYPE
            SYNTAX Integer32 (0..24)
            UNITS "Hours"
            MAX-ACCESS read-write
            STATUS current
            DESCRIPTION
                "Adjusts the time after the RF will be muted in case of a reference problem.
                Zero hours means react immediately."
            ::= { commandsTxEntry 90 }

        
        cmdExcPidWOIS OBJECT-TYPE
            SYNTAX Integer32 (0..8191)
            MAX-ACCESS read-write
            STATUS current
            DESCRIPTION
                "This value is programmed to match the desired Wide Area OIS PID."
            ::= { commandsTxEntry 91 }

        
        cmdExcPidWCC OBJECT-TYPE
            SYNTAX Integer32 (0..8191)
            MAX-ACCESS read-write
            STATUS current
            DESCRIPTION
                "This value is programmed to match the desired Wide Area control channel PID."
            ::= { commandsTxEntry 92 }

        
        cmdExcPidWCON OBJECT-TYPE
            SYNTAX Integer32 (0..8191)
            MAX-ACCESS read-write
            STATUS current
            DESCRIPTION
                "This value is programmed to match the desired Wide Area Content PID."
            ::= { commandsTxEntry 93 }

        
        cmdExcPidLOIS OBJECT-TYPE
            SYNTAX Integer32 (0..8191)
            MAX-ACCESS read-write
            STATUS current
            DESCRIPTION
                "This value is programmed to match the desired Local Area OIS PID."
            ::= { commandsTxEntry 94 }

        
        cmdExcPidLCC OBJECT-TYPE
            SYNTAX Integer32 (0..8191)
            MAX-ACCESS read-write
            STATUS current
            DESCRIPTION
                "This value is programmed to match the desired Local Area control channel PID."
            ::= { commandsTxEntry 95 }

        
        cmdExcPidLCON OBJECT-TYPE
            SYNTAX Integer32 (0..8191)
            MAX-ACCESS read-write
            STATUS current
            DESCRIPTION
                "This value is programmed to match the desired Local Area Content PID."
            ::= { commandsTxEntry 96 }

        
        cmdExcRfWarningLimit OBJECT-TYPE
            SYNTAX FloatingPoint
            UNITS "dB"
            MAX-ACCESS read-write
            STATUS current
            DESCRIPTION
                "Warning limit for the RF control.
                min: -15.0, max: 0.0"
            ::= { commandsTxEntry 97 }

        
        cmdExcRfFailLimit OBJECT-TYPE
            SYNTAX FloatingPoint
            UNITS "dB"
            MAX-ACCESS read-write
            STATUS current
            DESCRIPTION
                "Fault limit for the RF control.
                min: -15.0, max: 0.0"
            ::= { commandsTxEntry 98 }

        
        cmdExcOutputPower OBJECT-TYPE
            SYNTAX FloatingPoint
            UNITS "W"
            MAX-ACCESS read-write
            STATUS current
            DESCRIPTION
                "amplifier output power
                0 ... 400 W"
            ::= { commandsTxEntry 99 }

        
-- output stage    
        cmdOstRefVoltageVision OBJECT-TYPE
            SYNTAX FloatingPoint
            UNITS "Percent"
            MAX-ACCESS read-write
            STATUS current
            DESCRIPTION
                "This adjusts the output power of the amplifier.
                This value is settable with maximal 1 position after point (example 11.2)."
            ::= { commandsTxEntry 100 }

        
        cmdOstMaxOutletTempThreshold OBJECT-TYPE
            SYNTAX Integer32 (45..65)
            UNITS "Degree Celsius"
            MAX-ACCESS read-write
            STATUS current
            DESCRIPTION
                "This sets the threshold for the outlet temperature."
            ::= { commandsTxEntry 101 }

        
        cmdExcMonitoringOutput OBJECT-TYPE
            SYNTAX INTEGER
                {
                off(1),
                reference10MHz(2),
                generated1PPS(3),
                kHz1(4),
                pulse1PPS(5)
                }
            MAX-ACCESS read-write
            STATUS current
            DESCRIPTION
                "Selects which signal appears at the monitoring output."
            ::= { commandsTxEntry 110 }

        
        cmdExcFailDelayMode OBJECT-TYPE
            SYNTAX FailDelayMode
            MAX-ACCESS read-write
            STATUS current
            DESCRIPTION
                "Condition when the fail delay time is used."
            ::= { commandsTxEntry 115 }

        
-- summary info *************************
        summaryInfo OBJECT IDENTIFIER ::= { rsXx8000MediaFloTxObjs 2 }

        
        summaryFaultTx OBJECT-TYPE
            SYNTAX TruthValue
            MAX-ACCESS read-only
            STATUS current
            DESCRIPTION
                "This indicates a summary fault of the transmitter.
                true(1)  --> summary fault
                false(2) --> no summary fault
                
                There is a fault of at least one module (e.g. Exciter) which causes this summary 
                fault.
                
                An equivalent would be the LED Fault at the transmitters frontpanel."
            ::= { summaryInfo 1 }

        
        summaryWarningTx OBJECT-TYPE
            SYNTAX TruthValue
            MAX-ACCESS read-only
            STATUS current
            DESCRIPTION
                "This indicates a summary warning of the transmitter.
                true(1)  --> summary warning
                false(2) --> no summary warning
                
                There is a fault of at least one module (e.g. Exciter) which causes this summary 
                warning.
                
                An equivalent would be the LED Warning at the transmitters frontpanel."
            ::= { summaryInfo 2 }

        
        localModeTx OBJECT-TYPE
            SYNTAX TruthValue
            MAX-ACCESS read-only
            STATUS current
            DESCRIPTION
                "This indicates the local/remote-mode of the transmitter.
                true(1)  --> local
                false(2) --> remote
                
                The transmitter is either in local-mode or in remote-mode. 
                For security reasons it is not possible to set this value!
                
                An equivalent would the LED Local at the transmitters frontpanel."
            ::= { summaryInfo 3 }

        
        rfOnTx OBJECT-TYPE
            SYNTAX TruthValue
            MAX-ACCESS read-only
            STATUS current
            DESCRIPTION
                "The RF is present for the corresponding transmitter."
            ::= { summaryInfo 4 }

        
        forwardPower OBJECT-TYPE
            SYNTAX FloatingPoint
            UNITS "Watt"
            MAX-ACCESS read-only
            STATUS current
            DESCRIPTION
                "The measured forwarded power [W] of the transmitter. 
                For Active Reserve systems it is the sum of both outputstages."
            ::= { summaryInfo 5 }

        
        reflectedPower OBJECT-TYPE
            SYNTAX FloatingPoint
            UNITS "Watt"
            MAX-ACCESS read-only
            STATUS current
            DESCRIPTION
                "The measured reflected power [W] of the transmitter. 
                For Active Reserve systems it is the sum of both outputstages.
                
                Not available for lowpower systems."
            ::= { summaryInfo 6 }

        
        summaryFaultExcA OBJECT-TYPE
            SYNTAX TruthValue
            MAX-ACCESS read-only
            STATUS current
            DESCRIPTION
                "This indicates a summary fault of exciterA."
            ::= { summaryInfo 7 }

        
        summaryFaultOstA OBJECT-TYPE
            SYNTAX TruthValue
            MAX-ACCESS read-only
            STATUS current
            DESCRIPTION
                "This indicates a summary fault of outputstageA."
            ::= { summaryInfo 8 }

        
        summaryFaultExcB OBJECT-TYPE
            SYNTAX TruthValue
            MAX-ACCESS read-only
            STATUS current
            DESCRIPTION
                "This indicates a summary fault of exciterA."
            ::= { summaryInfo 9 }

        
        summaryFaultOstB OBJECT-TYPE
            SYNTAX TruthValue
            MAX-ACCESS read-only
            STATUS current
            DESCRIPTION
                "This indicates a summary fault of outputstageB."
            ::= { summaryInfo 10 }

        
        exciterAutomaticReady OBJECT-TYPE
            SYNTAX TruthValue
            MAX-ACCESS read-only
            STATUS current
            DESCRIPTION
                "The Exciter Automatic is Ready. 
                In case of any fault on one exciter, there will be a switchover to the other 
                exciter."
            ::= { summaryInfo 11 }

        
        exciterAutomaticChanged OBJECT-TYPE
            SYNTAX TruthValue
            MAX-ACCESS read-only
            STATUS current
            DESCRIPTION
                "The Exciter Automatic has changed. 
                There was a fault on one exciter which lead to this changeover."
            ::= { summaryInfo 12 }

        
        exciterAutomaticFault OBJECT-TYPE
            SYNTAX TruthValue
            MAX-ACCESS read-only
            STATUS current
            DESCRIPTION
                "The Exciter Automatic is faulty. 
                In case of any fault on one exciter, there will be no switchover to the other 
                exciter, because of this fault."
            ::= { summaryInfo 13 }

        
        outputstageAutomaticReady OBJECT-TYPE
            SYNTAX TruthValue
            MAX-ACCESS read-only
            STATUS current
            DESCRIPTION
                "The Outputstage Automatic is Ready. 
                In case of any fault on one outputstage, there will be a switchover to the other 
                outputstage.
                
                This paramter is only available for systems with an automatic output switch."
            ::= { summaryInfo 14 }

        
        outputstageAutomaticChanged OBJECT-TYPE
            SYNTAX TruthValue
            MAX-ACCESS read-only
            STATUS current
            DESCRIPTION
                "The Outputstage Automatic has changed. 
                There was a fault on one outputstage which lead to this changeover.
                
                This paramter is only available for systems with an automatic output switch."
            ::= { summaryInfo 15 }

        
        outputstageAutomaticFault OBJECT-TYPE
            SYNTAX TruthValue
            MAX-ACCESS read-only
            STATUS current
            DESCRIPTION
                "The Outputstage Automatic is faulty. 
                In case of any fault on one outputstage, there will be no switchover to the other 
                outputstage, because of this fault.
                
                This paramter is only available for systems with an automatic output switch."
            ::= { summaryInfo 16 }

        
        noConnectionExcA OBJECT-TYPE
            SYNTAX TruthValue
            MAX-ACCESS read-only
            STATUS current
            DESCRIPTION
                "No Connection between NetCCU and ExciterA."
            ::= { summaryInfo 17 }

        
        noConnectionOstA OBJECT-TYPE
            SYNTAX TruthValue
            MAX-ACCESS read-only
            STATUS current
            DESCRIPTION
                "No Connection between NetCCU and OutputstageA."
            ::= { summaryInfo 18 }

        
        noConnectionExcB OBJECT-TYPE
            SYNTAX TruthValue
            MAX-ACCESS read-only
            STATUS current
            DESCRIPTION
                "No Connection between NetCCU and ExciterB."
            ::= { summaryInfo 19 }

        
        noConnectionOstB OBJECT-TYPE
            SYNTAX TruthValue
            MAX-ACCESS read-only
            STATUS current
            DESCRIPTION
                "No Connection between NetCCU and OutputstageB."
            ::= { summaryInfo 20 }

        
        activeExcA OBJECT-TYPE
            SYNTAX TruthValue
            MAX-ACCESS read-only
            STATUS current
            DESCRIPTION
                "ExciterA is currently active."
            ::= { summaryInfo 21 }

        
        activeOstA OBJECT-TYPE
            SYNTAX TruthValue
            MAX-ACCESS read-only
            STATUS current
            DESCRIPTION
                "OutputstageA is currently active."
            ::= { summaryInfo 22 }

        
        activeExcB OBJECT-TYPE
            SYNTAX TruthValue
            MAX-ACCESS read-only
            STATUS current
            DESCRIPTION
                "ExciterB is currently active."
            ::= { summaryInfo 23 }

        
        activeOstB OBJECT-TYPE
            SYNTAX TruthValue
            MAX-ACCESS read-only
            STATUS current
            DESCRIPTION
                "OutputstageB is currently active."
            ::= { summaryInfo 24 }

        
        forwardPowerOstA OBJECT-TYPE
            SYNTAX FloatingPoint
            UNITS "Watt"
            MAX-ACCESS read-only
            STATUS current
            DESCRIPTION
                "The measured forwarded power [W] of the OutputstageA."
            ::= { summaryInfo 25 }

        
        reflectedPowerOstA OBJECT-TYPE
            SYNTAX FloatingPoint
            UNITS "Watt"
            MAX-ACCESS read-only
            STATUS current
            DESCRIPTION
                "The measured reflected power [W] of the OutputstageA.
                
                Not available for lowpower systems."
            ::= { summaryInfo 26 }

        
        forwardPowerOstB OBJECT-TYPE
            SYNTAX FloatingPoint
            UNITS "Watt"
            MAX-ACCESS read-only
            STATUS current
            DESCRIPTION
                "The measured forwarded power [W] of the OutputstageB."
            ::= { summaryInfo 27 }

        
        reflectedPowerOstB OBJECT-TYPE
            SYNTAX FloatingPoint
            UNITS "Watt"
            MAX-ACCESS read-only
            STATUS current
            DESCRIPTION
                "The measured reflected power [W] of the OutputstageB.
                
                Not available for lowpower systems."
            ::= { summaryInfo 28 }

        
        powerSupply OBJECT-TYPE
            SYNTAX FloatingPoint
            UNITS "volt"
            MAX-ACCESS read-only
            STATUS current
            DESCRIPTION
                "Monitoring value of the output voltages of the power supply."
            ::= { summaryInfo 29 }

        
        additionalPowerSupply OBJECT-TYPE
            SYNTAX TruthValue
            MAX-ACCESS read-only
            STATUS current
            DESCRIPTION
                "Shows whether the NetCCU has an additional (external) power supply."
            ::= { summaryInfo 30 }

        
        internalPowerSupply OBJECT-TYPE
            SYNTAX FloatingPoint
            UNITS "volt"
            MAX-ACCESS read-only
            STATUS current
            DESCRIPTION
                "Monitoring value of the output voltages of the internal power supply."
            ::= { summaryInfo 31 }

        
        externalPowerSupply OBJECT-TYPE
            SYNTAX FloatingPoint
            UNITS "volt"
            MAX-ACCESS read-only
            STATUS current
            DESCRIPTION
                "Monitoring value of the output voltages of the external power supply."
            ::= { summaryInfo 32 }

        
        detailedInfo OBJECT IDENTIFIER ::= { rsXx8000MediaFloTxObjs 3 }

        
-- ost table  *************************
        ostTable OBJECT-TYPE
            SYNTAX SEQUENCE OF OstEntry
            MAX-ACCESS not-accessible
            STATUS current
            DESCRIPTION
                "The table of racks."
            ::= { detailedInfo 3 }

        
        ostEntry OBJECT-TYPE
            SYNTAX OstEntry
            MAX-ACCESS not-accessible
            STATUS current
            DESCRIPTION
                "A row (an entry) for one rack or amplifier respectively."
            INDEX { ostIdx, ostRackIdx, ostRackAmpIdx }
            ::= { ostTable 1 }

        
        OstEntry ::=
            SEQUENCE { 
                ostIdx
                    IndexAB,
                ostRackIdx
                    IndexRack,
                ostRackInletTemperature
                    FloatingPoint,
                ostRackOutletTemperature
                    FloatingPoint,
                ostRackAuxPowerSupply
                    FloatingPoint,
                ostRackAmpIdx
                    IndexAmplifier,
                ostRackAmpI1A
                    FloatingPoint,
                ostRackAmpI2A
                    FloatingPoint,
                ostRackAmpI3A
                    FloatingPoint,
                ostRackAmpI4A
                    FloatingPoint,
                ostRackAmpI1B
                    FloatingPoint,
                ostRackAmpI2B
                    FloatingPoint,
                ostRackAmpI3B
                    FloatingPoint,
                ostRackAmpI4B
                    FloatingPoint,
                ostRackAmpIDrv
                    FloatingPoint,
                ostRackAmpUDc
                    FloatingPoint,
                ostRackAmpIDc
                    FloatingPoint,
                ostRackAmpUDcControl
                    FloatingPoint,
                ostRackAmpUReg
                    FloatingPoint,
                ostRackAmpPowerA
                    FloatingPoint,
                ostRackAmpPowerB
                    FloatingPoint,
                ostRackAmpPowerOut
                    FloatingPoint,
                ostRackAmpPowerReflection
                    FloatingPoint,
                ostRackAmpPowerReference
                    FloatingPoint,
                ostRackAmpDeltaPhase
                    FloatingPoint,
                ostRackAmpCmdDeltaPhase
                    FloatingPoint
             }

        ostIdx OBJECT-TYPE
            SYNTAX IndexAB
            MAX-ACCESS not-accessible
            STATUS current
            DESCRIPTION
                "The dedicated outputstage (A/B)."
            ::= { ostEntry 1 }

        
        ostRackIdx OBJECT-TYPE
            SYNTAX IndexRack
            MAX-ACCESS not-accessible
            STATUS current
            DESCRIPTION
                "The rack number (1..10)."
            ::= { ostEntry 2 }

        
        ostRackInletTemperature OBJECT-TYPE
            SYNTAX FloatingPoint
            UNITS "Degree Celsius"
            MAX-ACCESS read-only
            STATUS current
            DESCRIPTION
                "The inlet temperature."
            ::= { ostEntry 3 }

        
        ostRackOutletTemperature OBJECT-TYPE
            SYNTAX FloatingPoint
            UNITS "Degree Celsius"
            MAX-ACCESS read-only
            STATUS current
            DESCRIPTION
                "The outlet temperature."
            ::= { ostEntry 4 }

        
        ostRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { ostEntry 5 }

        
        ostRackAmpIdx OBJECT-TYPE
            SYNTAX IndexAmplifier
            MAX-ACCESS not-accessible
            STATUS current
            DESCRIPTION
                "Amplifier Index"
            ::= { ostEntry 400 }

        
        ostRackAmpI1A OBJECT-TYPE
            SYNTAX FloatingPoint
            UNITS "Ampere"
            MAX-ACCESS read-only
            STATUS current
            DESCRIPTION
                "The power amplifier module current (I_1A)."
            ::= { ostEntry 401 }

        
        ostRackAmpI2A OBJECT-TYPE
            SYNTAX FloatingPoint
            UNITS "Ampere"
            MAX-ACCESS read-only
            STATUS current
            DESCRIPTION
                "The power amplifier module current (I_2A)."
            ::= { ostEntry 402 }

        
        ostRackAmpI3A OBJECT-TYPE
            SYNTAX FloatingPoint
            UNITS "Ampere"
            MAX-ACCESS read-only
            STATUS current
            DESCRIPTION
                "The power amplifier module current (I_3A)."
            ::= { ostEntry 403 }

        
        ostRackAmpI4A OBJECT-TYPE
            SYNTAX FloatingPoint
            UNITS "Ampere"
            MAX-ACCESS read-only
            STATUS current
            DESCRIPTION
                "The power amplifier module current (I_4A)."
            ::= { ostEntry 404 }

        
        ostRackAmpI1B OBJECT-TYPE
            SYNTAX FloatingPoint
            UNITS "Ampere"
            MAX-ACCESS read-only
            STATUS current
            DESCRIPTION
                "The power amplifier module current (I_1B)."
            ::= { ostEntry 405 }

        
        ostRackAmpI2B OBJECT-TYPE
            SYNTAX FloatingPoint
            UNITS "Ampere"
            MAX-ACCESS read-only
            STATUS current
            DESCRIPTION
                "The power amplifier module current (I_2B)."
            ::= { ostEntry 406 }

        
        ostRackAmpI3B OBJECT-TYPE
            SYNTAX FloatingPoint
            UNITS "Ampere"
            MAX-ACCESS read-only
            STATUS current
            DESCRIPTION
                "The power amplifier module current (I_3B)."
            ::= { ostEntry 407 }

        
        ostRackAmpI4B OBJECT-TYPE
            SYNTAX FloatingPoint
            UNITS "Ampere"
            MAX-ACCESS read-only
            STATUS current
            DESCRIPTION
                "The power amplifier module current (I_4B)."
            ::= { ostEntry 408 }

        
        ostRackAmpIDrv OBJECT-TYPE
            SYNTAX FloatingPoint
            UNITS "Ampere"
            MAX-ACCESS read-only
            STATUS current
            DESCRIPTION
                "The driver module current (I_DRV)."
            ::= { ostEntry 409 }

        
        ostRackAmpUDc OBJECT-TYPE
            SYNTAX FloatingPoint
            UNITS "Volt"
            MAX-ACCESS read-only
            STATUS current
            DESCRIPTION
                "The power amplifier supply voltage."
            ::= { ostEntry 410 }

        
        ostRackAmpIDc OBJECT-TYPE
            SYNTAX FloatingPoint
            UNITS "Ampere"
            MAX-ACCESS read-only
            STATUS current
            DESCRIPTION
                "The power amplifier supply current."
            ::= { ostEntry 411 }

        
        ostRackAmpUDcControl OBJECT-TYPE
            SYNTAX FloatingPoint
            UNITS "Volt"
            MAX-ACCESS read-only
            STATUS current
            DESCRIPTION
                "The power supply control voltage."
            ::= { ostEntry 412 }

        
        ostRackAmpUReg OBJECT-TYPE
            SYNTAX FloatingPoint
            UNITS "Volt"
            MAX-ACCESS read-only
            STATUS current
            DESCRIPTION
                "The power amplifier AGC voltage."
            ::= { ostEntry 413 }

        
        ostRackAmpPowerA OBJECT-TYPE
            SYNTAX FloatingPoint
            UNITS "Volt"
            MAX-ACCESS read-only
            STATUS current
            DESCRIPTION
                "The voltage power detector A."
            ::= { ostEntry 414 }

        
        ostRackAmpPowerB OBJECT-TYPE
            SYNTAX FloatingPoint
            UNITS "Volt"
            MAX-ACCESS read-only
            STATUS current
            DESCRIPTION
                "The voltage power detector B."
            ::= { ostEntry 415 }

        
        ostRackAmpPowerOut OBJECT-TYPE
            SYNTAX FloatingPoint
            UNITS "Volt"
            MAX-ACCESS read-only
            STATUS current
            DESCRIPTION
                "The voltage forward power detector."
            ::= { ostEntry 416 }

        
        ostRackAmpPowerReflection OBJECT-TYPE
            SYNTAX FloatingPoint
            UNITS "Volt"
            MAX-ACCESS read-only
            STATUS current
            DESCRIPTION
                "The voltage reflected power detector."
            ::= { ostEntry 417 }

        
        ostRackAmpPowerReference OBJECT-TYPE
            SYNTAX FloatingPoint
            UNITS "Volt"
            MAX-ACCESS read-only
            STATUS current
            DESCRIPTION
                "The reference voltage for output power."
            ::= { ostEntry 418 }

        
        ostRackAmpDeltaPhase OBJECT-TYPE
            SYNTAX FloatingPoint
            UNITS "Percent"
            MAX-ACCESS read-only
            STATUS current
            DESCRIPTION
                "The measured phase delta for output power."
            ::= { ostEntry 419 }

        
        ostRackAmpCmdDeltaPhase OBJECT-TYPE
            SYNTAX FloatingPoint
            UNITS "Percent"
            MAX-ACCESS read-write
            STATUS current
            DESCRIPTION
                "The phase delta setting for output power.
                The range is -50.0% to 50.0%."
            ::= { ostEntry 420 }

        
-- exciter input  *************************
        exciterInputTable OBJECT-TYPE
            SYNTAX SEQUENCE OF ExciterInputEntry
            MAX-ACCESS not-accessible
            STATUS current
            DESCRIPTION
                "A table for more detailed information about the exciter.
                These values are all read-only. For settings, refer to commands."
            ::= { detailedInfo 19 }

        
        exciterInputEntry OBJECT-TYPE
            SYNTAX ExciterInputEntry
            MAX-ACCESS not-accessible
            STATUS current
            DESCRIPTION
                "An entry for a designated input channel."
            INDEX { excInputExcIdx, excInputIdx }
            ::= { exciterInputTable 1 }

        
        ExciterInputEntry ::=
            SEQUENCE { 
                excInputExcIdx
                    IndexAB,
                excInputIdx
                    Integer32,
                excInputName
                    INTEGER,
                excInputConnected
                    TruthValue,
                excInputAsiLocked
                    TruthValue,
                excInputActive
                    TruthValue,
                excInputPacketRate
                    Integer32
             }

        excInputExcIdx OBJECT-TYPE
            SYNTAX IndexAB
            MAX-ACCESS not-accessible
            STATUS current
            DESCRIPTION
                "The index for exciterA (and exciterB if there are DualDrive systems)."
            ::= { exciterInputEntry 3 }

        
        excInputIdx OBJECT-TYPE
            SYNTAX Integer32 (1..2)
            MAX-ACCESS not-accessible
            STATUS current
            DESCRIPTION
                "The index for the different input."
            ::= { exciterInputEntry 4 }

        
        excInputName OBJECT-TYPE
            SYNTAX INTEGER
                {
                input1(1),
                input2(2)
                }
            MAX-ACCESS read-only
            STATUS current
            DESCRIPTION
                "This is the logical name for the index for the different input channels."
            ::= { exciterInputEntry 5 }

        
        excInputConnected OBJECT-TYPE
            SYNTAX TruthValue
            MAX-ACCESS read-only
            STATUS current
            DESCRIPTION
                "The input is connected."
            ::= { exciterInputEntry 6 }

        
        excInputAsiLocked OBJECT-TYPE
            SYNTAX TruthValue
            MAX-ACCESS read-only
            STATUS current
            DESCRIPTION
                "The input is locked."
            ::= { exciterInputEntry 7 }

        
        excInputActive OBJECT-TYPE
            SYNTAX TruthValue
            MAX-ACCESS read-only
            STATUS current
            DESCRIPTION
                "The input is active."
            ::= { exciterInputEntry 8 }

        
        excInputPacketRate OBJECT-TYPE
            SYNTAX Integer32
            MAX-ACCESS read-only
            STATUS current
            DESCRIPTION
                "The packet rate of this input."
            ::= { exciterInputEntry 9 }

        
-- exciter status  *************************
        exciterStatusTable OBJECT-TYPE
            SYNTAX SEQUENCE OF ExciterStatusEntry
            MAX-ACCESS not-accessible
            STATUS current
            DESCRIPTION
                "A table for more detailed information about the exciter.
                These values are all read-only. For settings, refer to commands."
            ::= { detailedInfo 20 }

        
        exciterStatusEntry OBJECT-TYPE
            SYNTAX ExciterStatusEntry
            MAX-ACCESS not-accessible
            STATUS current
            DESCRIPTION
                "An entry for a designated exciter."
            INDEX { excStatusExcIdx }
            ::= { exciterStatusTable 1 }

        
        ExciterStatusEntry ::=
            SEQUENCE { 
                excStatusExcIdx
                    IndexAB,
                excStatusRfOutputAgcRegulation
                    FloatingPoint,
                excStatusRfIqAdjustAuto
                    INTEGER,
                excStatusRfIqAdjustLO1Frequency
                    FloatingPoint,
                excStatusNominalPower
                    Integer32,
                excStatusVSWR
                    FloatingPoint,
                excStatusAmplifierControl
                    SwitchOnOff,
                excStatusSsfArrivalTime
                    Integer32,
                excStatusTransmitterDelay
                    Integer32,
                excStatusTimeDeviation
                    Integer32,
                excStatusLocalLength
                    Integer32,
                excStatusFrameLength
                    Integer32,
                excStatusSuperFrameLength
                    Integer32,
                excStatusCurrentFifoLevel
                    Integer32,
                excStatusTS1OutOfFrameErrors
                    Integer32,
                excStatusTS2OutOfFrameErrors
                    Integer32,
                excStatusOverheadCounter
                    Integer32,
                excStatusDroppedGroups
                    Integer32,
                excStatusDroppedPackets
                    Integer32,
                excStatusCoreResetCounter
                    Integer32,
                excStatusMTISeqErrorCounter
                    Integer32,
                excStatusMTIScheduleErrors
                    Integer32,
                excStatusLastErrorOnPacketSeq
                    Integer32,
                excStatusLastErrorOnPacketID
                    Integer32,
                excStatusPacketRateWOIS
                    Integer32,
                excStatusPacketRateWCC
                    Integer32,
                excStatusPacketRateWCON
                    Integer32,
                excStatusPacketRateLOIS
                    Integer32,
                excStatusPacketRateLCC
                    Integer32,
                excStatusPacketRateLCON
                    Integer32,
                excStatusFailDelay
                    FailDelayStatus
             }

        excStatusExcIdx OBJECT-TYPE
            SYNTAX IndexAB
            MAX-ACCESS not-accessible
            STATUS current
            DESCRIPTION
                "The index for exciterA (and exciterB if there are DualDrive systems)."
            ::= { exciterStatusEntry 3 }

        
        excStatusRfOutputAgcRegulation OBJECT-TYPE
            SYNTAX FloatingPoint
            UNITS "Percent"
            MAX-ACCESS read-only
            STATUS current
            DESCRIPTION
                "Shows the operating point of the RF regulator. The shown value should be around 
                50 percent."
            ::= { exciterStatusEntry 4 }

        
        excStatusRfIqAdjustAuto OBJECT-TYPE
            SYNTAX INTEGER
                {
                notAdjusted(1),
                inProgress(2),
                adjusted(3)
                }
            UNITS "Percent"
            MAX-ACCESS read-only
            STATUS current
            DESCRIPTION
                "Automatic I/Q-Adjust."
            ::= { exciterStatusEntry 5 }

        
        excStatusRfIqAdjustLO1Frequency OBJECT-TYPE
            SYNTAX FloatingPoint
            UNITS "MHz"
            MAX-ACCESS read-only
            STATUS current
            DESCRIPTION
                "Modulator LO1."
            ::= { exciterStatusEntry 6 }

        
        excStatusNominalPower OBJECT-TYPE
            SYNTAX Integer32
            UNITS "W"
            MAX-ACCESS read-write
            STATUS current
            DESCRIPTION
                "Description."
            ::= { exciterStatusEntry 7 }

        
        excStatusVSWR OBJECT-TYPE
            SYNTAX FloatingPoint
            MAX-ACCESS read-only
            STATUS current
            DESCRIPTION
                "Voltage Standing Wave Ratio"
            ::= { exciterStatusEntry 9 }

        
        excStatusAmplifierControl OBJECT-TYPE
            SYNTAX SwitchOnOff
            MAX-ACCESS read-only
            STATUS current
            DESCRIPTION
                "Shows if the exciter is properly configured to control an amplifier directly 
                connected to the exciter."
            ::= { exciterStatusEntry 10 }

        
        excStatusSsfArrivalTime OBJECT-TYPE
            SYNTAX Integer32
            UNITS "Nanoseconds"
            MAX-ACCESS read-only
            STATUS current
            DESCRIPTION
                "The span of time the signal is on way from output SFN adapter to input
                transmitter."
            ::= { exciterStatusEntry 13 }

        
        excStatusTransmitterDelay OBJECT-TYPE
            SYNTAX Integer32
            UNITS "Nanoseconds"
            MAX-ACCESS read-only
            STATUS current
            DESCRIPTION
                "The latency associated with the transmit hardware."
            ::= { exciterStatusEntry 14 }

        
        excStatusTimeDeviation OBJECT-TYPE
            SYNTAX Integer32
            UNITS "Nanoseconds"
            MAX-ACCESS read-only
            STATUS current
            DESCRIPTION
                "The time deviation."
            ::= { exciterStatusEntry 15 }

        
        excStatusLocalLength OBJECT-TYPE
            SYNTAX Integer32
            MAX-ACCESS read-only
            STATUS current
            DESCRIPTION
                "The local length."
            ::= { exciterStatusEntry 17 }

        
        excStatusFrameLength OBJECT-TYPE
            SYNTAX Integer32
            MAX-ACCESS read-only
            STATUS current
            DESCRIPTION
                "The frame length."
            ::= { exciterStatusEntry 18 }

        
        excStatusSuperFrameLength OBJECT-TYPE
            SYNTAX Integer32
            MAX-ACCESS read-only
            STATUS current
            DESCRIPTION
                "The Super frame length."
            ::= { exciterStatusEntry 19 }

        
        excStatusCurrentFifoLevel OBJECT-TYPE
            SYNTAX Integer32
            MAX-ACCESS read-only
            STATUS current
            DESCRIPTION
                "Denotes the number of Bytes in the Wide area SFN Buffer. This is for network 
                monitoring purposes only. This number is constantly updated once per second, and 
                reflects a snapshot as to what the fifo depth is at any given time."
            ::= { exciterStatusEntry 25 }

        
        excStatusTS1OutOfFrameErrors OBJECT-TYPE
            SYNTAX Integer32
            MAX-ACCESS read-only
            STATUS current
            DESCRIPTION
                "Number of occurrences of an out of frame detection on transport stream 1 since 
                the last reset."
            ::= { exciterStatusEntry 26 }

        
        excStatusTS2OutOfFrameErrors OBJECT-TYPE
            SYNTAX Integer32
            MAX-ACCESS read-only
            STATUS current
            DESCRIPTION
                "Number of occurrences of an out of frame detection on transport stream 2 since 
                the last reset."
            ::= { exciterStatusEntry 27 }

        
        excStatusOverheadCounter OBJECT-TYPE
            SYNTAX Integer32
            MAX-ACCESS read-only
            STATUS current
            DESCRIPTION
                "Indicates the number of MAC data or OIS descriptor packets
                that were found to have illegal overhead data."
            ::= { exciterStatusEntry 28 }

        
        excStatusDroppedGroups OBJECT-TYPE
            SYNTAX Integer32
            MAX-ACCESS read-only
            STATUS current
            DESCRIPTION
                "Indicates the number of groups that were dropped since the last reset, due to the 
                mpeg transport error bit being set in an OIS or MAC group descriptor packet."
            ::= { exciterStatusEntry 29 }

        
        excStatusDroppedPackets OBJECT-TYPE
            SYNTAX Integer32
            MAX-ACCESS read-only
            STATUS current
            DESCRIPTION
                "Indicates the number of MAC data packets that were dropped since the last reset, 
                due to the mpeg transport error bit being set or due to an MTI version mismatch."
            ::= { exciterStatusEntry 30 }

        
        excStatusCoreResetCounter OBJECT-TYPE
            SYNTAX Integer32
            MAX-ACCESS read-only
            STATUS current
            DESCRIPTION
                "Denotes the number of resets of the Medio FLO core since the last reboot of the 
                exciter. If this value is greater than zero it indicates an error in signal 
                processing."
            ::= { exciterStatusEntry 31 }

        
        excStatusMTISeqErrorCounter OBJECT-TYPE
            SYNTAX Integer32
            MAX-ACCESS read-only
            STATUS current
            DESCRIPTION
                "This counter will increment if packets are dropped upstream for any reason or if 
                packet ordering is not maintained."
            ::= { exciterStatusEntry 32 }

        
        excStatusMTIScheduleErrors OBJECT-TYPE
            SYNTAX Integer32
            MAX-ACCESS read-only
            STATUS current
            DESCRIPTION
                "This counter is increased in case of following events: 
                - MLC overlaps 
                - MTI packets out of sequence errors 
                - late MTI packet errors."
            ::= { exciterStatusEntry 33 }

        
        excStatusLastErrorOnPacketSeq OBJECT-TYPE
            SYNTAX Integer32
            MAX-ACCESS read-only
            STATUS current
            DESCRIPTION
                "Holds the sequence number of the last errornous MTI descriptor packet."
            ::= { exciterStatusEntry 34 }

        
        excStatusLastErrorOnPacketID OBJECT-TYPE
            SYNTAX Integer32
            MAX-ACCESS read-only
            STATUS current
            DESCRIPTION
                "Holds the MTI packet ID of the last errornous MTI Descriptor packet."
            ::= { exciterStatusEntry 35 }

        
        excStatusPacketRateWOIS OBJECT-TYPE
            SYNTAX Integer32
            MAX-ACCESS read-only
            STATUS current
            DESCRIPTION
                "Denotes the number of active TS stream Packets received between the 2 most recent 
                GPS 1 PPS signals having a PID equal to the Wide OIS PID value."
            ::= { exciterStatusEntry 40 }

        
        excStatusPacketRateWCC OBJECT-TYPE
            SYNTAX Integer32
            MAX-ACCESS read-only
            STATUS current
            DESCRIPTION
                "Denotes the number of active TS stream Packets received between the 2 most recent 
                GPS 1 PPS signals having a PID equal to the Wide Control Channel PID value."
            ::= { exciterStatusEntry 41 }

        
        excStatusPacketRateWCON OBJECT-TYPE
            SYNTAX Integer32
            MAX-ACCESS read-only
            STATUS current
            DESCRIPTION
                "Denotes the number of active TS stream Packets received between the 2 most recent 
                GPS 1 PPS signals having a PID equal to the Wide Content Data PID value."
            ::= { exciterStatusEntry 42 }

        
        excStatusPacketRateLOIS OBJECT-TYPE
            SYNTAX Integer32
            MAX-ACCESS read-only
            STATUS current
            DESCRIPTION
                "Denotes the number of active TS stream Packets received between the 2 most recent 
                GPS 1 PPS signals having a PID equal to the Local OIS PID value."
            ::= { exciterStatusEntry 43 }

        
        excStatusPacketRateLCC OBJECT-TYPE
            SYNTAX Integer32
            MAX-ACCESS read-only
            STATUS current
            DESCRIPTION
                "Denotes the number of active TS stream Packets received between the 2 most recent 
                GPS 1 PPS signals having a PID equal to the Local Control Channel PID value."
            ::= { exciterStatusEntry 44 }

        
        excStatusPacketRateLCON OBJECT-TYPE
            SYNTAX Integer32
            MAX-ACCESS read-only
            STATUS current
            DESCRIPTION
                "Denotes the number of active TS stream Packets received between the 2 most recent 
                GPS 1 PPS signals having a PID equal to the Local Content Data PID value."
            ::= { exciterStatusEntry 45 }

        
        excStatusFailDelay OBJECT-TYPE
            SYNTAX FailDelayStatus
            MAX-ACCESS read-only
            STATUS current
            DESCRIPTION
                "Shows whether the fail delay time is qualified."
            ::= { exciterStatusEntry 50 }

        
-- exciter precorrection ******************
        exciterPrecorrectionTable OBJECT-TYPE
            SYNTAX SEQUENCE OF ExciterPrecorrectionEntry
            MAX-ACCESS not-accessible
            STATUS current
            DESCRIPTION
                "Exciter precorrection."
            ::= { detailedInfo 21 }

        
        exciterPrecorrectionEntry OBJECT-TYPE
            SYNTAX ExciterPrecorrectionEntry
            MAX-ACCESS not-accessible
            STATUS current
            DESCRIPTION
                "A row (an entry) for one exciter."
            INDEX { excPrecExcIdx }
            ::= { exciterPrecorrectionTable 1 }

        
        ExciterPrecorrectionEntry ::=
            SEQUENCE { 
                excPrecExcIdx
                    IndexAB,
                excPrecLinCorrection
                    SwitchOnOff,
                excPrecLinAutomaticADE
                    INTEGER,
                excPrecLinMaxAmplitudeRipple
                    FloatingPoint,
                excPrecLinMaxGroupDelayRipple
                    Integer32,
                excPrecLinAmplitudeRipple
                    FloatingPoint,
                excPrecLinGroupDelayRipple
                    Integer32,
                excPrecLinInputLevel
                    INTEGER,
                excPrecLinAutomatic
                    INTEGER,
                excPrecNonlinCorrection
                    SwitchOnOff,
                excPrecNonlinAutomaticADE
                    INTEGER,
                excPrecNonlinThresholdShoulders
                    FloatingPoint,
                excPrecNonlinShoulderLeft
                    FloatingPoint,
                excPrecNonlinShoulderRight
                    FloatingPoint,
                excPrecNonlinInputLevel
                    INTEGER,
                excPrecNonlinAutomatic
                    INTEGER,
                excPrecExtendedGroupDelay
                    SwitchOnOff
             }

        excPrecExcIdx OBJECT-TYPE
            SYNTAX IndexAB
            MAX-ACCESS not-accessible
            STATUS current
            DESCRIPTION
                "The dedicated exciter (A/B)."
            ::= { exciterPrecorrectionEntry 3 }

        
        excPrecLinCorrection OBJECT-TYPE
            SYNTAX SwitchOnOff
            MAX-ACCESS read-write
            STATUS current
            DESCRIPTION
                "Switches on/turns off the linear precorrector."
            ::= { exciterPrecorrectionEntry 4 }

        
        excPrecLinAutomaticADE OBJECT-TYPE
            SYNTAX INTEGER
                {
                manual(1),
                automatic(2),
                adaptive(3)
                }
            MAX-ACCESS read-write
            STATUS current
            DESCRIPTION
                "Enables /disables the automatic precorrector. To get the ADE in work linear 
                precorrection has to be switched on."
            ::= { exciterPrecorrectionEntry 5 }

        
        excPrecLinMaxAmplitudeRipple OBJECT-TYPE
            SYNTAX FloatingPoint
            UNITS "dB"
            MAX-ACCESS read-write
            STATUS current
            DESCRIPTION
                "Sets te maximum ripple for automatic amplitude correction (0.0 ... 2.0)."
            ::= { exciterPrecorrectionEntry 6 }

        
        excPrecLinMaxGroupDelayRipple OBJECT-TYPE
            SYNTAX Integer32 (0..500)
            UNITS "Nanoseconds"
            MAX-ACCESS read-write
            STATUS current
            DESCRIPTION
                "Sets the maximum ripple for automatic group delay correction."
            ::= { exciterPrecorrectionEntry 7 }

        
        excPrecLinAmplitudeRipple OBJECT-TYPE
            SYNTAX FloatingPoint
            UNITS "dB"
            MAX-ACCESS read-only
            STATUS current
            DESCRIPTION
                "Shows the current amplitude ripple."
            ::= { exciterPrecorrectionEntry 8 }

        
        excPrecLinGroupDelayRipple OBJECT-TYPE
            SYNTAX Integer32
            UNITS "Nanoseconds"
            MAX-ACCESS read-only
            STATUS current
            DESCRIPTION
                "Shows the current group delay ripple."
            ::= { exciterPrecorrectionEntry 9 }

        
        excPrecLinInputLevel OBJECT-TYPE
            SYNTAX INTEGER
                {
                tooHigh(1),
                ok(2),
                tooLow(3),
                failure(4)
                }
            MAX-ACCESS read-only
            STATUS current
            DESCRIPTION
                "Shows the state of the feedback signal from the measurement point between output 
                stage and antenna."
            ::= { exciterPrecorrectionEntry 10 }

        
        excPrecLinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 11 }

        
        excPrecNonlinCorrection OBJECT-TYPE
            SYNTAX SwitchOnOff
            MAX-ACCESS read-write
            STATUS current
            DESCRIPTION
                "Switches on/turns off the nonlinear precorrector."
            ::= { exciterPrecorrectionEntry 12 }

        
        excPrecNonlinAutomaticADE OBJECT-TYPE
            SYNTAX INTEGER
                {
                manual(1),
                automatic(2),
                adaptive(3)
                }
            MAX-ACCESS read-write
            STATUS current
            DESCRIPTION
                "Enables /disables the automatic precorrector. To get the ADE in work nonlinear 
                precorrection has to be switched on."
            ::= { exciterPrecorrectionEntry 13 }

        
        excPrecNonlinThresholdShoulders OBJECT-TYPE
            SYNTAX FloatingPoint
            UNITS "dB"
            MAX-ACCESS read-write
            STATUS current
            DESCRIPTION
                "The target shoulder distance for ADE (0.0 ... 40.0)."
            ::= { exciterPrecorrectionEntry 14 }

        
        excPrecNonlinShoulderLeft OBJECT-TYPE
            SYNTAX FloatingPoint
            UNITS "dB"
            MAX-ACCESS read-only
            STATUS current
            DESCRIPTION
                "Displays the current measurement for the left handed shoulder distance."
            ::= { exciterPrecorrectionEntry 15 }

        
        excPrecNonlinShoulderRight OBJECT-TYPE
            SYNTAX FloatingPoint
            UNITS "dB"
            MAX-ACCESS read-only
            STATUS current
            DESCRIPTION
                "Displays the current measurement of the right handed shoulder."
            ::= { exciterPrecorrectionEntry 16 }

        
        excPrecNonlinInputLevel OBJECT-TYPE
            SYNTAX INTEGER
                {
                tooHigh(1),
                ok(2),
                tooLow(3),
                failure(4)
                }
            MAX-ACCESS read-only
            STATUS current
            DESCRIPTION
                "Shows the state of the feedback signal from the measurement point between output 
                stage and antenna."
            ::= { exciterPrecorrectionEntry 17 }

        
        excPrecNonlinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 18 }

        
        excPrecExtendedGroupDelay OBJECT-TYPE
            SYNTAX SwitchOnOff
            MAX-ACCESS read-write
            STATUS current
            DESCRIPTION
                "Switch extended group delay on or off.
                Switching on is possible only when the corresponding option key is active."
            ::= { exciterPrecorrectionEntry 30 }

        
-- product info *************************
        productInfoTable OBJECT-TYPE
            SYNTAX SEQUENCE OF ProductInfoEntry
            MAX-ACCESS not-accessible
            STATUS current
            DESCRIPTION
                "The table for all product typeplates."
            ::= { detailedInfo 100 }

        
        productInfoEntry OBJECT-TYPE
            SYNTAX ProductInfoEntry
            MAX-ACCESS not-accessible
            STATUS current
            DESCRIPTION
                "A row (an entry) for one typeplate."
            INDEX { prodInfoModuleIdx, prodInfoDeviceIdx, prodInfoRackIdx, prodInfoAmpIdx }
            ::= { productInfoTable 1 }

        
        ProductInfoEntry ::=
            SEQUENCE { 
                prodInfoModuleIdx
                    ProdInfoModuleNameTv,
                prodInfoDeviceIdx
                    IndexAB,
                prodInfoRackIdx
                    IndexRack,
                prodInfoAmpIdx
                    IndexAmplifier,
                prodInfoModuleName
                    ProdInfoModuleNameTv,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime,
                productInfoFloModVersion
                    ReadableString
             }

        prodInfoModuleIdx OBJECT-TYPE
            SYNTAX ProdInfoModuleNameTv
            MAX-ACCESS not-accessible
            STATUS current
            DESCRIPTION
                "The module index."
            ::= { productInfoEntry 1 }

        
        prodInfoDeviceIdx OBJECT-TYPE
            SYNTAX IndexAB
            MAX-ACCESS not-accessible
            STATUS current
            DESCRIPTION
                "The dedicated device (A/B)."
            ::= { productInfoEntry 2 }

        
        prodInfoRackIdx OBJECT-TYPE
            SYNTAX IndexRack
            MAX-ACCESS not-accessible
            STATUS current
            DESCRIPTION
                "The rack number (1..10)."
            ::= { productInfoEntry 3 }

        
        prodInfoAmpIdx OBJECT-TYPE
            SYNTAX IndexAmplifier
            MAX-ACCESS not-accessible
            STATUS current
            DESCRIPTION
                "Amplifier Index"
            ::= { productInfoEntry 4 }

        
        prodInfoModuleName OBJECT-TYPE
            SYNTAX ProdInfoModuleNameTv
            MAX-ACCESS read-only
            STATUS current
            DESCRIPTION
                "The readable module type."
            ::= { productInfoEntry 5 }

        
        prodInfoSerialNumber OBJECT-TYPE
            SYNTAX ReadableString
            MAX-ACCESS read-only
            STATUS current
            DESCRIPTION
                "The serial number of the subdevice."
            ::= { productInfoEntry 6 }

        
        prodInfoIdentNumberSW OBJECT-TYPE
            SYNTAX ReadableString
            MAX-ACCESS read-only
            STATUS current
            DESCRIPTION
                "The Rohde&Schwarz identification number of the software, for example 
                2094.2090.02."
            ::= { productInfoEntry 7 }

        
        prodInfoVersionNumberSW OBJECT-TYPE
            SYNTAX ReadableString
            MAX-ACCESS read-only
            STATUS current
            DESCRIPTION
                "The Rohde&Schwarz revision number of the software, for example 1.2.1."
            ::= { productInfoEntry 8 }

        
        prodInfoIdentNumberHW OBJECT-TYPE
            SYNTAX ReadableString
            MAX-ACCESS read-only
            STATUS current
            DESCRIPTION
                "The Rohde&Schwarz identification number of the hardware, for example 
                2095.8007.02 (NetCCU)."
            ::= { productInfoEntry 9 }

        
        prodInfoVersionNumberHW OBJECT-TYPE
            SYNTAX ReadableString
            MAX-ACCESS read-only
            STATUS current
            DESCRIPTION
                "The Rohde&Schwarz revision number (product index) of the hardware, for example 
                03.03."
            ::= { productInfoEntry 10 }

        
        productInfoProductDateHW OBJECT-TYPE
            SYNTAX DateAndTime
            MAX-ACCESS read-only
            STATUS current
            DESCRIPTION
                "The Rohde&Schwarz production date of the hardware."
            ::= { productInfoEntry 11 }

        
        productInfoFloModVersion OBJECT-TYPE
            SYNTAX ReadableString
            MAX-ACCESS read-only
            STATUS current
            DESCRIPTION
                "The FPGA version."
            ::= { productInfoEntry 20 }

        
-- logbook  *************************
        logbook OBJECT IDENTIFIER ::= { rsXx8000MediaFloTxObjs 4 }

        
        netCCUNumberOfEntries OBJECT-TYPE
            SYNTAX LogbookMaxEntryNumber
            MAX-ACCESS read-only
            STATUS current
            DESCRIPTION
                "The number of entries in logbook."
            ::= { logbook 1 }

        
        netCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing 
                anything."
            ::= { logbook 2 }

        
        netCCULogbookTable OBJECT-TYPE
            SYNTAX SEQUENCE OF NetCCULogbookEntry
            MAX-ACCESS not-accessible
            STATUS current
            DESCRIPTION
                "NetCCU logbook table."
            ::= { logbook 3 }

        
        netCCULogbookEntry OBJECT-TYPE
            SYNTAX NetCCULogbookEntry
            MAX-ACCESS not-accessible
            STATUS current
            DESCRIPTION
                "This is a entry in the logbook."
            INDEX { netCCULogbookEntryIdx }
            ::= { netCCULogbookTable 1 }

        
        NetCCULogbookEntry ::=
            SEQUENCE { 
                netCCULogbookEntryIdx
                    LogbookMaxEntryNumber,
                netCCULogbookEntryNbr
                    LogbookMaxEntryNumber,
                netCCULogbookType
                    EventClass,
                netCCULogbookSlope
                    LogbookEntrySlope,
                netCCULogbookMessage
                    LogbookEntryMessagesNetCCU,
                netCCULogbookDateTime
                    DateAndTime
             }

        netCCULogbookEntryIdx OBJECT-TYPE
            SYNTAX LogbookMaxEntryNumber
            MAX-ACCESS not-accessible
            STATUS current
            DESCRIPTION
                "This is an increasing number from 1 to 128. It is used as an index column for 
                SNMP."
            ::= { netCCULogbookEntry 1 }

        
        netCCULogbookEntryNbr OBJECT-TYPE
            SYNTAX LogbookMaxEntryNumber
            MAX-ACCESS read-only
            STATUS current
            DESCRIPTION
                "This is the number of the logbook entry. It is an decreasing number from max 128 
                down to 1."
            ::= { netCCULogbookEntry 2 }

        
        netCCULogbookType OBJECT-TYPE
            SYNTAX EventClass
            MAX-ACCESS read-only
            STATUS current
            DESCRIPTION
                "Can either be Fault, Warning or State."
            ::= { netCCULogbookEntry 3 }

        
        netCCULogbookSlope OBJECT-TYPE
            SYNTAX LogbookEntrySlope
            MAX-ACCESS read-only
            STATUS current
            DESCRIPTION
                "Either set (event raises) or reset (event disappears)."
            ::= { netCCULogbookEntry 4 }

        
        netCCULogbookMessage OBJECT-TYPE
            SYNTAX LogbookEntryMessagesNetCCU
            MAX-ACCESS read-only
            STATUS current
            DESCRIPTION
                "See RS-XX8000-COMMON-MIB - TextualConvention for details."
            ::= { netCCULogbookEntry 5 }

        
        netCCULogbookDateTime OBJECT-TYPE
            SYNTAX DateAndTime
            MAX-ACCESS read-only
            STATUS current
            DESCRIPTION
                "The time of the logbook entry."
            ::= { netCCULogbookEntry 6 }

        
        exciterANumberOfEntries OBJECT-TYPE
            SYNTAX LogbookMaxEntryNumber
            MAX-ACCESS read-only
            STATUS current
            DESCRIPTION
                "The number of entries in logbook."
            ::= { logbook 4 }

        
        exciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing 
                anything."
            ::= { logbook 5 }

        
        exciterALogbookTable OBJECT-TYPE
            SYNTAX SEQUENCE OF ExciterALogbookEntry
            MAX-ACCESS not-accessible
            STATUS current
            DESCRIPTION
                "ExciterA logbook table."
            ::= { logbook 6 }

        
        exciterALogbookEntry OBJECT-TYPE
            SYNTAX ExciterALogbookEntry
            MAX-ACCESS not-accessible
            STATUS current
            DESCRIPTION
                "This is a entry in the logbook."
            INDEX { excALogbookEntryIdx }
            ::= { exciterALogbookTable 1 }

        
        ExciterALogbookEntry ::=
            SEQUENCE { 
                excALogbookEntryIdx
                    LogbookMaxEntryNumber,
                excALogbookEntryNbr
                    LogbookMaxEntryNumber,
                excALogbookType
                    EventClass,
                excALogbookSlope
                    LogbookEntrySlope,
                excALogbookMessage
                    LogbookEntryMessagesExcTv,
                excALogbookDateTime
                    DateAndTime
             }

        excALogbookEntryIdx OBJECT-TYPE
            SYNTAX LogbookMaxEntryNumber
            MAX-ACCESS not-accessible
            STATUS current
            DESCRIPTION
                "This is an increasing number from 1 to 128. It is used as an index column for 
                SNMP."
            ::= { exciterALogbookEntry 1 }

        
        excALogbookEntryNbr OBJECT-TYPE
            SYNTAX LogbookMaxEntryNumber
            MAX-ACCESS read-only
            STATUS current
            DESCRIPTION
                "This is the number of the logbook entry. It is an decreasing number from max 128 
                down to 1."
            ::= { exciterALogbookEntry 2 }

        
        excALogbookType OBJECT-TYPE
            SYNTAX EventClass
            MAX-ACCESS read-only
            STATUS current
            DESCRIPTION
                "Can either be Fault, Warning or State."
            ::= { exciterALogbookEntry 3 }

        
        excALogbookSlope OBJECT-TYPE
            SYNTAX LogbookEntrySlope
            MAX-ACCESS read-only
            STATUS current
            DESCRIPTION
                "Either set (event raises) or reset (event disappears)."
            ::= { exciterALogbookEntry 4 }

        
        excALogbookMessage OBJECT-TYPE
            SYNTAX LogbookEntryMessagesExcTv
            MAX-ACCESS read-only
            STATUS current
            DESCRIPTION
                "See RS-XX8000-COMMON-MIB - TextualConvention for details."
            ::= { exciterALogbookEntry 5 }

        
        excALogbookDateTime OBJECT-TYPE
            SYNTAX DateAndTime
            MAX-ACCESS read-only
            STATUS current
            DESCRIPTION
                "The time of the logbook entry."
            ::= { exciterALogbookEntry 6 }

        
        outputstageANumberOfEntries OBJECT-TYPE
            SYNTAX LogbookMaxEntryNumber
            MAX-ACCESS read-only
            STATUS current
            DESCRIPTION
                "The number of entries in logbook."
            ::= { logbook 7 }

        
        outputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing 
                anything."
            ::= { logbook 8 }

        
        outputstageALogbookTable OBJECT-TYPE
            SYNTAX SEQUENCE OF OutputstageALogbookEntry
            MAX-ACCESS not-accessible
            STATUS current
            DESCRIPTION
                "OutputstageA logbook table."
            ::= { logbook 9 }

        
        outputstageALogbookEntry OBJECT-TYPE
            SYNTAX OutputstageALogbookEntry
            MAX-ACCESS not-accessible
            STATUS current
            DESCRIPTION
                "This is a entry in the logbook."
            INDEX { ostALogbookEntryIdx }
            ::= { outputstageALogbookTable 1 }

        
        OutputstageALogbookEntry ::=
            SEQUENCE { 
                ostALogbookEntryIdx
                    LogbookMaxEntryNumber,
                ostALogbookEntryNbr
                    LogbookMaxEntryNumber,
                ostALogbookType
                    EventClass,
                ostALogbookSlope
                    LogbookEntrySlope,
                ostALogbookMessage
                    LogbookEntryMessagesOST,
                ostALogbookDateTime
                    DateAndTime
             }

        ostALogbookEntryIdx OBJECT-TYPE
            SYNTAX LogbookMaxEntryNumber
            MAX-ACCESS not-accessible
            STATUS current
            DESCRIPTION
                "This is an increasing number from 1 to 128. It is used as an index column for 
                SNMP."
            ::= { outputstageALogbookEntry 1 }

        
        ostALogbookEntryNbr OBJECT-TYPE
            SYNTAX LogbookMaxEntryNumber
            MAX-ACCESS read-only
            STATUS current
            DESCRIPTION
                "This is the number of the logbook entry. It is an decreasing number from max 128 
                down to 1."
            ::= { outputstageALogbookEntry 2 }

        
        ostALogbookType OBJECT-TYPE
            SYNTAX EventClass
            MAX-ACCESS read-only
            STATUS current
            DESCRIPTION
                "Can either be Fault, Warning or State."
            ::= { outputstageALogbookEntry 3 }

        
        ostALogbookSlope OBJECT-TYPE
            SYNTAX LogbookEntrySlope
            MAX-ACCESS read-only
            STATUS current
            DESCRIPTION
                "Either set (event raises) or reset (event disappears)."
            ::= { outputstageALogbookEntry 4 }

        
        ostALogbookMessage OBJECT-TYPE
            SYNTAX LogbookEntryMessagesOST
            MAX-ACCESS read-only
            STATUS current
            DESCRIPTION
                "See RS-XX8000-COMMON-MIB - TextualConvention for details."
            ::= { outputstageALogbookEntry 5 }

        
        ostALogbookDateTime OBJECT-TYPE
            SYNTAX DateAndTime
            MAX-ACCESS read-only
            STATUS current
            DESCRIPTION
                "The time of the logbook entry."
            ::= { outputstageALogbookEntry 6 }

        
        exciterBNumberOfEntries OBJECT-TYPE
            SYNTAX LogbookMaxEntryNumber
            MAX-ACCESS read-only
            STATUS current
            DESCRIPTION
                "The number of entries in logbook."
            ::= { logbook 10 }

        
        exciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing 
                anything."
            ::= { logbook 11 }

        
        exciterBLogbookTable OBJECT-TYPE
            SYNTAX SEQUENCE OF ExciterBLogbookEntry
            MAX-ACCESS not-accessible
            STATUS current
            DESCRIPTION
                "ExciterB logbook table."
            ::= { logbook 12 }

        
        exciterBLogbookEntry OBJECT-TYPE
            SYNTAX ExciterBLogbookEntry
            MAX-ACCESS not-accessible
            STATUS current
            DESCRIPTION
                "This is a entry in the logbook."
            INDEX { excBLogbookEntryIdx }
            ::= { exciterBLogbookTable 1 }

        
        ExciterBLogbookEntry ::=
            SEQUENCE { 
                excBLogbookEntryIdx
                    LogbookMaxEntryNumber,
                excBLogbookEntryNbr
                    LogbookMaxEntryNumber,
                excBLogbookType
                    EventClass,
                excBLogbookSlope
                    LogbookEntrySlope,
                excBLogbookMessage
                    LogbookEntryMessagesExcTv,
                excBLogbookDateTime
                    DateAndTime
             }

        excBLogbookEntryIdx OBJECT-TYPE
            SYNTAX LogbookMaxEntryNumber
            MAX-ACCESS not-accessible
            STATUS current
            DESCRIPTION
                "This is an increasing number from 1 to 128. It is used as an index column for 
                SNMP."
            ::= { exciterBLogbookEntry 1 }

        
        excBLogbookEntryNbr OBJECT-TYPE
            SYNTAX LogbookMaxEntryNumber
            MAX-ACCESS read-only
            STATUS current
            DESCRIPTION
                "This is the number of the logbook entry. It is an decreasing number from max 128 
                down to 1."
            ::= { exciterBLogbookEntry 2 }

        
        excBLogbookType OBJECT-TYPE
            SYNTAX EventClass
            MAX-ACCESS read-only
            STATUS current
            DESCRIPTION
                "Can either be Fault, Warning or State."
            ::= { exciterBLogbookEntry 3 }

        
        excBLogbookSlope OBJECT-TYPE
            SYNTAX LogbookEntrySlope
            MAX-ACCESS read-only
            STATUS current
            DESCRIPTION
                "Either set (event raises) or reset (event disappears)."
            ::= { exciterBLogbookEntry 4 }

        
        excBLogbookMessage OBJECT-TYPE
            SYNTAX LogbookEntryMessagesExcTv
            MAX-ACCESS read-only
            STATUS current
            DESCRIPTION
                "See RS-XX8000-COMMON-MIB - TextualConvention for details."
            ::= { exciterBLogbookEntry 5 }

        
        excBLogbookDateTime OBJECT-TYPE
            SYNTAX DateAndTime
            MAX-ACCESS read-only
            STATUS current
            DESCRIPTION
                "The time of the logbook entry."
            ::= { exciterBLogbookEntry 6 }

        
        outputstageBNumberOfEntries OBJECT-TYPE
            SYNTAX LogbookMaxEntryNumber
            MAX-ACCESS read-only
            STATUS current
            DESCRIPTION
                "The number of entries in logbook."
            ::= { logbook 13 }

        
        outputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing 
                anything."
            ::= { logbook 14 }

        
        outputstageBLogbookTable OBJECT-TYPE
            SYNTAX SEQUENCE OF OutputstageBLogbookEntry
            MAX-ACCESS not-accessible
            STATUS current
            DESCRIPTION
                "OutputstageB logbook table."
            ::= { logbook 15 }

        
        outputstageBLogbookEntry OBJECT-TYPE
            SYNTAX OutputstageBLogbookEntry
            MAX-ACCESS not-accessible
            STATUS current
            DESCRIPTION
                "This is a entry in the logbook."
            INDEX { ostBLogbookEntryIdx }
            ::= { outputstageBLogbookTable 1 }

        
        OutputstageBLogbookEntry ::=
            SEQUENCE { 
                ostBLogbookEntryIdx
                    LogbookMaxEntryNumber,
                ostBLogbookEntryNbr
                    LogbookMaxEntryNumber,
                ostBLogbookType
                    EventClass,
                ostBLogbookSlope
                    LogbookEntrySlope,
                ostBLogbookMessage
                    LogbookEntryMessagesOST,
                ostBLogbookDateTime
                    DateAndTime
             }

        ostBLogbookEntryIdx OBJECT-TYPE
            SYNTAX LogbookMaxEntryNumber
            MAX-ACCESS not-accessible
            STATUS current
            DESCRIPTION
                "This is an increasing number from 1 to 128. It is used as an index column for 
                SNMP."
            ::= { outputstageBLogbookEntry 1 }

        
        ostBLogbookEntryNbr OBJECT-TYPE
            SYNTAX LogbookMaxEntryNumber
            MAX-ACCESS read-only
            STATUS current
            DESCRIPTION
                "This is the number of the logbook entry. It is an decreasing number from max 128 
                down to 1."
            ::= { outputstageBLogbookEntry 2 }

        
        ostBLogbookType OBJECT-TYPE
            SYNTAX EventClass
            MAX-ACCESS read-only
            STATUS current
            DESCRIPTION
                "Can either be Fault, Warning or State."
            ::= { outputstageBLogbookEntry 3 }

        
        ostBLogbookSlope OBJECT-TYPE
            SYNTAX LogbookEntrySlope
            MAX-ACCESS read-only
            STATUS current
            DESCRIPTION
                "Either set (event raises) or reset (event disappears)."
            ::= { outputstageBLogbookEntry 4 }

        
        ostBLogbookMessage OBJECT-TYPE
            SYNTAX LogbookEntryMessagesOST
            MAX-ACCESS read-only
            STATUS current
            DESCRIPTION
                "See RS-XX8000-COMMON-MIB - TextualConvention for details."
            ::= { outputstageBLogbookEntry 5 }

        
        ostBLogbookDateTime OBJECT-TYPE
            SYNTAX DateAndTime
            MAX-ACCESS read-only
            STATUS current
            DESCRIPTION
                "The time of the logbook entry."
            ::= { outputstageBLogbookEntry 6 }

        
        logbookFrameNetCCU OBJECT-TYPE
            SYNTAX LogbookFrame
            MAX-ACCESS read-only
            STATUS current
            DESCRIPTION
                "The complete logbook of the NetCCU."
            ::= { logbook 100 }

        
        logbookFrameExciterA OBJECT-TYPE
            SYNTAX LogbookFrame
            MAX-ACCESS read-only
            STATUS current
            DESCRIPTION
                "The complete logbook of the exciter A."
            ::= { logbook 101 }

        
        logbookFrameOutputstageA OBJECT-TYPE
            SYNTAX LogbookFrame
            MAX-ACCESS read-only
            STATUS current
            DESCRIPTION
                "The complete logbook of the outputstage A."
            ::= { logbook 102 }

        
        logbookFrameExciterB OBJECT-TYPE
            SYNTAX LogbookFrame
            MAX-ACCESS read-only
            STATUS current
            DESCRIPTION
                "The complete logbook of the exciter B."
            ::= { logbook 103 }

        
        logbookFrameOutputstageB OBJECT-TYPE
            SYNTAX LogbookFrame
            MAX-ACCESS read-only
            STATUS current
            DESCRIPTION
                "The complete logbook of the outputstage B."
            ::= { logbook 104 }

        
-- RF probes *************************
        rfProbesTable OBJECT-TYPE
            SYNTAX SEQUENCE OF RfProbesEntry
            MAX-ACCESS not-accessible
            STATUS current
            DESCRIPTION
                "This table contains all commands for the RF probes."
            ::= { rsXx8000MediaFloTxObjs 5 }

        
        rfProbesEntry OBJECT-TYPE
            SYNTAX RfProbesEntry
            MAX-ACCESS not-accessible
            STATUS current
            DESCRIPTION
                "An entry for a designated device."
            INDEX { rfProbesOstIdx }
            ::= { rfProbesTable 1 }

        
        RfProbesEntry ::=
            SEQUENCE { 
                rfProbesNetCCURfProbe1
                    FloatingPoint,
                rfProbesNetCCURfProbe2
                    FloatingPoint,
                rfProbesAntFwdNominal
                    FloatingPoint,
                rfProbesAntFwdWarningLimit
                    FloatingPoint,
                rfProbesAntFwdFailLimit
                    FloatingPoint,
                rfProbesAntFwdDelayTimeRfFail
                    Integer32,
                rfProbesAntFwdSetOffset
                    Trigger,
                rfProbesAntFwdSetGain
                    Trigger,
                rfProbesAntReflWarningLimit
                    FloatingPoint,
                rfProbesAntReflSetOffset
                    Trigger,
                rfProbesAntReflSetGain
                    Trigger,
                rfProbesDLFwdNominal
                    FloatingPoint,
                rfProbesDLFwdWarningLimit
                    FloatingPoint,
                rfProbesDLFwdFailLimit
                    FloatingPoint,
                rfProbesDLFwdDelayTimeRfFail
                    Integer32,
                rfProbesDLFwdSetOffset
                    Trigger,
                rfProbesDLFwdSetGain
                    Trigger,
                rfProbesDLReflWarningLimit
                    FloatingPoint,
                rfProbesDLReflSetOffset
                    Trigger,
                rfProbesDLReflSetGain
                    Trigger,
                rfProbesOstIdx
                    IndexAB,
                rfProbesOstFwdNominal
                    FloatingPoint,
                rfProbesOstFwdWarningLimit
                    FloatingPoint,
                rfProbesOstFwdFailLimit
                    FloatingPoint,
                rfProbesOstFwdDelayTimeRfFail
                    Integer32,
                rfProbesOstFwdSetOffset
                    Trigger,
                rfProbesOstFwdSetGain
                    Trigger,
                rfProbesOstReflWarningLimit
                    FloatingPoint,
                rfProbesOstReflSetOffset
                    Trigger,
                rfProbesOstReflSetGain
                    Trigger
             }

        rfProbesNetCCURfProbe1 OBJECT-TYPE
            SYNTAX FloatingPoint
            UNITS "Volt"
            MAX-ACCESS read-only
            STATUS current
            DESCRIPTION
                "Current voltage on RF Probe 1."
            ::= { rfProbesEntry 1 }

        
        rfProbesNetCCURfProbe2 OBJECT-TYPE
            SYNTAX FloatingPoint
            UNITS "Volt"
            MAX-ACCESS read-only
            STATUS current
            DESCRIPTION
                "Current voltage on RF Probe 2."
            ::= { rfProbesEntry 2 }

        
        rfProbesAntFwdNominal OBJECT-TYPE
            SYNTAX FloatingPoint
            UNITS "Watt"
            MAX-ACCESS read-write
            STATUS current
            DESCRIPTION
                "This sets the nominal value [W] of the transmitter (to antenna)."
            ::= { rfProbesEntry 3 }

        
        rfProbesAntFwdWarningLimit OBJECT-TYPE
            SYNTAX FloatingPoint
            UNITS "dB"
            MAX-ACCESS read-write
            STATUS current
            DESCRIPTION
                "This sets the warning limit for the transmitters RF control (to antenna)."
            ::= { rfProbesEntry 4 }

        
        rfProbesAntFwdFailLimit OBJECT-TYPE
            SYNTAX FloatingPoint
            UNITS "dB"
            MAX-ACCESS read-write
            STATUS current
            DESCRIPTION
                "This sets the fault limit for the transmitters RF control (to antenna)."
            ::= { rfProbesEntry 5 }

        
        rfProbesAntFwdDelayTimeRfFail OBJECT-TYPE
            SYNTAX Integer32 (1..20)
            UNITS "seconds"
            MAX-ACCESS read-write
            STATUS current
            DESCRIPTION
                "This sets the delay time for the RF Fail control (to antenna)."
            ::= { rfProbesEntry 6 }

        
        rfProbesAntFwdSetOffset OBJECT-TYPE
            SYNTAX Trigger
            MAX-ACCESS read-write
            STATUS current
            DESCRIPTION
                "This triggers Set Offset."
            ::= { rfProbesEntry 7 }

        
        rfProbesAntFwdSetGain OBJECT-TYPE
            SYNTAX Trigger
            MAX-ACCESS read-write
            STATUS current
            DESCRIPTION
                "This triggers Set Gain."
            ::= { rfProbesEntry 8 }

        
        rfProbesAntReflWarningLimit OBJECT-TYPE
            SYNTAX FloatingPoint
            UNITS "dB"
            MAX-ACCESS read-write
            STATUS current
            DESCRIPTION
                "This sets the warning limit for the transmitters reflection control (to 
                antenna)."
            ::= { rfProbesEntry 9 }

        
        rfProbesAntReflSetOffset OBJECT-TYPE
            SYNTAX Trigger
            MAX-ACCESS read-write
            STATUS current
            DESCRIPTION
                "This triggers Set Offset."
            ::= { rfProbesEntry 10 }

        
        rfProbesAntReflSetGain OBJECT-TYPE
            SYNTAX Trigger
            MAX-ACCESS read-write
            STATUS current
            DESCRIPTION
                "This triggers Set Gain."
            ::= { rfProbesEntry 11 }

        
        rfProbesDLFwdNominal OBJECT-TYPE
            SYNTAX FloatingPoint
            UNITS "Watt"
            MAX-ACCESS read-write
            STATUS current
            DESCRIPTION
                "This sets the nominal value [W] of the transmitter (to dummyload)."
            ::= { rfProbesEntry 12 }

        
        rfProbesDLFwdWarningLimit OBJECT-TYPE
            SYNTAX FloatingPoint
            UNITS "dB"
            MAX-ACCESS read-write
            STATUS current
            DESCRIPTION
                "This sets the warning limit for the transmitters RF control (to dummyload)."
            ::= { rfProbesEntry 13 }

        
        rfProbesDLFwdFailLimit OBJECT-TYPE
            SYNTAX FloatingPoint
            UNITS "dB"
            MAX-ACCESS read-write
            STATUS current
            DESCRIPTION
                "This sets the fault limit for the transmitters RF control (to dummyload)."
            ::= { rfProbesEntry 14 }

        
        rfProbesDLFwdDelayTimeRfFail OBJECT-TYPE
            SYNTAX Integer32 (1..20)
            UNITS "seconds"
            MAX-ACCESS read-write
            STATUS current
            DESCRIPTION
                "This sets the delay time for the RF Fail control (to dummyload)."
            ::= { rfProbesEntry 15 }

        
        rfProbesDLFwdSetOffset OBJECT-TYPE
            SYNTAX Trigger
            MAX-ACCESS read-write
            STATUS current
            DESCRIPTION
                "This triggers Set Offset."
            ::= { rfProbesEntry 16 }

        
        rfProbesDLFwdSetGain OBJECT-TYPE
            SYNTAX Trigger
            MAX-ACCESS read-write
            STATUS current
            DESCRIPTION
                "This triggers Set Gain."
            ::= { rfProbesEntry 17 }

        
        rfProbesDLReflWarningLimit OBJECT-TYPE
            SYNTAX FloatingPoint
            UNITS "dB"
            MAX-ACCESS read-write
            STATUS current
            DESCRIPTION
                "This sets the warning limit for the transmitters reflection control (to 
                dummyload)."
            ::= { rfProbesEntry 18 }

        
        rfProbesDLReflSetOffset OBJECT-TYPE
            SYNTAX Trigger
            MAX-ACCESS read-write
            STATUS current
            DESCRIPTION
                "This triggers Set Offset."
            ::= { rfProbesEntry 19 }

        
        rfProbesDLReflSetGain OBJECT-TYPE
            SYNTAX Trigger
            MAX-ACCESS read-write
            STATUS current
            DESCRIPTION
                "This triggers Set Gain."
            ::= { rfProbesEntry 20 }

        
        rfProbesOstIdx OBJECT-TYPE
            SYNTAX IndexAB
            MAX-ACCESS not-accessible
            STATUS current
            DESCRIPTION
                "The dedicated outputstage (A/B)."
            ::= { rfProbesEntry 21 }

        
        rfProbesOstFwdNominal OBJECT-TYPE
            SYNTAX FloatingPoint
            UNITS "Watt"
            MAX-ACCESS read-write
            STATUS current
            DESCRIPTION
                "This sets the nominal value [W] of the outputstage."
            ::= { rfProbesEntry 22 }

        
        rfProbesOstFwdWarningLimit OBJECT-TYPE
            SYNTAX FloatingPoint
            UNITS "dB"
            MAX-ACCESS read-write
            STATUS current
            DESCRIPTION
                "This sets the warning limit for the outputstage RF control."
            ::= { rfProbesEntry 23 }

        
        rfProbesOstFwdFailLimit OBJECT-TYPE
            SYNTAX FloatingPoint
            UNITS "dB"
            MAX-ACCESS read-write
            STATUS current
            DESCRIPTION
                "This sets the fault limit for the outputstage RF control."
            ::= { rfProbesEntry 24 }

        
        rfProbesOstFwdDelayTimeRfFail OBJECT-TYPE
            SYNTAX Integer32 (1..20)
            UNITS "seconds"
            MAX-ACCESS read-write
            STATUS current
            DESCRIPTION
                "This sets the delay time for the outputstage RF Fail control."
            ::= { rfProbesEntry 25 }

        
        rfProbesOstFwdSetOffset OBJECT-TYPE
            SYNTAX Trigger
            MAX-ACCESS read-write
            STATUS current
            DESCRIPTION
                "This triggers Set Offset."
            ::= { rfProbesEntry 26 }

        
        rfProbesOstFwdSetGain OBJECT-TYPE
            SYNTAX Trigger
            MAX-ACCESS read-write
            STATUS current
            DESCRIPTION
                "This triggers Set Gain."
            ::= { rfProbesEntry 27 }

        
        rfProbesOstReflWarningLimit OBJECT-TYPE
            SYNTAX FloatingPoint
            UNITS "dB"
            MAX-ACCESS read-write
            STATUS current
            DESCRIPTION
                "This sets the warning limit for the outputstage reflection control."
            ::= { rfProbesEntry 28 }

        
        rfProbesOstReflSetOffset OBJECT-TYPE
            SYNTAX Trigger
            MAX-ACCESS read-write
            STATUS current
            DESCRIPTION
                "This triggers Set Offset."
            ::= { rfProbesEntry 29 }

        
        rfProbesOstReflSetGain OBJECT-TYPE
            SYNTAX Trigger
            MAX-ACCESS read-write
            STATUS current
            DESCRIPTION
                "This triggers Set Gain."
            ::= { rfProbesEntry 30 }

        
-- rack Table *************************
        rackTable OBJECT-TYPE
            SYNTAX SEQUENCE OF RackEntry
            MAX-ACCESS not-accessible
            STATUS current
            DESCRIPTION
                "This table contains important commands for the racks."
            ::= { rsXx8000MediaFloTxObjs 6 }

        
        rackEntry OBJECT-TYPE
            SYNTAX RackEntry
            MAX-ACCESS not-accessible
            STATUS current
            DESCRIPTION
                "An entry for a designated rack or rack's rf probe."
            INDEX { ostDeviceIdx, rackIdx, rackRfProbeIdx }
            ::= { rackTable 1 }

        
        RackEntry ::=
            SEQUENCE { 
                ostDeviceIdx
                    IndexAB,
                rackIdx
                    IndexRack,
                rackRfProbeIdx
                    INTEGER,
                amplifiersPerRack
                    Integer32,
                rackRfEventSignalling
                    TruthValue,
                rackReferenceVoltage
                    FloatingPoint,
                amplifiersPowerSupply
                    FloatingPoint,
                rackGeneralPurposeInput
                    INTEGER,
                rackOnOff
                    SwitchOnOff,
                rfProbePresent
                    TruthValue,
                rfProbeConfigurationLabel
                    ReadableString,
                rfProbeConfigurationNominalValue
                    Integer32,
                rfProbeThresholdRfFailLimit
                    FloatingPoint,
                rfProbeThresholdTimeoutRfFailCtr
                    Integer32,
                rfProbeThresholdWarningLimit
                    FloatingPoint,
                rfProbeCalibrationGain
                    FloatingPoint,
                rfProbeCalibrationOffset
                    FloatingPoint,
                rfProbeCalibrationSetGain
                    Trigger,
                rfProbeCalibrationSetOffset
                    Trigger,
                rfProbeMeasuredValue
                    FloatingPoint
             }

        ostDeviceIdx OBJECT-TYPE
            SYNTAX IndexAB
            MAX-ACCESS not-accessible
            STATUS current
            DESCRIPTION
                "The index to address outputstageA and outputstageB."
            ::= { rackEntry 2 }

        
        rackIdx OBJECT-TYPE
            SYNTAX IndexRack
            MAX-ACCESS not-accessible
            STATUS current
            DESCRIPTION
                "The index to address the racks."
            ::= { rackEntry 3 }

        
        rackRfProbeIdx OBJECT-TYPE
            SYNTAX INTEGER
                {
                forward(1),
                reflected(2)
                }
            MAX-ACCESS not-accessible
            STATUS current
            DESCRIPTION
                "The index to address forward and reflected RF probes.
                For not RF probe parameters this index is always 1."
            ::= { rackEntry 4 }

        
        amplifiersPerRack OBJECT-TYPE
            SYNTAX Integer32 (1..10)
            MAX-ACCESS read-only
            STATUS current
            DESCRIPTION
                "The number of amplifiers of a rack."
            ::= { rackEntry 6 }

        
        rackRfEventSignalling OBJECT-TYPE
            SYNTAX TruthValue
            MAX-ACCESS read-write
            STATUS current
            DESCRIPTION
                "This configures whether to signal rf events or not."
            ::= { rackEntry 7 }

        
        rackReferenceVoltage OBJECT-TYPE
            SYNTAX FloatingPoint
            UNITS "percent"
            MAX-ACCESS read-write
            STATUS current
            DESCRIPTION
                "This parameter controls the reference voltage (31.0 ... 100.0)."
            ::= { rackEntry 8 }

        
        amplifiersPowerSupply OBJECT-TYPE
            SYNTAX FloatingPoint
            UNITS "percent"
            MAX-ACCESS read-write
            STATUS current
            DESCRIPTION
                "This parameter controls the power supplies of the amplifier 
                within the rack (31.0 ... 100.0)."
            ::= { rackEntry 9 }

        
        rackGeneralPurposeInput OBJECT-TYPE
            SYNTAX INTEGER
                {
                unused(1),
                doorOpen(2),
                extCoolingWarning(3),
                extCoolingFault(4)
                }
            MAX-ACCESS read-write
            STATUS current
            DESCRIPTION
                "Setting of the general purpose input behaviour."
            ::= { rackEntry 10 }

        
        rackOnOff OBJECT-TYPE
            SYNTAX SwitchOnOff
            MAX-ACCESS read-write
            STATUS current
            DESCRIPTION
                "This switches the rack on/off."
            ::= { rackEntry 20 }

        
        rfProbePresent OBJECT-TYPE
            SYNTAX TruthValue
            MAX-ACCESS read-only
            STATUS current
            DESCRIPTION
                "If the RF probe of this rack is present."
            ::= { rackEntry 50 }

        
        rfProbeConfigurationLabel OBJECT-TYPE
            SYNTAX ReadableString (SIZE (0..12))
            MAX-ACCESS read-write
            STATUS obsolete
            DESCRIPTION
                "Name for the measured signal on RF Probe."
            ::= { rackEntry 51 }

        
        rfProbeConfigurationNominalValue OBJECT-TYPE
            SYNTAX Integer32 (0..100000)
            UNITS "W"
            MAX-ACCESS read-write
            STATUS current
            DESCRIPTION
                "The nominal value of the measured signal."
            ::= { rackEntry 52 }

        
        rfProbeThresholdRfFailLimit OBJECT-TYPE
            SYNTAX FloatingPoint
            UNITS "dB"
            MAX-ACCESS read-write
            STATUS current
            DESCRIPTION
                "Fault limit for the RF control (-20.0 ... 0.0)."
            ::= { rackEntry 55 }

        
        rfProbeThresholdTimeoutRfFailCtr OBJECT-TYPE
            SYNTAX Integer32 (1..20)
            UNITS "s"
            MAX-ACCESS read-write
            STATUS current
            DESCRIPTION
                "Timeout for RF Fail Control."
            ::= { rackEntry 56 }

        
        rfProbeThresholdWarningLimit OBJECT-TYPE
            SYNTAX FloatingPoint
            UNITS "dB"
            MAX-ACCESS read-write
            STATUS current
            DESCRIPTION
                "Warning limit for the RF control (-20.0 ... 0.0).
                
                For reflected probes:
                Warning limit for the reflection control. This limit is added to the 
                fault limit to generate the real warning limit; e.g. the fault limit 
                is -17.0dB and the warning limit is -3.0dB, so the warning is active 
                on a reflected power higher than -20.0 dB."
            ::= { rackEntry 57 }

        
        rfProbeCalibrationGain OBJECT-TYPE
            SYNTAX FloatingPoint
            UNITS "V"
            MAX-ACCESS read-only
            STATUS current
            DESCRIPTION
                "Measured value of gain calibration."
            ::= { rackEntry 60 }

        
        rfProbeCalibrationOffset OBJECT-TYPE
            SYNTAX FloatingPoint
            UNITS "V"
            MAX-ACCESS read-only
            STATUS current
            DESCRIPTION
                "Measured value of offset calibration."
            ::= { rackEntry 61 }

        
        rfProbeCalibrationSetGain OBJECT-TYPE
            SYNTAX Trigger
            MAX-ACCESS read-write
            STATUS current
            DESCRIPTION
                "Sets the gain calibration."
            ::= { rackEntry 62 }

        
        rfProbeCalibrationSetOffset OBJECT-TYPE
            SYNTAX Trigger
            MAX-ACCESS read-write
            STATUS current
            DESCRIPTION
                "Sets the offset calibration."
            ::= { rackEntry 63 }

        
        rfProbeMeasuredValue OBJECT-TYPE
            SYNTAX FloatingPoint
            UNITS "W"
            MAX-ACCESS read-only
            STATUS current
            DESCRIPTION
                "Measured forward/reflected power of antenna signal."
            ::= { rackEntry 65 }

        
        sx801AmplifierTable OBJECT-TYPE
            SYNTAX SEQUENCE OF Sx801AmplifierEntry
            MAX-ACCESS not-accessible
            STATUS current
            DESCRIPTION
                "Amplifier status values for SX801 amplifiers."
            ::= { rsXx8000MediaFloTxObjs 7 }

        
        sx801AmplifierEntry OBJECT-TYPE
            SYNTAX Sx801AmplifierEntry
            MAX-ACCESS not-accessible
            STATUS current
            DESCRIPTION
                "A row (an entry) for one amplifier."
            INDEX { sx801AmpIdx }
            ::= { sx801AmplifierTable 1 }

        
        Sx801AmplifierEntry ::=
            SEQUENCE { 
                sx801AmpIdx
                    IndexAmplifier,
                sx801AmpRfOut
                    Sx801AmplifierState,
                sx801AmpRfIn
                    Sx801AmplifierState,
                sx801AmpReflection
                    INTEGER,
                sx801AmpOn
                    INTEGER,
                sx801AmpAC
                    Sx801AmplifierState,
                sx801AmpCommunication
                    INTEGER,
                sx801AmpTransistor
                    Sx801AmplifierState,
                sx801AmpDriver
                    Sx801AmplifierState,
                sx801AmpTemperature
                    Sx801AmplifierState,
                sx801AmpBlower
                    Sx801AmplifierState,
                sx801AmpRegulation
                    Sx801AmplifierState,
                sx801AmpUpdate
                    TruthValue,
                sx801Supply1Temperature
                    Sx801AmplifierState,
                sx801Supply2Temperature
                    Sx801AmplifierState,
                sx801SupplyRTemperature
                    Sx801AmplifierState,
                sx801Supply1DC
                    Sx801AmplifierState,
                sx801Supply2DC
                    Sx801AmplifierState,
                sx801SupplyRDC
                    Sx801AmplifierState,
                sx801AmpValueI1
                    FloatingPoint,
                sx801AmpValueI2
                    FloatingPoint,
                sx801AmpValueI3
                    FloatingPoint,
                sx801AmpValueI4
                    FloatingPoint,
                sx801AmpValueIPre
                    FloatingPoint,
                sx801AmpValueIDrv1
                    FloatingPoint,
                sx801AmpValueIDrv2
                    FloatingPoint,
                sx801AmpValuePowerOut
                    FloatingPoint,
                sx801AmpValueReflection
                    FloatingPoint,
                sx801AmpValueVRef
                    FloatingPoint,
                sx801AmpValueVReg
                    FloatingPoint,
                sx801AmpValueTemperature
                    FloatingPoint,
                sx801AmpValueMonAtt
                    FloatingPoint,
                sx801AmpValueVAux1
                    FloatingPoint,
                sx801AmpValueVAux2
                    FloatingPoint,
                sx801Supply1ValuePwr
                    FloatingPoint,
                sx801Supply2ValuePwr
                    FloatingPoint,
                sx801Supply1ValueDc
                    FloatingPoint,
                sx801Supply2ValueDc
                    FloatingPoint
             }

        sx801AmpIdx OBJECT-TYPE
            SYNTAX IndexAmplifier
            MAX-ACCESS not-accessible
            STATUS current
            DESCRIPTION
                "The amplifier index."
            ::= { sx801AmplifierEntry 1 }

        
        sx801AmpRfOut OBJECT-TYPE
            SYNTAX Sx801AmplifierState
            MAX-ACCESS read-only
            STATUS current
            DESCRIPTION
                "Shows if the amplifier generates an RF or not.
                off(1): The amplifier output is switched off
                e.g. because the amplifier gets no input signal or the transmitter has been switched off
                warning(2): There is an RF but its level is less than the RF warning limit.
                ok(3): The RF level is greater than the RF warning limit."
            ::= { sx801AmplifierEntry 2 }

        
        sx801AmpRfIn OBJECT-TYPE
            SYNTAX Sx801AmplifierState
            MAX-ACCESS read-only
            STATUS current
            DESCRIPTION
                "Displays the state of the amplifier input.
                off(1): no input signal detected
                warning(2): the level of the input signal is too low or too high.
                ok(3): input signal is OK."
            ::= { sx801AmplifierEntry 3 }

        
        sx801AmpReflection OBJECT-TYPE
            SYNTAX INTEGER
                {
                off(1),
                warning(2),
                unknown(3),
                fault(4)
                }
            MAX-ACCESS read-only
            STATUS current
            DESCRIPTION
                " A reflection on RF output of this Amplifier module has been detected.
                This leads to a reduction of output power of the amplifier.
                
                "
            ::= { sx801AmplifierEntry 4 }

        
        sx801AmpOn OBJECT-TYPE
            SYNTAX INTEGER
                {
                off(1),
                on(3),
                unknown(4)
                }
            MAX-ACCESS read-only
            STATUS current
            DESCRIPTION
                "Shows if the amplifier has been switched on by the control unit."
            ::= { sx801AmplifierEntry 5 }

        
        sx801AmpAC OBJECT-TYPE
            SYNTAX Sx801AmplifierState
            MAX-ACCESS read-only
            STATUS current
            DESCRIPTION
                "Shows the state of primary voltage of the power supply."
            ::= { sx801AmplifierEntry 6 }

        
        sx801AmpCommunication OBJECT-TYPE
            SYNTAX INTEGER
                {
                off(1),
                unknown(2),
                ok(3),
                fault(4)
                }
            MAX-ACCESS read-only
            STATUS current
            DESCRIPTION
                "Displays if the CAN communication between amplifier and Sx801 is working or not."
            ::= { sx801AmplifierEntry 7 }

        
        sx801AmpTransistor OBJECT-TYPE
            SYNTAX Sx801AmplifierState
            MAX-ACCESS read-only
            STATUS current
            DESCRIPTION
                "A transistor fail is displayed here.
                For further information please see the amplifiers service menue."
            ::= { sx801AmplifierEntry 8 }

        
        sx801AmpDriver OBJECT-TYPE
            SYNTAX Sx801AmplifierState
            MAX-ACCESS read-only
            STATUS current
            DESCRIPTION
                "Shows a failure if one of the internal driver transistors does not work properly.
                For further information please see the amplifiers service menue."
            ::= { sx801AmplifierEntry 9 }

        
        sx801AmpTemperature OBJECT-TYPE
            SYNTAX Sx801AmplifierState
            MAX-ACCESS read-only
            STATUS current
            DESCRIPTION
                "Shows a fault if the temperature of amplifier module is too high."
            ::= { sx801AmplifierEntry 10 }

        
        sx801AmpBlower OBJECT-TYPE
            SYNTAX Sx801AmplifierState
            MAX-ACCESS read-only
            STATUS current
            DESCRIPTION
                "Displays the state of the internal blowers."
            ::= { sx801AmplifierEntry 11 }

        
        sx801AmpRegulation OBJECT-TYPE
            SYNTAX Sx801AmplifierState
            MAX-ACCESS read-only
            STATUS current
            DESCRIPTION
                "Shows a fault if the amplifier is not able to control its output power."
            ::= { sx801AmplifierEntry 12 }

        
        sx801AmpUpdate OBJECT-TYPE
            SYNTAX TruthValue
            MAX-ACCESS read-only
            STATUS current
            DESCRIPTION
                "Firmware update is in progress.
                This will be started automatically during a software update procedure of the transmitter."
            ::= { sx801AmplifierEntry 13 }

        
        sx801Supply1Temperature OBJECT-TYPE
            SYNTAX Sx801AmplifierState
            MAX-ACCESS read-only
            STATUS current
            DESCRIPTION
                "Shows a fault if the temperature of power supply one is too high."
            ::= { sx801AmplifierEntry 14 }

        
        sx801Supply2Temperature OBJECT-TYPE
            SYNTAX Sx801AmplifierState
            MAX-ACCESS read-only
            STATUS current
            DESCRIPTION
                "Shows a fault if the temperature of power supply two is too high."
            ::= { sx801AmplifierEntry 15 }

        
        sx801SupplyRTemperature OBJECT-TYPE
            SYNTAX Sx801AmplifierState
            MAX-ACCESS read-only
            STATUS current
            DESCRIPTION
                "Shows a fault if the temperature of the reserve power supply is too high."
            ::= { sx801AmplifierEntry 16 }

        
        sx801Supply1DC OBJECT-TYPE
            SYNTAX Sx801AmplifierState
            MAX-ACCESS read-only
            STATUS current
            DESCRIPTION
                "Shows a fault if the output voltage of power supply one is not ok."
            ::= { sx801AmplifierEntry 17 }

        
        sx801Supply2DC OBJECT-TYPE
            SYNTAX Sx801AmplifierState
            MAX-ACCESS read-only
            STATUS current
            DESCRIPTION
                "Shows a fault if the output voltage of power supply two is not ok."
            ::= { sx801AmplifierEntry 18 }

        
        sx801SupplyRDC OBJECT-TYPE
            SYNTAX Sx801AmplifierState
            MAX-ACCESS read-only
            STATUS current
            DESCRIPTION
                "Shows a fault if the output voltage of the reserve power supply is not ok."
            ::= { sx801AmplifierEntry 19 }

        
        sx801AmpValueI1 OBJECT-TYPE
            SYNTAX FloatingPoint
            UNITS "Ampere"
            MAX-ACCESS read-only
            STATUS current
            DESCRIPTION
                "The internal current from transistor pair 1."
            ::= { sx801AmplifierEntry 50 }

        
        sx801AmpValueI2 OBJECT-TYPE
            SYNTAX FloatingPoint
            UNITS "Ampere"
            MAX-ACCESS read-only
            STATUS current
            DESCRIPTION
                "The internal current from transistor pair 2."
            ::= { sx801AmplifierEntry 51 }

        
        sx801AmpValueI3 OBJECT-TYPE
            SYNTAX FloatingPoint
            UNITS "Ampere"
            MAX-ACCESS read-only
            STATUS current
            DESCRIPTION
                "The internal current from transistor pair 3."
            ::= { sx801AmplifierEntry 52 }

        
        sx801AmpValueI4 OBJECT-TYPE
            SYNTAX FloatingPoint
            UNITS "Ampere"
            MAX-ACCESS read-only
            STATUS current
            DESCRIPTION
                "The internal current from transistor pair 4."
            ::= { sx801AmplifierEntry 53 }

        
        sx801AmpValueIPre OBJECT-TYPE
            SYNTAX FloatingPoint
            UNITS "Ampere"
            MAX-ACCESS read-only
            STATUS current
            DESCRIPTION
                "The internal current from preamplifier."
            ::= { sx801AmplifierEntry 54 }

        
        sx801AmpValueIDrv1 OBJECT-TYPE
            SYNTAX FloatingPoint
            UNITS "Ampere"
            MAX-ACCESS read-only
            STATUS current
            DESCRIPTION
                "The internal current from driver transistor pair 1."
            ::= { sx801AmplifierEntry 55 }

        
        sx801AmpValueIDrv2 OBJECT-TYPE
            SYNTAX FloatingPoint
            UNITS "Ampere"
            MAX-ACCESS read-only
            STATUS current
            DESCRIPTION
                "The internal current from driver transistor pair 2."
            ::= { sx801AmplifierEntry 56 }

        
        sx801AmpValuePowerOut OBJECT-TYPE
            SYNTAX FloatingPoint
            UNITS "Watt"
            MAX-ACCESS read-only
            STATUS current
            DESCRIPTION
                "The base value in Volt to calculate the output power
                of this amplifier module."
            ::= { sx801AmplifierEntry 57 }

        
        sx801AmpValueReflection OBJECT-TYPE
            SYNTAX FloatingPoint
            UNITS "Watt"
            MAX-ACCESS read-only
            STATUS current
            DESCRIPTION
                "The base value in Volt for detection of reflections."
            ::= { sx801AmplifierEntry 58 }

        
        sx801AmpValueVRef OBJECT-TYPE
            SYNTAX FloatingPoint
            UNITS "Volt"
            MAX-ACCESS read-only
            STATUS current
            DESCRIPTION
                "The internal reference voltage to set the output power."
            ::= { sx801AmplifierEntry 59 }

        
        sx801AmpValueVReg OBJECT-TYPE
            SYNTAX FloatingPoint
            UNITS "Volt"
            MAX-ACCESS read-only
            STATUS current
            DESCRIPTION
                "The internal value for output power regulation."
            ::= { sx801AmplifierEntry 60 }

        
        sx801AmpValueTemperature OBJECT-TYPE
            SYNTAX FloatingPoint
            UNITS "degree Celsius"
            MAX-ACCESS read-only
            STATUS current
            DESCRIPTION
                "The internal temperature of Amplifier.
                In case of L-band amplifier, the shown temperature is valid only,
                if the amplifier is switched on."
            ::= { sx801AmplifierEntry 61 }

        
        sx801AmpValueMonAtt OBJECT-TYPE
            SYNTAX FloatingPoint
            UNITS "dB"
            MAX-ACCESS read-only
            STATUS current
            DESCRIPTION
                "The attenuation of monitoring output on the front of the
                amplifier module (Amp RF Mon)."
            ::= { sx801AmplifierEntry 62 }

        
        sx801AmpValueVAux1 OBJECT-TYPE
            SYNTAX FloatingPoint
            UNITS "Volt"
            MAX-ACCESS read-only
            STATUS current
            DESCRIPTION
                "The voltage power detector 1."
            ::= { sx801AmplifierEntry 63 }

        
        sx801AmpValueVAux2 OBJECT-TYPE
            SYNTAX FloatingPoint
            UNITS "Volt"
            MAX-ACCESS read-only
            STATUS current
            DESCRIPTION
                "The voltage power detector 2."
            ::= { sx801AmplifierEntry 64 }

        
        sx801Supply1ValuePwr OBJECT-TYPE
            SYNTAX FloatingPoint
            UNITS "Volt"
            MAX-ACCESS read-only
            STATUS current
            DESCRIPTION
                "The power supply one control voltage."
            ::= { sx801AmplifierEntry 65 }

        
        sx801Supply2ValuePwr OBJECT-TYPE
            SYNTAX FloatingPoint
            UNITS "Volt"
            MAX-ACCESS read-only
            STATUS current
            DESCRIPTION
                "The power supply two control voltage."
            ::= { sx801AmplifierEntry 66 }

        
        sx801Supply1ValueDc OBJECT-TYPE
            SYNTAX FloatingPoint
            UNITS "Volt"
            MAX-ACCESS read-only
            STATUS current
            DESCRIPTION
                "The internal supply voltage of transistor path two.
                In systems with two power supplies this value is equal
                to the output voltage of supply one."
            ::= { sx801AmplifierEntry 67 }

        
        sx801Supply2ValueDc OBJECT-TYPE
            SYNTAX FloatingPoint
            UNITS "Volt"
            MAX-ACCESS read-only
            STATUS current
            DESCRIPTION
                "The internal supply voltage of transistor path two.
                In systems with two power supplies this value is equal
                to the output voltage of supply two."
            ::= { sx801AmplifierEntry 68 }

        
-- *****************************************************************************
-- **          event definitions
-- *****************************************************************************
        rsXx8000MediaFloTxEvents OBJECT IDENTIFIER ::= { rsXx8000MediaFloTx 3 }

        
        eventTx OBJECT IDENTIFIER ::= { rsXx8000MediaFloTxEvents 2 }

        
-- notifications
        eventsTxV2 OBJECT-IDENTITY
            STATUS current
            DESCRIPTION 
                "Compatibility to SMIv1."
            ::= { eventTx 0 }

        
        txSummaryFault NOTIFICATION-TYPE
            OBJECTS { eventAlarmPriority, eventAlarmClass, eventEvent }
            STATUS current
            DESCRIPTION 
                "Transmitter Summary Fault."
            ::= { eventsTxV2 1 }

        
        txSummaryWarning NOTIFICATION-TYPE
            OBJECTS { eventAlarmPriority, eventAlarmClass, eventEvent }
            STATUS current
            DESCRIPTION 
                "Transmitter Summary Warning."
            ::= { eventsTxV2 2 }

        
        txLocal NOTIFICATION-TYPE
            OBJECTS { eventAlarmPriority, eventAlarmClass, eventEvent }
            STATUS current
            DESCRIPTION 
                "Transmitter Local/Remote."
            ::= { eventsTxV2 3 }

        
        txRfOn NOTIFICATION-TYPE
            OBJECTS { eventAlarmPriority, eventAlarmClass, eventEvent }
            STATUS current
            DESCRIPTION 
                "Transmitter RF On/Off."
            ::= { eventsTxV2 4 }

        
        txRfOk NOTIFICATION-TYPE
            OBJECTS { eventAlarmPriority, eventAlarmClass, eventEvent }
            STATUS current
            DESCRIPTION 
                "Transmitter RF Ok / Not OK."
            ::= { eventsTxV2 5 }

        
        txParamSetSubDeviceDiffers NOTIFICATION-TYPE
            OBJECTS { eventAlarmPriority, eventAlarmClass, eventEvent }
            STATUS obsolete
            DESCRIPTION 
                "Parameterset of subdevice is different.
                The currently loaded parameterset is inconsistent because
                a subdevice (e.g. an exciter) has a different configuration than expected.
                To correct this, save settings to the current or save a complete new."
            ::= { eventsTxV2 6 }

        
        txParamSetValuesChanged NOTIFICATION-TYPE
            OBJECTS { eventAlarmPriority, eventAlarmClass, eventEvent }
            STATUS current
            DESCRIPTION 
                "Value Of Current Parameterset Changed.
                The currently loaded parameterset is inconsistent because
                there were changes happening since the load/save of it.
                To correct this, save settings to the current or save a complete new."
            ::= { eventsTxV2 7 }

        
        txRfLoopProgram NOTIFICATION-TYPE
            OBJECTS { eventAlarmPriority, eventAlarmClass, eventEvent }
            STATUS current
            DESCRIPTION 
                "NetCCU Loop Program."
            ::= { eventsTxV2 8 }

        
        txRfLoopReserve NOTIFICATION-TYPE
            OBJECTS { eventAlarmPriority, eventAlarmClass, eventEvent }
            STATUS current
            DESCRIPTION 
                "NetCCU Loop Reserve."
            ::= { eventsTxV2 9 }

        
        txRfWarning NOTIFICATION-TYPE
            OBJECTS { eventAlarmPriority, eventAlarmClass, eventEvent }
            STATUS current
            DESCRIPTION 
                "NetCCU RF Warning."
            ::= { eventsTxV2 10 }

        
        txReflectionWarning NOTIFICATION-TYPE
            OBJECTS { eventAlarmPriority, eventAlarmClass, eventEvent }
            STATUS current
            DESCRIPTION 
                "NetCCU Reflection Warning."
            ::= { eventsTxV2 11 }

        
        txNetCCUFanFault NOTIFICATION-TYPE
            OBJECTS { eventAlarmPriority, eventAlarmClass, eventEvent }
            STATUS current
            DESCRIPTION 
                "NetCCU Fan Fault.
                This is valid, if Fan Control is switched on (see menu NetCCU Setup - Common)."
            ::= { eventsTxV2 12 }

        
        txNetCCUPowerSupply NOTIFICATION-TYPE
            OBJECTS { eventAlarmPriority, eventAlarmClass, eventEvent }
            STATUS current
            DESCRIPTION 
                "NetCCU Power Supply."
            ::= { eventsTxV2 13 }

        
        txRfFail NOTIFICATION-TYPE
            OBJECTS { eventAlarmPriority, eventAlarmClass, eventEvent }
            STATUS current
            DESCRIPTION 
                "NetCCU RF Fail."
            ::= { eventsTxV2 14 }

        
        txReflectionFault NOTIFICATION-TYPE
            OBJECTS { eventAlarmPriority, eventAlarmClass, eventEvent }
            STATUS current
            DESCRIPTION 
                "NetCCU Reflection Fault."
            ::= { eventsTxV2 15 }

        
        txNetCCUBoardTemperatureFault NOTIFICATION-TYPE
            OBJECTS { eventAlarmPriority, eventAlarmClass, eventEvent }
            STATUS deprecated
            DESCRIPTION 
                "NetCCU Board Temperature Fault.
                
                deprecated: this information is now handled as a warning
                (txNetCCUBoardTemperatureWarning)"
            ::= { eventsTxV2 16 }

        
        txNetCCUNoConnectionToExcA NOTIFICATION-TYPE
            OBJECTS { eventAlarmPriority, eventAlarmClass, eventEvent }
            STATUS current
            DESCRIPTION 
                "NetCCU Connection To ExciterA Faulty."
            ::= { eventsTxV2 17 }

        
        txNetCCUNoConnectionToOstA NOTIFICATION-TYPE
            OBJECTS { eventAlarmPriority, eventAlarmClass, eventEvent, indexAB }
            STATUS current
            DESCRIPTION 
                "NetCCU Connection To OutputstageA Faulty."
            ::= { eventsTxV2 18 }

        
        txNetCCUNoConnectionToExcB NOTIFICATION-TYPE
            OBJECTS { eventAlarmPriority, eventAlarmClass, eventEvent }
            STATUS current
            DESCRIPTION 
                "NetCCU Connection To ExciterB Faulty."
            ::= { eventsTxV2 19 }

        
        txNetCCUNoConnectionToOstB NOTIFICATION-TYPE
            OBJECTS { eventAlarmPriority, eventAlarmClass, eventEvent, indexAB }
            STATUS current
            DESCRIPTION 
                "NetCCU Connection To OutputstageB Faulty."
            ::= { eventsTxV2 20 }

        
        txAutomaticExcReady NOTIFICATION-TYPE
            OBJECTS { eventAlarmPriority, eventAlarmClass, eventEvent }
            STATUS current
            DESCRIPTION 
                "Exciter Automatic Ready."
            ::= { eventsTxV2 21 }

        
        txAutomaticExcChanged NOTIFICATION-TYPE
            OBJECTS { eventAlarmPriority, eventAlarmClass, eventEvent }
            STATUS current
            DESCRIPTION 
                "Exciter Automatic Changed."
            ::= { eventsTxV2 22 }

        
        txAutomaticExcFault NOTIFICATION-TYPE
            OBJECTS { eventAlarmPriority, eventAlarmClass, eventEvent }
            STATUS current
            DESCRIPTION 
                "Exciter Automatic Fault."
            ::= { eventsTxV2 23 }

        
        txAutomaticOstReady NOTIFICATION-TYPE
            OBJECTS { eventAlarmPriority, eventAlarmClass, eventEvent }
            STATUS current
            DESCRIPTION 
                "Outputstage Automatic Ready.
                
                This paramter is only available for systems with an automatic output switch."
            ::= { eventsTxV2 24 }

        
        txAutomaticOstChanged NOTIFICATION-TYPE
            OBJECTS { eventAlarmPriority, eventAlarmClass, eventEvent }
            STATUS current
            DESCRIPTION 
                "Outputstage Automatic Changed.
                
                This paramter is only available for systems with an automatic output switch."
            ::= { eventsTxV2 25 }

        
        txAutomaticOstFault NOTIFICATION-TYPE
            OBJECTS { eventAlarmPriority, eventAlarmClass, eventEvent }
            STATUS current
            DESCRIPTION 
                "Outputstage Automatic Fault.
                
                This paramter is only available for systems with an automatic output switch."
            ::= { eventsTxV2 26 }

        
        txNetCCUBoardTemperatureWarning NOTIFICATION-TYPE
            OBJECTS { eventAlarmPriority, eventAlarmClass, eventEvent }
            STATUS current
            DESCRIPTION 
                "NetCCU Board Temperature Warning"
            ::= { eventsTxV2 27 }

        
        txInternalPowerSupplyWarning NOTIFICATION-TYPE
            OBJECTS { eventAlarmPriority, eventAlarmClass, eventEvent }
            STATUS current
            DESCRIPTION 
                "NetCCU internal Power Supply warning"
            ::= { eventsTxV2 30 }

        
        txExternalPowerSupplyWarning NOTIFICATION-TYPE
            OBJECTS { eventAlarmPriority, eventAlarmClass, eventEvent }
            STATUS current
            DESCRIPTION 
                "NetCCU external (additional) Power Supply warning"
            ::= { eventsTxV2 31 }

        
        txModeSwitchOverStarted NOTIFICATION-TYPE
            OBJECTS { eventAlarmPriority, eventAlarmClass, eventEvent }
            STATUS current
            DESCRIPTION 
                "Switch over of TX mode started."
            ::= { eventsTxV2 35 }

        
        txModeSwitchOverEnded NOTIFICATION-TYPE
            OBJECTS { eventAlarmPriority, eventAlarmClass, eventEvent }
            STATUS current
            DESCRIPTION 
                "Switch over of TX mode ended."
            ::= { eventsTxV2 36 }

        
        txModeInconsistent NOTIFICATION-TYPE
            OBJECTS { eventAlarmPriority, eventAlarmClass, eventEvent }
            STATUS current
            DESCRIPTION 
                "An inconsistency in configuration of TX mode was detected.
                The CCU and exiter configurations are incompatible."
            ::= { eventsTxV2 37 }

        
        txModeSwitchOverFailed NOTIFICATION-TYPE
            OBJECTS { eventAlarmPriority, eventAlarmClass, eventEvent }
            STATUS current
            DESCRIPTION 
                "Switch over of TX mode failed.
                Please check whether the configurations of CCU and exciter are correct."
            ::= { eventsTxV2 38 }

        
        txExcSummaryFault NOTIFICATION-TYPE
            OBJECTS { eventAlarmPriority, eventAlarmClass, eventEvent, indexAB }
            STATUS current
            DESCRIPTION 
                "Exciter Summary Fault."
            ::= { eventsTxV2 100 }

        
        txExcSummaryWarning NOTIFICATION-TYPE
            OBJECTS { eventAlarmPriority, eventAlarmClass, eventEvent, indexAB }
            STATUS current
            DESCRIPTION 
                "Exciter Summary Warning."
            ::= { eventsTxV2 101 }

        
        txExcLocal NOTIFICATION-TYPE
            OBJECTS { eventAlarmPriority, eventAlarmClass, eventEvent, indexAB }
            STATUS current
            DESCRIPTION 
                "Exciter Local/Remote"
            ::= { eventsTxV2 102 }

        
        txExcInputConnect1 NOTIFICATION-TYPE
            OBJECTS { eventAlarmPriority, eventAlarmClass, eventEvent, indexAB }
            STATUS current
            DESCRIPTION 
                "Exciter has connected input 1 signal."
            ::= { eventsTxV2 105 }

        
        txExcInputConnect2 NOTIFICATION-TYPE
            OBJECTS { eventAlarmPriority, eventAlarmClass, eventEvent, indexAB }
            STATUS current
            DESCRIPTION 
                "Exciter has connected input 2 signal."
            ::= { eventsTxV2 106 }

        
        txExcInputAsiLocked1 NOTIFICATION-TYPE
            OBJECTS { eventAlarmPriority, eventAlarmClass, eventEvent, indexAB }
            STATUS current
            DESCRIPTION 
                "Exciter has locked ASI 1 input."
            ::= { eventsTxV2 107 }

        
        txExcInputAsiLocked2 NOTIFICATION-TYPE
            OBJECTS { eventAlarmPriority, eventAlarmClass, eventEvent, indexAB }
            STATUS current
            DESCRIPTION 
                "Exciter has locked ASI 2 input."
            ::= { eventsTxV2 108 }

        
        txExcInputActive1 NOTIFICATION-TYPE
            OBJECTS { eventAlarmPriority, eventAlarmClass, eventEvent, indexAB }
            STATUS current
            DESCRIPTION 
                "Exciter Input 1 is active."
            ::= { eventsTxV2 109 }

        
        txExcInputActive2 NOTIFICATION-TYPE
            OBJECTS { eventAlarmPriority, eventAlarmClass, eventEvent, indexAB }
            STATUS current
            DESCRIPTION 
                "Exciter Input 2 is active."
            ::= { eventsTxV2 110 }

        
        txExcRfOn NOTIFICATION-TYPE
            OBJECTS { eventAlarmPriority, eventAlarmClass, eventEvent, indexAB }
            STATUS current
            DESCRIPTION 
                "Exciter RF On."
            ::= { eventsTxV2 114 }

        
        txExcRfFail NOTIFICATION-TYPE
            OBJECTS { eventAlarmPriority, eventAlarmClass, eventEvent, indexAB }
            STATUS current
            DESCRIPTION 
                "Exciter RF Fail."
            ::= { eventsTxV2 115 }

        
        txExcOn NOTIFICATION-TYPE
            OBJECTS { eventAlarmPriority, eventAlarmClass, eventEvent, indexAB }
            STATUS current
            DESCRIPTION 
                "Exciter On."
            ::= { eventsTxV2 116 }

        
        txExcRfLoop NOTIFICATION-TYPE
            OBJECTS { eventAlarmPriority, eventAlarmClass, eventEvent, indexAB }
            STATUS current
            DESCRIPTION 
                "Exciter RF loop."
            ::= { eventsTxV2 117 }

        
        txExcBoardTemperatureFault NOTIFICATION-TYPE
            OBJECTS { eventAlarmPriority, eventAlarmClass, eventEvent, indexAB }
            STATUS current
            DESCRIPTION 
                "Exciter Board Temperature Fault."
            ::= { eventsTxV2 119 }

        
        txExcMute NOTIFICATION-TYPE
            OBJECTS { eventAlarmPriority, eventAlarmClass, eventEvent, indexAB }
            STATUS current
            DESCRIPTION 
                "Exciter Mute."
            ::= { eventsTxV2 120 }

        
        txExcNoInput NOTIFICATION-TYPE
            OBJECTS { eventAlarmPriority, eventAlarmClass, eventEvent, indexAB }
            STATUS current
            DESCRIPTION 
                "Exciter has no valid input signal."
            ::= { eventsTxV2 121 }

        
        txExcReferenceFail NOTIFICATION-TYPE
            OBJECTS { eventAlarmPriority, eventAlarmClass, eventEvent, indexAB }
            STATUS current
            DESCRIPTION 
                "Exciter Reference Fail."
            ::= { eventsTxV2 124 }

        
        txExcPPSFail NOTIFICATION-TYPE
            OBJECTS { eventAlarmPriority, eventAlarmClass, eventEvent, indexAB }
            STATUS current
            DESCRIPTION 
                "Exciter PPS Fail."
            ::= { eventsTxV2 126 }

        
        txExcOutputOpen NOTIFICATION-TYPE
            OBJECTS { eventAlarmPriority, eventAlarmClass, eventEvent, indexAB }
            STATUS current
            DESCRIPTION 
                "Exciter output open."
            ::= { eventsTxV2 128 }

        
        txExcSelfTest NOTIFICATION-TYPE
            OBJECTS { eventAlarmPriority, eventAlarmClass, eventEvent, indexAB }
            STATUS current
            DESCRIPTION 
                "Exciter hardware self test."
            ::= { eventsTxV2 129 }

        
        txExcTestSignal NOTIFICATION-TYPE
            OBJECTS { eventAlarmPriority, eventAlarmClass, eventEvent, indexAB }
            STATUS current
            DESCRIPTION 
                "Exciter Testsignal Active."
            ::= { eventsTxV2 130 }

        
        txExcFanWarning NOTIFICATION-TYPE
            OBJECTS { eventAlarmPriority, eventAlarmClass, eventEvent, indexAB }
            STATUS current
            DESCRIPTION 
                "Exciter has one faulty fan."
            ::= { eventsTxV2 131 }

        
        txExcFanFault NOTIFICATION-TYPE
            OBJECTS { eventAlarmPriority, eventAlarmClass, eventEvent, indexAB }
            STATUS current
            DESCRIPTION 
                "Both exciter fans are faulty."
            ::= { eventsTxV2 132 }

        
        txExcSFNDelay NOTIFICATION-TYPE
            OBJECTS { eventAlarmPriority, eventAlarmClass, eventEvent, indexAB }
            STATUS current
            DESCRIPTION 
                "Exciter SFN Delay Fault."
            ::= { eventsTxV2 134 }

        
        txExcFloModSumWarning NOTIFICATION-TYPE
            OBJECTS { eventAlarmPriority, eventAlarmClass, eventEvent, indexAB }
            STATUS current
            DESCRIPTION 
                "Exciter FLO Modulator Summary Warning."
            ::= { eventsTxV2 140 }

        
        txExcFloModSumError NOTIFICATION-TYPE
            OBJECTS { eventAlarmPriority, eventAlarmClass, eventEvent, indexAB }
            STATUS current
            DESCRIPTION 
                "Exciter FLO Modulator Summary Error."
            ::= { eventsTxV2 141 }

        
        txExcFloModSFNBufferWarning NOTIFICATION-TYPE
            OBJECTS { eventAlarmPriority, eventAlarmClass, eventEvent, indexAB }
            STATUS current
            DESCRIPTION 
                "Exciter FLO Modulator SFN Buffer Warning."
            ::= { eventsTxV2 142 }

        
        txExcFloModError NOTIFICATION-TYPE
            OBJECTS { eventAlarmPriority, eventAlarmClass, eventEvent, indexAB }
            STATUS current
            DESCRIPTION 
                "Exciter FLO Modulator Error."
            ::= { eventsTxV2 143 }

        
        txExcFloModMemoryError NOTIFICATION-TYPE
            OBJECTS { eventAlarmPriority, eventAlarmClass, eventEvent, indexAB }
            STATUS current
            DESCRIPTION 
                "Exciter FLO Modulator Memory Error."
            ::= { eventsTxV2 144 }

        
        txExcFloModParameterUpdate NOTIFICATION-TYPE
            OBJECTS { eventAlarmPriority, eventAlarmClass, eventEvent, indexAB }
            STATUS current
            DESCRIPTION 
                "Exciter FLO Modulator Parameter Update."
            ::= { eventsTxV2 145 }

        
        txOstSummaryFault NOTIFICATION-TYPE
            OBJECTS { eventAlarmPriority, eventAlarmClass, eventEvent, indexAB }
            STATUS current
            DESCRIPTION 
                "Outputstage Summary Fault."
            ::= { eventsTxV2 200 }

        
        txOstSummaryWarning NOTIFICATION-TYPE
            OBJECTS { eventAlarmPriority, eventAlarmClass, eventEvent, indexAB }
            STATUS current
            DESCRIPTION 
                "Outputstage Summary Warning."
            ::= { eventsTxV2 201 }

        
        txOstRfOn NOTIFICATION-TYPE
            OBJECTS { eventAlarmPriority, eventAlarmClass, eventEvent, indexAB }
            STATUS current
            DESCRIPTION 
                "Outputstage RF On."
            ::= { eventsTxV2 202 }

        
        txOstRfOk NOTIFICATION-TYPE
            OBJECTS { eventAlarmPriority, eventAlarmClass, eventEvent, indexAB }
            STATUS current
            DESCRIPTION 
                "Outputstage RF Ok."
            ::= { eventsTxV2 203 }

        
        txOstNoInput NOTIFICATION-TYPE
            OBJECTS { eventAlarmPriority, eventAlarmClass, eventEvent, indexAB }
            STATUS current
            DESCRIPTION 
                "Outputstage no input signal."
            ::= { eventsTxV2 204 }

        
        txOstRfWarning NOTIFICATION-TYPE
            OBJECTS { eventAlarmPriority, eventAlarmClass, eventEvent, indexAB }
            STATUS current
            DESCRIPTION 
                "Outputstage RF Warning."
            ::= { eventsTxV2 205 }

        
        txOstReflectionWarning NOTIFICATION-TYPE
            OBJECTS { eventAlarmPriority, eventAlarmClass, eventEvent, indexAB }
            STATUS current
            DESCRIPTION 
                "Outputstage Reflection Warning."
            ::= { eventsTxV2 206 }

        
        txOstRackWarning NOTIFICATION-TYPE
            OBJECTS { eventAlarmPriority, eventAlarmClass, eventEvent, indexAB }
            STATUS current
            DESCRIPTION 
                "Outputstage Rack Warning. At least one rack has an error pending."
            ::= { eventsTxV2 207 }

        
        txOstCoolingWarning NOTIFICATION-TYPE
            OBJECTS { eventAlarmPriority, eventAlarmClass, eventEvent, indexAB }
            STATUS current
            DESCRIPTION 
                "Outputstage Cooling Warning."
            ::= { eventsTxV2 208 }

        
        txOstRfFail NOTIFICATION-TYPE
            OBJECTS { eventAlarmPriority, eventAlarmClass, eventEvent, indexAB }
            STATUS current
            DESCRIPTION 
                "Outputstage RF Fail."
            ::= { eventsTxV2 209 }

        
        txOstReflectionFault NOTIFICATION-TYPE
            OBJECTS { eventAlarmPriority, eventAlarmClass, eventEvent, indexAB }
            STATUS current
            DESCRIPTION 
                "Outputstage Reflection Fault."
            ::= { eventsTxV2 210 }

        
        txOstACFault NOTIFICATION-TYPE
            OBJECTS { eventAlarmPriority, eventAlarmClass, eventEvent, indexAB }
            STATUS current
            DESCRIPTION 
                "Outputstage AC Fault."
            ::= { eventsTxV2 211 }

        
        txOstCoolingFault NOTIFICATION-TYPE
            OBJECTS { eventAlarmPriority, eventAlarmClass, eventEvent, indexAB }
            STATUS current
            DESCRIPTION 
                "Outputstage Cooling Fault."
            ::= { eventsTxV2 212 }

        
        txOstCommFault NOTIFICATION-TYPE
            OBJECTS { eventAlarmPriority, eventAlarmClass, eventEvent, indexAB }
            STATUS current
            DESCRIPTION 
                "Outputstage Communication Fault."
            ::= { eventsTxV2 213 }

        
        txRackSumFault NOTIFICATION-TYPE
            OBJECTS { eventAlarmPriority, eventAlarmClass, eventEvent, indexAB, indexRack
                 }
            STATUS current
            DESCRIPTION 
                "Summary Fault at a designated rack.
                This event automatically leads to txOstRackWarning."
            ::= { eventsTxV2 300 }

        
        txRackSumWarning NOTIFICATION-TYPE
            OBJECTS { eventAlarmPriority, eventAlarmClass, eventEvent, indexAB, indexRack
                 }
            STATUS current
            DESCRIPTION 
                "Summary Warning at a designated rack."
            ::= { eventsTxV2 301 }

        
        txRackOn NOTIFICATION-TYPE
            OBJECTS { eventAlarmPriority, eventAlarmClass, eventEvent, indexAB, indexRack
                 }
            STATUS current
            DESCRIPTION 
                "The designated racks operation mode is on."
            ::= { eventsTxV2 302 }

        
        txRackGpiWarning NOTIFICATION-TYPE
            OBJECTS { eventAlarmPriority, eventAlarmClass, eventEvent, indexAB, indexRack
                 }
            STATUS current
            DESCRIPTION 
                "A warning on the general purpose input occurred.
                This depends on the current configuration of the GPI. (See:Rack Setup/Rack Controller)"
            ::= { eventsTxV2 303 }

        
        txRackFan1Fault NOTIFICATION-TYPE
            OBJECTS { eventAlarmPriority, eventAlarmClass, eventEvent, indexAB, indexRack
                 }
            STATUS current
            DESCRIPTION 
                "The designated rack signals a fault of fan 1."
            ::= { eventsTxV2 304 }

        
        txRackFan2Fault NOTIFICATION-TYPE
            OBJECTS { eventAlarmPriority, eventAlarmClass, eventEvent, indexAB, indexRack
                 }
            STATUS current
            DESCRIPTION 
                "The designated rack signals a fault of fan 2."
            ::= { eventsTxV2 305 }

        
        txRackCoolingSumWarning NOTIFICATION-TYPE
            OBJECTS { eventAlarmPriority, eventAlarmClass, eventEvent, indexAB, indexRack
                 }
            STATUS current
            DESCRIPTION 
                "The designated rack signals a summary cooling warning."
            ::= { eventsTxV2 306 }

        
        txRackAmplifierSumFault NOTIFICATION-TYPE
            OBJECTS { eventAlarmPriority, eventAlarmClass, eventEvent, indexAB, indexRack
                 }
            STATUS current
            DESCRIPTION 
                "The designated rack signals at least one faulty amplifier."
            ::= { eventsTxV2 307 }

        
        txRackNoLink NOTIFICATION-TYPE
            OBJECTS { eventAlarmPriority, eventAlarmClass, eventEvent, indexAB, indexRack
                 }
            STATUS current
            DESCRIPTION 
                "No communication to the designated rack."
            ::= { eventsTxV2 308 }

        
        txRackGpiFault NOTIFICATION-TYPE
            OBJECTS { eventAlarmPriority, eventAlarmClass, eventEvent, indexAB, indexRack
                 }
            STATUS current
            DESCRIPTION 
                "A fault on the general purpose input occurred.
                This depends on the current configuration of the GPI. (See:Rack Setup/Rack Controller)"
            ::= { eventsTxV2 309 }

        
        txRackTemperatureFault NOTIFICATION-TYPE
            OBJECTS { eventAlarmPriority, eventAlarmClass, eventEvent, indexAB, indexRack
                 }
            STATUS current
            DESCRIPTION 
                "The designated rack signals a temperature fault - temperature too high."
            ::= { eventsTxV2 310 }

        
        txRackACFault NOTIFICATION-TYPE
            OBJECTS { eventAlarmPriority, eventAlarmClass, eventEvent, indexAB, indexRack
                 }
            STATUS current
            DESCRIPTION 
                "The designated rack signals an AC (phase) fault."
            ::= { eventsTxV2 311 }

        
        txRackCoolingSumFault NOTIFICATION-TYPE
            OBJECTS { eventAlarmPriority, eventAlarmClass, eventEvent, indexAB, indexRack
                 }
            STATUS current
            DESCRIPTION 
                "The designated rack signals a summary cooling fault."
            ::= { eventsTxV2 312 }

        
        txRackTempFaultAbs1 NOTIFICATION-TYPE
            OBJECTS { eventAlarmPriority, eventAlarmClass, eventEvent, indexAB, indexRack
                 }
            STATUS current
            DESCRIPTION 
                "The designated rack signals a temperature fault of absorber 1."
            ::= { eventsTxV2 313 }

        
        txRackTempFaultAbs2 NOTIFICATION-TYPE
            OBJECTS { eventAlarmPriority, eventAlarmClass, eventEvent, indexAB, indexRack
                 }
            STATUS current
            DESCRIPTION 
                "The designated rack signals a temperature fault of absorber 2."
            ::= { eventsTxV2 314 }

        
        txRackDCFault NOTIFICATION-TYPE
            OBJECTS { eventAlarmPriority, eventAlarmClass, eventEvent, indexAB, indexRack
                 }
            STATUS current
            DESCRIPTION 
                "The designated rack signals a DC fault."
            ::= { eventsTxV2 315 }

        
        txRackRfOn NOTIFICATION-TYPE
            OBJECTS { eventAlarmPriority, eventAlarmClass, eventEvent, indexAB, indexRack
                 }
            STATUS current
            DESCRIPTION 
                "RF power is on."
            ::= { eventsTxV2 318 }

        
        txRackRfOk NOTIFICATION-TYPE
            OBJECTS { eventAlarmPriority, eventAlarmClass, eventEvent, indexAB, indexRack
                 }
            STATUS current
            DESCRIPTION 
                "RF power is ok."
            ::= { eventsTxV2 319 }

        
        txRackRfWarning NOTIFICATION-TYPE
            OBJECTS { eventAlarmPriority, eventAlarmClass, eventEvent, indexAB, indexRack
                 }
            STATUS current
            DESCRIPTION 
                "RF power decreased the warning threshold."
            ::= { eventsTxV2 320 }

        
        txRackRfFault NOTIFICATION-TYPE
            OBJECTS { eventAlarmPriority, eventAlarmClass, eventEvent, indexAB, indexRack
                 }
            STATUS current
            DESCRIPTION 
                "RF output power decreased the fault threshold."
            ::= { eventsTxV2 321 }

        
        txRackReflectionWarning NOTIFICATION-TYPE
            OBJECTS { eventAlarmPriority, eventAlarmClass, eventEvent, indexAB, indexRack
                 }
            STATUS current
            DESCRIPTION 
                "The reflected power increased the warning threshold"
            ::= { eventsTxV2 322 }

        
        txRackReflectionFault NOTIFICATION-TYPE
            OBJECTS { eventAlarmPriority, eventAlarmClass, eventEvent, indexAB, indexRack
                 }
            STATUS current
            DESCRIPTION 
                "The reflected power increased the fault threshold."
            ::= { eventsTxV2 323 }

        
        txRackProbeNotCalibrated NOTIFICATION-TYPE
            OBJECTS { eventAlarmPriority, eventAlarmClass, eventEvent, indexAB, indexRack
                 }
            STATUS current
            DESCRIPTION 
                "At least one probe is not calibrated."
            ::= { eventsTxV2 330 }

        
        txRackTemperatureWarning NOTIFICATION-TYPE
            OBJECTS { eventAlarmPriority, eventAlarmClass, eventEvent, indexAB, indexRack
                 }
            STATUS current
            DESCRIPTION 
                "Rack temperature exceeded the warning threshold."
            ::= { eventsTxV2 331 }

        
        txRackOvervoltProtectWarning NOTIFICATION-TYPE
            OBJECTS { eventAlarmPriority, eventAlarmClass, eventEvent, indexAB, indexRack
                 }
            STATUS current
            DESCRIPTION 
                "Overvoltage protection is out of order."
            ::= { eventsTxV2 335 }

        
        txAmpSumFault NOTIFICATION-TYPE
            OBJECTS { eventAlarmPriority, eventAlarmClass, eventEvent, indexAB, indexRack, 
                indexAmplifier }
            STATUS current
            DESCRIPTION 
                "The designated amplifier signals summary fault."
            ::= { eventsTxV2 400 }

        
        txAmpSumWarning NOTIFICATION-TYPE
            OBJECTS { eventAlarmPriority, eventAlarmClass, eventEvent, indexAB, indexRack, 
                indexAmplifier }
            STATUS current
            DESCRIPTION 
                "The designated amplifier signals summary warning."
            ::= { eventsTxV2 401 }

        
        txAmpPowerOn NOTIFICATION-TYPE
            OBJECTS { eventAlarmPriority, eventAlarmClass, eventEvent, indexAB, indexRack, 
                indexAmplifier }
            STATUS current
            DESCRIPTION 
                "The designated amplifiers power is on."
            ::= { eventsTxV2 402 }

        
        txAmpDCOk NOTIFICATION-TYPE
            OBJECTS { eventAlarmPriority, eventAlarmClass, eventEvent, indexAB, indexRack, 
                indexAmplifier }
            STATUS current
            DESCRIPTION 
                "The designated amplifiers DC is ok."
            ::= { eventsTxV2 403 }

        
        txAmpACOk NOTIFICATION-TYPE
            OBJECTS { eventAlarmPriority, eventAlarmClass, eventEvent, indexAB, indexRack, 
                indexAmplifier }
            STATUS current
            DESCRIPTION 
                "The designated amplifiers AC is ok."
            ::= { eventsTxV2 404 }

        
        txAmpRfInFail NOTIFICATION-TYPE
            OBJECTS { eventAlarmPriority, eventAlarmClass, eventEvent, indexAB, indexRack, 
                indexAmplifier }
            STATUS current
            DESCRIPTION 
                "The designated amplifier signals RF input fail."
            ::= { eventsTxV2 405 }

        
        txAmpRfFail NOTIFICATION-TYPE
            OBJECTS { eventAlarmPriority, eventAlarmClass, eventEvent, indexAB, indexRack, 
                indexAmplifier }
            STATUS current
            DESCRIPTION 
                "The designated amplifier signals RF fail."
            ::= { eventsTxV2 406 }

        
        txAmpReflectionFault NOTIFICATION-TYPE
            OBJECTS { eventAlarmPriority, eventAlarmClass, eventEvent, indexAB, indexRack, 
                indexAmplifier }
            STATUS current
            DESCRIPTION 
                "The designated amplifier signals a reflection fault."
            ::= { eventsTxV2 407 }

        
        txAmpTemperatureFault NOTIFICATION-TYPE
            OBJECTS { eventAlarmPriority, eventAlarmClass, eventEvent, indexAB, indexRack, 
                indexAmplifier }
            STATUS current
            DESCRIPTION 
                "The designated amplifier signals a temperature fault - temperature is too high."
            ::= { eventsTxV2 408 }

        
        txAmpTransistorFault NOTIFICATION-TYPE
            OBJECTS { eventAlarmPriority, eventAlarmClass, eventEvent, indexAB, indexRack, 
                indexAmplifier }
            STATUS current
            DESCRIPTION 
                "The designated amplifier signals at least one faulty transistor."
            ::= { eventsTxV2 409 }

        
-- events table
        eventsTxTable OBJECT-TYPE
            SYNTAX SEQUENCE OF EventsTxEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventTx 1 }

        
        eventsTxEntry OBJECT-TYPE
            SYNTAX EventsTxEntry
            MAX-ACCESS not-accessible
            STATUS current
            DESCRIPTION
                "An event entry always consists of its indexes
                (used for addressing within redundancy systems) and 3 values:
                - name: an enumerated list of all possible notifications
                - mask: the corresponding mask (enable/disable)
                - priority: the corresponding priority (value in range 0..255)
                - event: the event itself (active/inactive)"
            INDEX { eventTxABIdx, eventTxRackIdx, eventTxAmpIdx, eventTxNameIdx }
            ::= { eventsTxTable 1 }

        
        EventsTxEntry ::=
            SEQUENCE { 
                eventTxABIdx
                    INTEGER,
                eventTxRackIdx
                    Integer32,
                eventTxAmpIdx
                    Integer32,
                eventTxNameIdx
                    EventMaxEntryNumber,
                eventTxName
                    INTEGER,
                eventTxMask
                    EventMask,
                eventTxPriority
                    EventPriority,
                eventTxEvent
                    EventState
             }

        eventTxABIdx OBJECT-TYPE
            SYNTAX INTEGER
                {
                a(1),
                b(2)
                }
            MAX-ACCESS not-accessible
            STATUS current
            DESCRIPTION
                "The value for the module A (exciterA, outputstageA) or 
                B (exciterB, outputstageB) for alarms.
                This is a helper column and therefore not-accessible."
            ::= { eventsTxEntry 1 }

        
        eventTxRackIdx OBJECT-TYPE
            SYNTAX Integer32 (1..10)
            MAX-ACCESS not-accessible
            STATUS current
            DESCRIPTION
                "The number of the designated rack.
                This is a helper column and therefore not-accessible."
            ::= { eventsTxEntry 2 }

        
        eventTxAmpIdx OBJECT-TYPE
            SYNTAX Integer32 (1..10)
            MAX-ACCESS not-accessible
            STATUS current
            DESCRIPTION
                "The number of the designated amplifier.
                This is a helper column and therefore not-accessible."
            ::= { eventsTxEntry 3 }

        
        eventTxNameIdx OBJECT-TYPE
            SYNTAX EventMaxEntryNumber
            MAX-ACCESS not-accessible
            STATUS current
            DESCRIPTION
                "The event number as integer.
                This is a helper column and therefore not-accessible."
            ::= { eventsTxEntry 4 }

        
        eventTxName OBJECT-TYPE
            SYNTAX INTEGER
                {
                txSummaryFault(1),
                txSummaryWarning(2),
                txLocal(3),
                txRfOn(4),
                txRfOk(5),
                txParamSetSubDeviceDiffers(6),
                txParamSetValuesChanged(7),
                txRfLoopProgram(8),
                txRfLoopReserve(9),
                txRfWarning(10),
                txReflectionWarning(11),
                txNetCCUFanFault(12),
                txNetCCUPowerSupply(13),
                txRfFail(14),
                txReflectionFault(15),
                txNetCCUBoardTemperatureFault(16),
                txNetCCUNoConnectionToExcA(17),
                txNetCCUNoConnectionToOstA(18),
                txNetCCUNoConnectionToExcB(19),
                txNetCCUNoConnectionToOstB(20),
                txAutomaticExcReady(21),
                txAutomaticExcChanged(22),
                txAutomaticExcFault(23),
                txAutomaticOstReady(24),
                txAutomaticOstChanged(25),
                txAutomaticOstFault(26),
                txNetCCUBoardTemperatureWarning(27),
                txInternalPowerSupplyWarning(30),
                txExternalPowerSupplyWarning(31),
                txModeSwitchOverStarted(35),
                txModeSwitchOverEnded(36),
                txModeInconsistent(37),
                txModeSwitchOverFailed(38),
                txExcSummaryFault(100),
                txExcSummaryWarning(101),
                txExcLocal(102),
                txExcInputConnect1(105),
                txExcInputConnect2(106),
                txExcInputAsiLocked1(107),
                txExcInputAsiLocked2(108),
                txExcInputActive1(109),
                txExcInputActive2(110),
                txExcRfOn(114),
                txExcRfFail(115),
                txExcOn(116),
                txExcRfLoop(117),
                txExcBoardTemperatureFault(119),
                txExcMute(120),
                txExcNoInput(121),
                txExcReferenceFail(124),
                txExcPPSFail(126),
                txExcOutputOpen(128),
                txExcSelfTest(129),
                txExcTestSignal(130),
                txExcFanWarning(131),
                txExcFanFault(132),
                txExcSFNDelay(134),
                txExcFloModSumWarning(140),
                txExcFloModSumError(141),
                txExcFloModSFNBufferWarning(142),
                txExcFloModError(143),
                txExcFloModMemoryError(144),
                txExcFloModParameterUpdate(145),
                txOstSummaryFault(200),
                txOstSummaryWarning(201),
                txOstRfOn(202),
                txOstRfOk(203),
                txOstNoInput(204),
                txOstRfWarning(205),
                txOstReflectionWarning(206),
                txOstRackWarning(207),
                txOstCoolingWarning(208),
                txOstRfFail(209),
                txOstReflectionFault(210),
                txOstACFault(211),
                txOstCoolingFault(212),
                txOstCommFault(213),
                txRackSumFault(300),
                txRackSumWarning(301),
                txRackOn(302),
                txRackGpiWarning(303),
                txRackFan1Fault(304),
                txRackFan2Fault(305),
                txRackCoolingSumWarning(306),
                txRackAmplifierSumFault(307),
                txRackNoLink(308),
                txRackGpiFault(309),
                txRackTemperatureFault(310),
                txRackACFault(311),
                txRackCoolingSumFault(312),
                txRackTempFaultAbs1(313),
                txRackTempFaultAbs2(314),
                txRackDCFault(315),
                txRackRfOn(318),
                txRackRfOk(319),
                txRackRfWarning(320),
                txRackRfFault(321),
                txRackReflectionWarning(322),
                txRackReflectionFault(323),
                txRackProbeNotCalibrated(330),
                txRackTemperatureWarning(331),
                txRackOvervoltProtectWarning(335),
                txAmpSumFault(400),
                txAmpSumWarning(401),
                txAmpPowerOn(402),
                txAmpDCOk(403),
                txAmpACOk(404),
                txAmpRfInFail(405),
                txAmpRfFail(406),
                txAmpReflectionFault(407),
                txAmpTemperatureFault(408),
                txAmpTransistorFault(409)
                }
            MAX-ACCESS read-only
            STATUS current
            DESCRIPTION
                "The event name as readable integer.
                The enumeration correlates with the notifications under eventsTxV2."
            ::= { eventsTxEntry 5 }

        
        eventTxMask OBJECT-TYPE
            SYNTAX EventMask
            MAX-ACCESS read-write
            STATUS current
            DESCRIPTION
                "See TextualConvention for details."
            ::= { eventsTxEntry 6 }

        
        eventTxPriority OBJECT-TYPE
            SYNTAX EventPriority
            MAX-ACCESS read-write
            STATUS current
            DESCRIPTION
                "See TextualConvention for details."
            ::= { eventsTxEntry 7 }

        
        eventTxEvent OBJECT-TYPE
            SYNTAX EventState
            MAX-ACCESS read-only
            STATUS current
            DESCRIPTION
                "See TextualConvention for details."
            ::= { eventsTxEntry 8 }

        
-- *****************************************************************************
-- **          conformance statements
-- *****************************************************************************
        rsXx8000MediaFloTxConf OBJECT IDENTIFIER ::= { rsXx8000MediaFloTx 5 }

        
        rsXx8000MediaFloTxGroups OBJECT IDENTIFIER ::= { rsXx8000MediaFloTxConf 1 }

        
        groupObjectsGeneral OBJECT-GROUP
            OBJECTS { cmdTxResetSumFault, cmdTxParametersetLoad, cmdTxParametersetSave, cmdTxOperationModeProgram, cmdTxSystemMode, 
                cmdOstMaxOutletTempThreshold, summaryFaultTx, summaryWarningTx, localModeTx, rfOnTx, 
                cmdOstRefVoltageVision, forwardPower, reflectedPower, summaryFaultExcA, summaryFaultOstA, 
                noConnectionExcA, noConnectionOstA, powerSupply, additionalPowerSupply, netCCUNumberOfEntries, 
                netCCULogbookClear, netCCULogbookEntryNbr, netCCULogbookType, netCCULogbookSlope, netCCULogbookMessage, 
                netCCULogbookDateTime, exciterANumberOfEntries, exciterALogbookClear, excALogbookEntryNbr, excALogbookType, 
                excALogbookSlope, excALogbookMessage, excALogbookDateTime, outputstageANumberOfEntries, outputstageALogbookClear, 
                ostALogbookEntryNbr, ostALogbookType, ostALogbookSlope, ostALogbookMessage, ostALogbookDateTime, 
                logbookFrameNetCCU, logbookFrameExciterA, logbookFrameOutputstageA, ostRackInletTemperature, ostRackOutletTemperature, 
                ostRackAuxPowerSupply }
            STATUS current
            DESCRIPTION 
                "Group for general objects."
            ::= { rsXx8000MediaFloTxGroups 1 }

        
        groupObjectsDualDrive OBJECT-GROUP
            OBJECTS { cmdTxOperationModeReserve, cmdTxOpModeExcAutomatic, cmdTxPreselectExciter, cmdTxDelayTimeExcAutomatic, summaryFaultExcB, 
                exciterAutomaticReady, exciterAutomaticChanged, exciterAutomaticFault, noConnectionExcB, activeExcA, 
                activeExcB, exciterBNumberOfEntries, exciterBLogbookClear, excBLogbookEntryNbr, excBLogbookType, 
                excBLogbookSlope, excBLogbookMessage, excBLogbookDateTime, logbookFrameExciterB }
            STATUS current
            DESCRIPTION 
                "Group for objects in case of DualDrive."
            ::= { rsXx8000MediaFloTxGroups 2 }

        
        groupObjectsPowerReserve OBJECT-GROUP
            OBJECTS { cmdTxOpModeOstAutomatic, cmdTxPreselectOutputstage, cmdTxDelayTimeOstAutomatic, summaryFaultOstB, outputstageAutomaticReady, 
                outputstageAutomaticChanged, outputstageAutomaticFault, noConnectionOstB, activeOstA, activeOstB, 
                forwardPowerOstA, reflectedPowerOstA, forwardPowerOstB, reflectedPowerOstB, outputstageBNumberOfEntries, 
                outputstageBLogbookClear, ostBLogbookEntryNbr, ostBLogbookType, ostBLogbookSlope, ostBLogbookMessage, 
                ostBLogbookDateTime, logbookFrameOutputstageB }
            STATUS current
            DESCRIPTION 
                "Group for objects in case of active or passive power reserve."
            ::= { rsXx8000MediaFloTxGroups 3 }

        
        groupObjectsExciter OBJECT-GROUP
            OBJECTS { cmdExcTransmitterId, cmdExcInfrastructureId, cmdExcLocalTimeOffset, cmdExcDstIndicator, cmdExcBandwidth, 
                cmdLoisInsertion, cmdExcPreselectInput, cmdExcAutoswitch, cmdExcTypeOfLossOfInput, cmdExcInputFailDelayTime, 
                cmdExcOnInputFail, cmdExcNetworkGeogrDelay, cmdExcClockRegulation, cmdExcDeviationReset, cmdExcDeviationLimit, 
                cmdExcPosPilotLength, cmdExcNationalLength, cmdExcWideAreaId, cmdExcLocalAreaId, cmdExcClearErrors, 
                cmdExcClearResets, cmdExcCoreReset, cmdExcTestMode, cmdExcFrequency, cmdExcReference, 
                cmdExcOcxoAdjust, cmdExcRfOutput, cmdExcRfOutputRegulation, cmdExcRfOutputManualRfLevel, cmdExcRfOutputAttenuation, 
                cmdExcRfOutputRfSlope, cmdExcRfOutputModulationSlope, cmdExcRfIqAdjustStart, cmdExcRfIqAdjustTestsignal, cmdExcRfIqAdjustBiasCoarseI, 
                cmdExcRfIqAdjustBiasCoarseQ, cmdExcRfIqAdjustBiasFineI, cmdExcRfIqAdjustBiasFineQ, cmdExcRfIqAdjustGainI, cmdExcRfIqAdjustGainQ, 
                cmdExcRfIqAdjustPhase, cmdExcMuteOnPPSFail, cmdExcMuteOnReferenceFail, cmdExcRefFailDelayTime, cmdExcPidWOIS, 
                cmdExcPidWCC, cmdExcPidWCON, cmdExcPidLOIS, cmdExcPidLCC, cmdExcPidLCON, 
                excInputName, excInputConnected, excInputAsiLocked, excInputActive, excInputPacketRate, 
                excStatusRfOutputAgcRegulation, excStatusRfIqAdjustAuto, excStatusRfIqAdjustLO1Frequency, excStatusNominalPower, excStatusVSWR, 
                excStatusAmplifierControl, excStatusSsfArrivalTime, excStatusTransmitterDelay, excStatusTimeDeviation, excStatusLocalLength, 
                excStatusFrameLength, excStatusSuperFrameLength, excStatusCurrentFifoLevel, excStatusTS1OutOfFrameErrors, excStatusTS2OutOfFrameErrors, 
                excStatusOverheadCounter, excStatusDroppedGroups, excStatusDroppedPackets, excStatusCoreResetCounter, excStatusMTISeqErrorCounter, 
                excStatusMTIScheduleErrors, excStatusLastErrorOnPacketSeq, excStatusLastErrorOnPacketID, excStatusPacketRateWOIS, excStatusPacketRateWCC, 
                excStatusPacketRateWCON, excStatusPacketRateLOIS, excStatusPacketRateLCC, excStatusPacketRateLCON, excPrecLinCorrection, 
                excPrecLinAutomaticADE, excPrecLinMaxAmplitudeRipple, excPrecLinMaxGroupDelayRipple, excPrecLinAmplitudeRipple, excPrecLinGroupDelayRipple, 
                excPrecLinInputLevel, excPrecLinAutomatic, excPrecNonlinCorrection, excPrecNonlinAutomaticADE, excPrecNonlinThresholdShoulders, 
                excPrecNonlinShoulderLeft, excPrecNonlinShoulderRight, excPrecNonlinInputLevel, excPrecNonlinAutomatic, excPrecExtendedGroupDelay, 
                excStatusFailDelay, cmdExcFailDelayMode, cmdExcOutputPower, cmdExcRfWarningLimit, cmdExcRfFailLimit, 
                cmdExcMonitoringOutput }
            STATUS current
            DESCRIPTION 
                "Group for objects of exciter."
            ::= { rsXx8000MediaFloTxGroups 10 }

        
        groupAmpMeasureValues OBJECT-GROUP
            OBJECTS { ostRackAmpI1A, ostRackAmpI2A, ostRackAmpI3A, ostRackAmpI4A, ostRackAmpI1B, 
                ostRackAmpI2B, ostRackAmpI3B, ostRackAmpI4B, ostRackAmpIDrv, ostRackAmpUDc, 
                ostRackAmpIDc, ostRackAmpUDcControl, ostRackAmpUReg, ostRackAmpPowerA, ostRackAmpPowerB, 
                ostRackAmpPowerOut, ostRackAmpPowerReflection, ostRackAmpPowerReference, ostRackAmpDeltaPhase, ostRackAmpCmdDeltaPhase
                 }
            STATUS current
            DESCRIPTION 
                "Group for objects of amplifier measure values."
            ::= { rsXx8000MediaFloTxGroups 20 }

        
        groupEventsAmplifier NOTIFICATION-GROUP
            NOTIFICATIONS { txAmpSumFault, txAmpSumWarning, txAmpPowerOn, txAmpDCOk, txAmpACOk, 
                txAmpRfInFail, txAmpRfFail, txAmpReflectionFault, txAmpTemperatureFault, txAmpTransistorFault
                 }
            STATUS current
            DESCRIPTION 
                "events from the amplifier (medium/high power only)"
            ::= { rsXx8000MediaFloTxGroups 21 }

        
        groupObjectsProductInfo OBJECT-GROUP
            OBJECTS { prodInfoModuleName, prodInfoSerialNumber, prodInfoIdentNumberSW, prodInfoVersionNumberSW, prodInfoIdentNumberHW, 
                prodInfoVersionNumberHW, productInfoProductDateHW, productInfoFloModVersion }
            STATUS current
            DESCRIPTION 
                "Group for productInfoTable."
            ::= { rsXx8000MediaFloTxGroups 25 }

        
        groupObjectsRfProbes OBJECT-GROUP
            OBJECTS { rfProbesNetCCURfProbe1, rfProbesNetCCURfProbe2, rfProbesAntFwdNominal, rfProbesAntFwdWarningLimit, rfProbesAntFwdFailLimit, 
                rfProbesAntFwdDelayTimeRfFail, rfProbesAntFwdSetOffset, rfProbesAntFwdSetGain, rfProbesAntReflWarningLimit, rfProbesAntReflSetOffset, 
                rfProbesAntReflSetGain, rfProbesOstFwdNominal, rfProbesOstFwdWarningLimit, rfProbesOstFwdFailLimit, rfProbesOstFwdDelayTimeRfFail, 
                rfProbesOstFwdSetOffset, rfProbesOstFwdSetGain, rfProbesOstReflWarningLimit, rfProbesOstReflSetOffset, rfProbesOstReflSetGain
                 }
            STATUS current
            DESCRIPTION 
                "Group for rfProbesTable."
            ::= { rsXx8000MediaFloTxGroups 26 }

        
        groupObjectsRackTable OBJECT-GROUP
            OBJECTS { amplifiersPerRack, rackRfEventSignalling, rackGeneralPurposeInput, rfProbePresent, rfProbeConfigurationNominalValue, 
                rfProbeThresholdRfFailLimit, rfProbeThresholdTimeoutRfFailCtr, rfProbeThresholdWarningLimit, rfProbeCalibrationGain, rfProbeCalibrationOffset, 
                rfProbeCalibrationSetGain, rfProbeCalibrationSetOffset, rfProbeMeasuredValue }
            STATUS current
            DESCRIPTION 
                "Group for rackTable"
            ::= { rsXx8000MediaFloTxGroups 27 }

        
        groupIndependentRacks OBJECT-GROUP
            OBJECTS { rackReferenceVoltage, amplifiersPowerSupply, rackOnOff }
            STATUS current
            DESCRIPTION 
                "object types that are relevant for NX variants with independent racks only"
            ::= { rsXx8000MediaFloTxGroups 28 }

        
        groupObjectsRE OBJECT-GROUP
            OBJECTS { summaryFaultExcA }
            STATUS current
            DESCRIPTION 
                "object types for the re-equip kit"
            ::= { rsXx8000MediaFloTxGroups 29 }

        
        groupDummyLoadRF OBJECT-GROUP
            OBJECTS { rfProbesDLFwdNominal, rfProbesDLFwdWarningLimit, rfProbesDLFwdFailLimit, rfProbesDLFwdDelayTimeRfFail, rfProbesDLFwdSetOffset, 
                rfProbesDLFwdSetGain, rfProbesDLReflWarningLimit, rfProbesDLReflSetOffset, rfProbesDLReflSetGain }
            STATUS current
            DESCRIPTION 
                "This group includes all object types regarding probes from dummy load.
                The object types in this group are defined only when a dummy load measure point exists.
                This can occur in reserve concept active reserve only.
                "
            ::= { rsXx8000MediaFloTxGroups 30 }

        
        groupObjectsSingleEnded OBJECT-GROUP
            OBJECTS { cmdTxRfSwitch }
            STATUS current
            DESCRIPTION 
                "Group for objects in case of SingleTx or DualDrive."
            ::= { rsXx8000MediaFloTxGroups 31 }

        
        groupObjectsSx801Amplifier OBJECT-GROUP
            OBJECTS { sx801AmpRfOut, sx801AmpRfIn, sx801AmpReflection, sx801AmpOn, sx801AmpAC, 
                sx801AmpCommunication, sx801AmpTransistor, sx801AmpDriver, sx801AmpTemperature, sx801AmpBlower, 
                sx801AmpRegulation, sx801AmpUpdate, sx801Supply1Temperature, sx801Supply2Temperature, sx801SupplyRTemperature, 
                sx801Supply1DC, sx801Supply2DC, sx801SupplyRDC, sx801AmpValueI1, sx801AmpValueI2, 
                sx801AmpValueI3, sx801AmpValueI4, sx801AmpValueIPre, sx801AmpValueIDrv1, sx801AmpValueIDrv2, 
                sx801AmpValuePowerOut, sx801AmpValueReflection, sx801AmpValueVRef, sx801AmpValueVReg, sx801AmpValueTemperature, 
                sx801AmpValueMonAtt, sx801AmpValueVAux1, sx801AmpValueVAux2, sx801Supply1ValuePwr, sx801Supply2ValuePwr, 
                sx801Supply1ValueDc, sx801Supply2ValueDc }
            STATUS current
            DESCRIPTION 
                "Objects for Sx801/SA801 amplifier status."
            ::= { rsXx8000MediaFloTxGroups 32 }

        
        groupObsoleted OBJECT-GROUP
            OBJECTS { cmdTxParametersetReSave, rfProbeConfigurationLabel }
            STATUS obsolete
            DESCRIPTION 
                "This group includes all deprecated and obsoleted objects."
            ::= { rsXx8000MediaFloTxGroups 99 }

        
        groupEventsGeneral NOTIFICATION-GROUP
            NOTIFICATIONS { txSummaryFault, txSummaryWarning, txLocal, txRfOn, txRfOk, 
                txParamSetValuesChanged, txRfLoopProgram, txRfWarning, txReflectionWarning, txNetCCUFanFault, 
                txNetCCUPowerSupply, txRfFail, txReflectionFault, txNetCCUNoConnectionToExcA, txNetCCUNoConnectionToOstA, 
                txModeSwitchOverStarted, txModeSwitchOverEnded, txModeInconsistent, txModeSwitchOverFailed, txOstSummaryFault, 
                txOstSummaryWarning, txOstRfOn, txOstRfOk, txOstNoInput, txOstRfWarning, 
                txOstReflectionWarning, txOstRackWarning, txOstCoolingWarning, txOstRfFail, txOstReflectionFault, 
                txOstACFault, txOstCoolingFault, txOstCommFault, txRackSumFault, txRackSumWarning, 
                txRackOn, txRackGpiWarning, txRackFan1Fault, txRackFan2Fault, txRackCoolingSumWarning, 
                txRackAmplifierSumFault, txRackNoLink, txRackGpiFault, txRackTemperatureFault, txRackACFault, 
                txRackCoolingSumFault, txRackTempFaultAbs1, txRackTempFaultAbs2, txRackDCFault, txRackRfOn, 
                txRackRfOk, txRackRfWarning, txRackRfFault, txRackReflectionWarning, txRackReflectionFault, 
                txRackProbeNotCalibrated, txRackTemperatureWarning, txRackOvervoltProtectWarning, txNetCCUBoardTemperatureWarning }
            STATUS current
            DESCRIPTION 
                "Group for general events."
            ::= { rsXx8000MediaFloTxGroups 100 }

        
        groupEventsDualDrive NOTIFICATION-GROUP
            NOTIFICATIONS { txRfLoopReserve, txNetCCUNoConnectionToExcB, txAutomaticExcReady, txAutomaticExcChanged, txAutomaticExcFault
                 }
            STATUS current
            DESCRIPTION 
                "Group for events in case of DualDrive."
            ::= { rsXx8000MediaFloTxGroups 101 }

        
        groupEventsPowerReserve NOTIFICATION-GROUP
            NOTIFICATIONS { txNetCCUNoConnectionToOstB, txAutomaticOstReady, txAutomaticOstChanged, txAutomaticOstFault }
            STATUS current
            DESCRIPTION 
                "Group for events in case of active or passive power reserve."
            ::= { rsXx8000MediaFloTxGroups 102 }

        
        groupAlarmAdditionalPowerSupply NOTIFICATION-GROUP
            NOTIFICATIONS { txInternalPowerSupplyWarning, txExternalPowerSupplyWarning }
            STATUS current
            DESCRIPTION 
                "Events that are available only when additionalPowerSupply is true."
            ::= { rsXx8000MediaFloTxGroups 103 }

        
        groupObjsAdditionalPowerSupply OBJECT-GROUP
            OBJECTS { internalPowerSupply, externalPowerSupply }
            STATUS current
            DESCRIPTION 
                "Objects that are available only when additionalPowerSupply is true."
            ::= { rsXx8000MediaFloTxGroups 104 }

        
        groupEventsExciter NOTIFICATION-GROUP
            NOTIFICATIONS { txExcSummaryFault, txExcSummaryWarning, txExcInputConnect1, txExcInputConnect2, txExcInputAsiLocked1, 
                txExcInputAsiLocked2, txExcInputActive1, txExcInputActive2, txExcRfOn, txExcRfFail, 
                txExcOn, txExcRfLoop, txExcBoardTemperatureFault, txExcMute, txExcNoInput, 
                txExcReferenceFail, txExcPPSFail, txExcOutputOpen, txExcSelfTest, txExcTestSignal, 
                txExcFanWarning, txExcFanFault, txExcSFNDelay, txExcFloModSumWarning, txExcFloModSumError, 
                txExcFloModSFNBufferWarning, txExcFloModError, txExcFloModMemoryError, txExcFloModParameterUpdate, txExcLocal
                 }
            STATUS current
            DESCRIPTION 
                "Group for events of exciter."
            ::= { rsXx8000MediaFloTxGroups 105 }

        
        groupObjectsControlExciter OBJECT-GROUP
            OBJECTS { cmdTxOperationModeReserve, cmdTxOpModeExcAutomatic, cmdTxDelayTimeExcAutomatic, summaryFaultExcB, exciterAutomaticReady, 
                exciterAutomaticChanged, exciterAutomaticFault, noConnectionExcB, activeExcB, cmdTxProgramExciterPrio, 
                cmdTxChangeOver, cmdTxSwitchPosition }
            STATUS current
            DESCRIPTION 
                "additional objects in case Sx801 is control exciter"
            ::= { rsXx8000MediaFloTxGroups 106 }

        
        groupEventTable OBJECT-GROUP
            OBJECTS { eventTxName, eventTxMask, eventTxPriority, eventTxEvent }
            STATUS current
            DESCRIPTION 
                "Group for all objects of event table."
            ::= { rsXx8000MediaFloTxGroups 400 }

        
        groupAlarmObsoleted NOTIFICATION-GROUP
            NOTIFICATIONS { txParamSetSubDeviceDiffers, txNetCCUBoardTemperatureFault }
            STATUS obsolete
            DESCRIPTION 
                "obsoleted or deprecated alarms."
            ::= { rsXx8000MediaFloTxGroups 500 }

        
        rsXx8000MediaFloTxCompl OBJECT IDENTIFIER ::= { rsXx8000MediaFloTxConf 2 }

        
        rsXx8000MFloSingleTx MODULE-COMPLIANCE
            STATUS current
            DESCRIPTION 
                "Reserve concept SingleTransmitter."
            MODULE -- this module
                MANDATORY-GROUPS { groupObjectsGeneral, groupObjectsExciter, groupObjectsProductInfo, groupObjectsRfProbes, groupObjectsRackTable, 
                    groupEventsGeneral, groupEventsExciter, groupEventTable, groupObjectsSingleEnded }
                GROUP groupIndependentRacks
                    DESCRIPTION 
                        "for variant with independent racks only"
                GROUP groupAlarmAdditionalPowerSupply
                    DESCRIPTION 
                        "only when additionalPowerSupply is true"
                OBJECT cmdOstRefVoltageVision
                    MIN-ACCESS not-accessible
                    DESCRIPTION 
                        "not accessible in variant with independent racks"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
            ::= { rsXx8000MediaFloTxCompl 1 }

        
        rsXx8000MFloDualDrive MODULE-COMPLIANCE
            STATUS current
            DESCRIPTION 
                "Reserve concept DualDrive."
            MODULE -- this module
                MANDATORY-GROUPS { groupObjectsGeneral, groupObjectsDualDrive, groupObjectsExciter, groupObjectsProductInfo, groupObjectsRfProbes, 
                    groupObjectsRackTable, groupEventsGeneral, groupEventsDualDrive, groupEventsExciter, groupEventTable, 
                    groupObjectsSingleEnded }
                GROUP groupIndependentRacks
                    DESCRIPTION 
                        "for variant with independent racks only"
                GROUP groupAlarmAdditionalPowerSupply
                    DESCRIPTION 
                        "only when additionalPowerSupply is true"
                OBJECT cmdOstRefVoltageVision
                    MIN-ACCESS not-accessible
                    DESCRIPTION 
                        "not accessible in variant with independent racks"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
            ::= { rsXx8000MediaFloTxCompl 2 }

        
        rsXx8000MFloActiveReserve MODULE-COMPLIANCE
            STATUS current
            DESCRIPTION 
                "Reserve concept Active Power Reserve."
            MODULE -- this module
                MANDATORY-GROUPS { groupObjectsGeneral, groupObjectsDualDrive, groupObjectsPowerReserve, groupObjectsExciter, groupObjectsProductInfo, 
                    groupObjectsRfProbes, groupObjectsRackTable, groupEventsGeneral, groupEventsDualDrive, groupEventsPowerReserve, 
                    groupEventsExciter, groupEventTable }
                GROUP groupIndependentRacks
                    DESCRIPTION 
                        "for variant with independent racks only"
                GROUP groupAlarmAdditionalPowerSupply
                    DESCRIPTION 
                        "only when additionalPowerSupply is true"
                OBJECT cmdOstRefVoltageVision
                    MIN-ACCESS not-accessible
                    DESCRIPTION 
                        "not accessible in variant with independent racks"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
                GROUP groupDummyLoadRF
                    DESCRIPTION 
                        "only when a dummy load measure point exists"
            ::= { rsXx8000MediaFloTxCompl 3 }

        
        rsXx8000MFloPassiveReserve MODULE-COMPLIANCE
            STATUS current
            DESCRIPTION 
                "Reserve concept Passive Power Reserve."
            MODULE -- this module
                MANDATORY-GROUPS { groupObjectsGeneral, groupObjectsDualDrive, groupObjectsPowerReserve, groupObjectsExciter, groupObjectsProductInfo, 
                    groupObjectsRfProbes, groupObjectsRackTable, groupEventsGeneral, groupEventsDualDrive, groupEventsPowerReserve, 
                    groupEventsExciter, groupEventTable }
                GROUP groupIndependentRacks
                    DESCRIPTION 
                        "for variant with independent racks only"
                GROUP groupAlarmAdditionalPowerSupply
                    DESCRIPTION 
                        "only when additionalPowerSupply is true"
                OBJECT cmdOstRefVoltageVision
                    MIN-ACCESS not-accessible
                    DESCRIPTION 
                        "not accessible in variant with independent racks"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
            ::= { rsXx8000MediaFloTxCompl 4 }

        
        rsXx8000MFloExciterOnly MODULE-COMPLIANCE
            STATUS current
            DESCRIPTION 
                "MediaFLO Exciter of 8000 series in a 7000 environment
                or
                Sx801 program exciter"
            MODULE -- this module
                MANDATORY-GROUPS { groupObjectsExciter, groupObjectsProductInfo, groupEventsExciter, groupObjectsSx801Amplifier, groupEventTable, 
                    groupObjectsRE }
            ::= { rsXx8000MediaFloTxCompl 5 }

        
        rsXx8000MFloSx801ControlExciter MODULE-COMPLIANCE
            STATUS current
            DESCRIPTION 
                "Sx801 as control exciter"
            MODULE -- this module
                MANDATORY-GROUPS { groupObjectsGeneral, groupObjectsExciter, groupObjectsProductInfo, groupEventsGeneral, groupEventsExciter, 
                    groupObjectsSx801Amplifier, groupEventTable, groupObjectsControlExciter }
            ::= { rsXx8000MediaFloTxCompl 6 }

        
    
    END
