-- *****************************************************************************
-- *****************************************************************************
-- **
-- **  COPYRIGHT      (c) 2006 Rohde & Schwarz GmbH & Co. KG
-- **                          Muehldorfstrasse 15
-- **    R & S                 D-81671 Muenchen
-- **
-- *****************************************************************************
-- **
-- **  MODULE         RS-XX8000-DVB-TX-MIB
-- **  
-- **  DESCRIPTION    Rohde & Schwarz SNMP
-- **
-- **  HISTORY
-- **
-- **  2006-11-28 hue - initial version
-- **  2007-03-08 hue - added low power, sorted groups
-- **  2007-07-11 sr  - added cmdTxDelayTimeExcAutomatic, 
-- **                         cmdTxDelayTimeOstAutomatic,
-- **                         cmdExcTypeLossOfInput, 
-- **                         cmdOstMaxOutletTempThreshold,
-- **                         forwardPowerOstA, forwardPowerOstB,
-- **                         reflectedPowerOstA, reflectedPowerOstB,
-- **                   renamed ostRackTable to ostTable,
-- **                           ostRackEntry to ostEntry,
-- **                   added ostRackAmp... nodes
-- **                   added productInfoTable, rfProbesTable
-- **                   defined alarm class for txAutomaticExcChanged,
-- **                                           txAutomaticOstChanged
-- **                   added groupProductInfo, groupAmpMeasureValues,
-- **                         groupRfProbes, groupSingleTxLPNoNetCCU,
-- **                         groupAlarmSingleTxLPNoNetCCU, 
-- **                         rsXx8000DVBSingleTxLPNoNetCCU
-- **  2007-08-09 kp - expansion of ProductInfoTable
-- **  2007-09-10 sr - remove forwardPowerOstA and reflectedPowerOstA
-- **                  from groupSingleTxMP and groupDualDriveMP
-- **  2007-12-07 sr - cmdExcSFNStaticDelay to FloatingPoint
-- **                  cmdExcSFNDeviationTime changed range
-- **                - new exciter commands for RfOutput, RfIqAdjust and Precorrection
-- **                - rename prodInfoDeviceNameIdx to prodInfoModuleIdx and
-- **                         prodInfoDeviceName to prodInfoModuleName
-- **                  using TC ProdInfoModuleNameTv with a new value for netCCU 
-- **                - rename txNetCCUBoardTemperatureWarning to
-- **                         txNetCCUBoardTemperatureFault
-- **                - new OBJECT-GROUPs groupExciterStatus and groupExciterPrecorrection
-- **  2008-03-31 sr  - change range of cmdTxDelayTimeExcAutomatic and 
-- **                   cmdTxDelayTimeOstAutomatic to 1..60
-- **             ks - SLx extension
-- **  2008-05-05 sr - cmdExcReferenceSource with value internGPS
-- **  2008-06-11 ks - cmdExcInput1Source, cmdExcInput2Source added
-- **  2008-07-23 sr - new SLx parameters: cmdExcTimeScheduler, configurationTable and
-- **                                      timeSchedulerTable
-- **                - new SFN Delay parameters in exciterStatusTable
-- **  2008-08-26 ks - rfProbesNetCCURfProbe1, rfProbesNetCCURfProbe2 read-only
-- **                          - cmdTxParametersetReSave obsolete
-- **  2008-07-29 hu - changed TextualConvention for Exciter LogbookEntryMessages
-- **  2008-09-10 sr - new rackTable
-- **                - new txRackRfWarning, txRackRfFault, txRackReflectionWarning,
-- **                      txRackReflectionFault
-- **                - new groupIndependentRacks 
-- **  2008-10-08 sr - cmdExcFrequency and configFrequency range up to 1500 MHz
-- **  2008-10-23 ks - new: cmdExcInpAutoReadyAfterChangeOv,
-- **                       txExcInputAutomaticSwitchReady, txExcInputAutomaticChangedOver
-- **  2008-12-12 sr - rfProbeConfigurationLabel obsolete
-- **                - txRackExtCoolingWarning renamed to txRackGpiWarning
-- **                - txRackExtCoolingFault renamed to txRackGpiFault
-- **  2009-01-06 sr - rfProbeCalibrationSetGain, rfProbeCalibrationSetOffset
-- **  2009-02-12 sr - InputSource with value tp
-- **                - new groupExcCommandsAdditional
-- **  2009-03-30 ks - txRackProbeNotCalibrated added
-- **                - txParamSetSubDeviceDiffers obsoleted
-- **  2009-05-28 ks -information for additional (external) power supply added
-- **                - txRackRfOn, txRackRfOk, txRackTemperatureWarning added
-- **  2009-06-17 ks - object groups, notification groups and
-- **                  module compliances reorganized
-- **  2009-06-26 ks - consideration of face-lift configuration in module compliances
-- **                - measured values for power supply added
-- **                - cmdExcInputAutoSwitch obsoleted
-- **                - conditional groupDummyLoadRF added
-- **  2009-07-16 ks - additional values for reserve concept 'backup exciter'
-- **  2009-09-10 ks - cmdTxSystemMode added
-- **                - traps for TX mode switch over added
-- **  2009-10-08 ks - txRackOvervoltProtectWarning added
-- **                - cmdExcInputAutoSwitch obsoleted
-- **  2009-11-13 ks - ostRackAmpDeltaPhase, ostRackAmpCmdDeltaPhase added
-- **  2009-11-26 ks - cmdExcRfFailLimit, cmdExcRfWarningLimit added
-- **  2009-11-27 ks - cmdExcInputFailDelayTime added
-- **  2009-11-30 ks - cmdExcMonitoringOutput, cmdExcOcxoAdjust added
-- **  2009-12-01 ks - configRxFrequency, configInputSource added
-- **  2009-12-04 ks - configuration2Table added
-- **  2009-12-07 ks - excStatusNominalPower added
-- **  2009-12-18 ks - txExcRfOk added
-- **  2010-01-12 ks - excStatusVSWR added
-- **  2010-01-29 ks - txNetCCUBoardTemperatureFault deprecated,
-- **                  txNetCCUBoardTemperatureWarning added
-- **  2010-02-02 ks - cmdExcExpectInputReserve, txExcInputReseveMissing added
-- **  2010-20-04 ks - cmdExcMuteCondition added
-- **  2010-05-21 ks - cmdTxRfSwitch added
-- **  2010-10-13 ks - cmdExcEnablePcrReset, cmdExcTimeForDailyPcrReset added
-- **  2010-12-02 ks - excStatusAmplifierControl, excStatusReqDataRateHP,
-- **                  excStatusReqDataRateLP added
-- **  2011-02-28 ks - Amplifier status for Sx801 added.
-- **  2011-05-12 ks - cmdExcFailDelayMode, excStatusFailDelay added
-- **  2012-09-03 ks - sx801AmplifierTable measured values added
-- **  2012-11-01 ks - Hierarchical input is no longer supported.
-- *****************************************************************************
-- *****************************************************************************

    RS-XX8000-DVB-TX-MIB DEFINITIONS ::= BEGIN
 
        IMPORTS
            rsXx8000, eventAlarmPriority, eventAlarmClass, eventEvent, indexAB, 
            indexRack, indexAmplifier, rsXx8000MibModule, ReadableString, FloatingPoint, 
            LogbookEntryMessagesNetCCU, LogbookEntryMessagesOST, LogbookEntrySlope, EventMaxEntryNumber, SwitchOnOff, 
            Trigger, EventMask, EventPriority, EventState, EventClass, 
            IndexRack, IndexAmplifier, IndexAB, LogbookMaxEntryNumber, ProdInfoModuleNameTv, 
            EqualizerCalibrationState, TvStandard, LogbookEntryMessagesExcTv, InputSource, TimeOfDay, 
            Sx801AmplifierState, FailDelayMode, FailDelayStatus            
                FROM RS-XX8000-COMMON-MIB            
            OBJECT-GROUP, MODULE-COMPLIANCE, NOTIFICATION-GROUP            
                FROM SNMPv2-CONF            
            Integer32, OBJECT-TYPE, MODULE-IDENTITY, OBJECT-IDENTITY, NOTIFICATION-TYPE            
                FROM SNMPv2-SMI            
            DateAndTime, TruthValue, RowStatus            
                FROM SNMPv2-TC;
    
    
        rsXx8000DvbTxMibModule MODULE-IDENTITY 
            LAST-UPDATED "201509101100Z"		-- September 10, 2015 at 11:00 GMT
            ORGANIZATION 
                "Rohde&Schwarz GmbH & Co. KG"
            CONTACT-INFO 
                "Torsten Huebscher
                Department 7TS2
                Broadcasting Division
                Muehldorfstrasse 15
                81671 Munich, Germany
                torsten.huebscher@rohde-schwarz.com"
            DESCRIPTION 
                "This MIB defines transmitting systems from Rohde & Schwarz.
                
                Use this MIB if your system meets the following requirements:
                - series XX8000 (NetCCU800),
                - DVB,
                - transmitter reserve concept SingleTx, DualDrive,
                  Active Reserve or Passive Reserve.
                
                The following MIBs are related to this:
                - RS-COMMON-MIB         - mandatory for this MIB
                - RS-XX8000-COMMON-MIB  - mandatory for this MIB"
            REVISION "201509101100Z"		-- September 10, 2015 at 11:00 GMT
            DESCRIPTION 
                "Hierarchical input always returns noHierarchy(1)
                "
            REVISION "201211010800Z"		-- November 01, 2012 at 08:00 GMT
            DESCRIPTION 
                "Hierarchical input is no longer supported."
            REVISION "201209030800Z"		-- September 03, 2012 at 08:00 GMT
            DESCRIPTION 
                "sx801AmplifierTable measured values added"
            REVISION "201105120800Z"		-- May 12, 2011 at 08:00 GMT
            DESCRIPTION 
                "cmdExcFailDelayMode, excStatusFailDelay added"
            REVISION "201102280800Z"		-- February 28, 2011 at 08:00 GMT
            DESCRIPTION 
                "Amplifier status for Sx801 added."
            REVISION "201012020800Z"		-- December 02, 2010 at 08:00 GMT
            DESCRIPTION 
                "excStatusAmplifierControl, excStatusReqDataRateHP,
                excStatusReqDataRateLP added"
            REVISION "201010130800Z"		-- October 13, 2010 at 08:00 GMT
            DESCRIPTION 
                "cmdExcEnablePcrReset, cmdExcTimeForDailyPcrReset added"
            REVISION "201005210800Z"		-- May 21, 2010 at 08:00 GMT
            DESCRIPTION 
                "cmdTxRfSwitch added"
            REVISION "201004160800Z"		-- April 16, 2010 at 08:00 GMT
            DESCRIPTION 
                "cmdExcMuteCondition added"
            REVISION "201002020800Z"		-- February 02, 2010 at 08:00 GMT
            DESCRIPTION 
                "cmdExcExpectInputReserve, txExcInputReseveMissing added"
            REVISION "201001290800Z"		-- January 29, 2010 at 08:00 GMT
            DESCRIPTION 
                "txNetCCUBoardTemperatureFault deprecated,
                txNetCCUBoardTemperatureWarning added"
            REVISION "201001120800Z"		-- January 12, 2010 at 08:00 GMT
            DESCRIPTION 
                "excStatusVSWR added"
            REVISION "200912180800Z"		-- December 18, 2009 at 08:00 GMT
            DESCRIPTION 
                "txExcRfOk added"
            REVISION "200911260800Z"		-- November 26, 2009 at 08:00 GMT
            DESCRIPTION 
                "cmdExcRfFailLimit, cmdExcRfWarningLimit,
                cmdExcInputFailDelayTime, cmdExcMonitoringOutput,
                cmdExcOcxoAdjust, configRxFrequency,
                configInputSource, configuration2Table,
                excStatusNominalPower  added"
            REVISION "200911130800Z"		-- November 13, 2009 at 08:00 GMT
            DESCRIPTION 
                "ostRackAmpDeltaPhase, ostRackAmpCmdDeltaPhase added"
            REVISION "200910080800Z"		-- October 08, 2009 at 08:00 GMT
            DESCRIPTION 
                "txRackOvervoltProtectWarning added
                cmdExcInputAutoSwitch obsoleted"
            REVISION "200909100800Z"		-- September 10, 2009 at 08:00 GMT
            DESCRIPTION 
                "cmdTxSystemMode added
                traps for TX mode switch over added"
            REVISION "200907160800Z"		-- July 16, 2009 at 08:00 GMT
            DESCRIPTION 
                "additional values for reserve concept 'backup exciter'"
            REVISION "200906260800Z"		-- June 26, 2009 at 08:00 GMT
            DESCRIPTION 
                "consideration of face-lift configuration in module compliances,
                measured values for power supply added,
                cmdExcInputAutoSwitch obsoleted,
                conditional groupDummyLoadRF added"
            REVISION "200906170900Z"		-- June 17, 2009 at 09:00 GMT
            DESCRIPTION 
                "object groups, notification groups and module compliances reorganized"
            REVISION "200905280900Z"		-- May 28, 2009 at 09:00 GMT
            DESCRIPTION 
                "information for additional (external) power supply added
                txRackRfOn, txRackRfOk, txRackTemperatureWarning added"
            REVISION "200903300900Z"		-- March 30, 2009 at 09:00 GMT
            DESCRIPTION 
                "txRackProbeNotCalibrated added
                txParamSetSubDeviceDiffers obsoleted"
            REVISION "200902121500Z"		-- February 12, 2009 at 15:00 GMT
            DESCRIPTION 
                "- InputSource with value tp
                - new groupExcCommandsAdditional"
            REVISION "200901290900Z"		-- January 29, 2009 at 09:00 GMT
            DESCRIPTION 
                "MODULE COMPLIANCE rsXx8000DVBReEquip"
            REVISION "200901061600Z"		-- January 06, 2009 at 16:00 GMT
            DESCRIPTION 
                "rfProbeCalibrationSetGain, rfProbeCalibrationSetOffset"
            REVISION "200812121430Z"		-- December 12, 2008 at 14:30 GMT
            DESCRIPTION 
                "rfProbeConfigurationLabel obsolete
                txRackExtCoolingWarning renamed to txRackGpiWarning
                txRackExtCoolingFault renamed to txRackGpiFault"
            REVISION "200810230800Z"		-- October 23, 2008 at 08:00 GMT
            DESCRIPTION 
                "cmdExcInpAutoReadyAfterChangeOv
                txExcInputAutomaticSwitchReady, txExcInputAutomaticChangedOver"
            REVISION "200810081030Z"		-- October 08, 2008 at 10:30 GMT
            DESCRIPTION 
                "cmdExcFrequency and configFrequency range up to 1500 MHz"
            REVISION "200809101500Z"		-- September 10, 2008 at 15:00 GMT
            DESCRIPTION 
                "new rackTable
                new txRackRfWarning, txRackRfFault, txRackReflectionWarning,
                    txRackReflectionFault
                new groupIndependentRacks"
            REVISION "200808291000Z"		-- August 29, 2008 at 10:00 GMT
            DESCRIPTION 
                "changed TextualConvention for Exciter LogbookEntryMessages"
            REVISION "200808260900Z"		-- August 26, 2008 at 09:00 GMT
            DESCRIPTION 
                "- rfProbesNetCCURfProbe1, rfProbesNetCCURfProbe2 read-only
                - cmdTxParametersetReSave obsolete"
            REVISION "200807231000Z"		-- July 23, 2008 at 10:00 GMT
            DESCRIPTION 
                "- new SLx parameters: cmdExcTimeScheduler, configurationTable and
                                      timeSchedulerTable
                - new SFN Delay parameters in exciterStatusTable"
            REVISION "200805050930Z"		-- May 05, 2008 at 09:30 GMT
            DESCRIPTION 
                "- cmdExcReferenceSource with value internGPS
                - cmdExcInput1Source, cmdExcInput2Source added"
            REVISION "200803311100Z"		-- March 31, 2008 at 11:00 GMT
            DESCRIPTION 
                "- change range of cmdTxDelayTimeExcAutomatic and 
                  cmdTxDelayTimeOstAutomatic to 1..60
                - adds cmdExcTransmitterType, cmdExcOutputPower
                  excPrecUserState, excPrecFactoryState, excPrecRestoreCurrentSettings, excPrecRestoreAllSettings"
            REVISION "200712071700Z"		-- December 07, 2007 at 17:00 GMT
            DESCRIPTION 
                "- cmdExcSFNStaticDelay to FloatingPoint
                  cmdExcSFNDeviationTime changed range
                - new exciter commands for RfOutput, RfIqAdjust and Precorrection
                - rename prodInfoDeviceNameIdx to prodInfoModuleIdx and
                         prodInfoDeviceName to prodInfoModuleName
                  using TC ProdInfoModuleNameTv with a new value for netCCU 
                - rename txNetCCUBoardTemperatureWarning to
                         txNetCCUBoardTemperatureFault
                - new OBJECT-GROUPs groupExciterStatus and groupExciterPrecorrection"
            REVISION "200709101100Z"		-- September 10, 2007 at 11:00 GMT
            DESCRIPTION 
                "remove forwardPowerOstA and reflectedPowerOstA from groupSingleMP and groupDualDriveMP"
            REVISION "200708091400Z"		-- August 09, 2007 at 14:00 GMT
            DESCRIPTION 
                "Expansion of ProductInfoTable"
            REVISION "200707111600Z"		-- July 11, 2007 at 16:00 GMT
            DESCRIPTION 
                "added cmdTxDelayTimeExcAutomatic,
                      cmdTxDelayTimeOstAutomatic,
                      cmdExcTypeLossOfInput,
                      cmdOstMaxOutletTempThreshold,
                      forwardPowerOstA, forwardPowerOstB,
                      reflectedPowerOstA, reflectedPowerOstB,
                renamed ostRackTable to ostTable,
                        ostRackEntry to ostEntry,
                added ostRackAmp... nodes
                added productInfoTable, rfProbesTable
                defined alarm class for txAutomaticExcChanged,
                                        txAutomaticOstChanged
                added groupProductInfo, groupAmpMeasureValues,
                      groupRfProbes, groupSingleTxLPNoNetCCU,
                      groupAlarmSingleTxLPNoNetCCU,
                      rsXx8000DVBSingleTxLPNoNetCCU"
            REVISION "200703081000Z"		-- March 08, 2007 at 10:00 GMT
            DESCRIPTION 
                "- Added LowPower
                - Sorted groups"
            REVISION "200612211000Z"		-- December 21, 2006 at 10:00 GMT
            DESCRIPTION 
                "This is the initial version."
            ::= { rsXx8000MibModule 3 }

        
    
    
--
-- Node definitions
--
    
        rsXx8000DvbTx OBJECT-IDENTITY
            STATUS current
            DESCRIPTION 
                "Xx8000 DVB transmitter."
            ::= { rsXx8000 4 }

        
-- *****************************************************************************
-- **          object definitions
-- *****************************************************************************
        rsXx8000DvbTxObjs OBJECT IDENTIFIER ::= { rsXx8000DvbTx 1 }

        
        commandsTxTable OBJECT-TYPE
            SYNTAX SEQUENCE OF CommandsTxEntry
            MAX-ACCESS not-accessible
            STATUS current
            DESCRIPTION
                "This table contains important commands for the transmitter."
            ::= { rsXx8000DvbTxObjs 1 }

        
        commandsTxEntry OBJECT-TYPE
            SYNTAX CommandsTxEntry
            MAX-ACCESS not-accessible
            STATUS current
            DESCRIPTION
                "An entry for a designated transmitter and device."
            INDEX { cmdDeviceIdx }
            ::= { commandsTxTable 1 }

        
        CommandsTxEntry ::=
            SEQUENCE { 
                cmdTxResetSumFault
                    Trigger,
                cmdTxParametersetLoad
                    Integer32,
                cmdTxParametersetSave
                    Integer32,
                cmdTxParametersetReSave
                    Trigger,
                cmdTxOperationModeProgram
                    SwitchOnOff,
                cmdTxOperationModeReserve
                    SwitchOnOff,
                cmdTxOpModeExcAutomatic
                    SwitchOnOff,
                cmdTxOpModeOstAutomatic
                    SwitchOnOff,
                cmdTxPreselectExciter
                    IndexAB,
                cmdTxPreselectOutputstage
                    INTEGER,
                cmdTxDelayTimeExcAutomatic
                    Integer32,
                cmdTxDelayTimeOstAutomatic
                    Integer32,
                cmdTxRfSwitch
                    INTEGER,
                cmdTxSystemMode
                    TvStandard,
                cmdTxProgramExciterPrio
                    SwitchOnOff,
                cmdTxChangeOver
                    Trigger,
                cmdTxSwitchPosition
                    INTEGER,
                cmdDeviceIdx
                    IndexAB,
                cmdExcOpModeInputAutomatic
                    SwitchOnOff,
                cmdExcPreselectInput
                    INTEGER,
                cmdExcMode
                    INTEGER,
                cmdExcNetworkMode
                    INTEGER,
                cmdExcTPSSource
                    INTEGER,
                cmdExcEnableCellID
                    SwitchOnOff,
                cmdExcTxAddress
                    Integer32,
                cmdExcTxAutomatic
                    SwitchOnOff,
                cmdExcInputAutoSwitch
                    SwitchOnOff,
                cmdExcInputSeamless
                    SwitchOnOff,
                cmdExcInputPriority
                    INTEGER,
                cmdExcInputCheckTimeForward
                    Integer32,
                cmdExcInputCheckTimeSwitchback
                    Integer32,
                cmdExcInputMuteOnFail
                    INTEGER,
                cmdExcInputManualPreseletionHP1
                    INTEGER,
                cmdExcInputManualPreseletionHP2
                    INTEGER,
                cmdExcInputManualPreseletionLP1
                    INTEGER,
                cmdExcInputManualPreseletionLP2
                    INTEGER,
                cmdExcTPSManualBandwidth
                    INTEGER,
                cmdExcTPSManualFFTLength
                    INTEGER,
                cmdExcTPSManualGuardInterval
                    INTEGER,
                cmdExcTPSManualConstellation
                    INTEGER,
                cmdExcTPSManualAlpha
                    INTEGER,
                cmdExcTPSManualCellID
                    Integer32,
                cmdExcTPSManualInterleaver
                    INTEGER,
                cmdExcTPSManualCoderateHP
                    INTEGER,
                cmdExcTPSManualCoderateLP
                    INTEGER,
                cmdExcTPSManualTimeSlicingHP
                    SwitchOnOff,
                cmdExcTPSManualTimeSlicingLP
                    SwitchOnOff,
                cmdExcTPSManualFECHP
                    SwitchOnOff,
                cmdExcTPSManualFECLP
                    SwitchOnOff,
                cmdExcSFNStaticDelay
                    FloatingPoint,
                cmdExcSFNDeviationTime
                    Integer32,
                cmdExcFrequency
                    Integer32,
                cmdExcReferenceSource
                    INTEGER,
                cmdExcMuteOnPPSFail
                    INTEGER,
                cmdExcMuteOnReferenceFail
                    INTEGER,
                cmdExcRefFailDelayTime
                    Integer32,
                cmdExcTypeLossOfInput
                    INTEGER,
                cmdExcRfOutput
                    SwitchOnOff,
                cmdExcRfOutputRegulation
                    SwitchOnOff,
                cmdExcRfOutputManualRfLevel
                    FloatingPoint,
                cmdExcRfOutputAttenuation
                    Integer32,
                cmdExcRfOutputRfSlope
                    FloatingPoint,
                cmdExcRfOutputModulationSlope
                    FloatingPoint,
                cmdExcRfIqAdjustStart
                    INTEGER,
                cmdExcRfIqAdjustTestsignal
                    SwitchOnOff,
                cmdExcRfIqAdjustBiasCoarseI
                    Integer32,
                cmdExcRfIqAdjustBiasCoarseQ
                    Integer32,
                cmdExcRfIqAdjustBiasFineI
                    Integer32,
                cmdExcRfIqAdjustBiasFineQ
                    Integer32,
                cmdExcRfIqAdjustGainI
                    Integer32,
                cmdExcRfIqAdjustGainQ
                    Integer32,
                cmdExcRfIqAdjustPhase
                    FloatingPoint,
                cmdExcInput1Source
                    InputSource,
                cmdExcInput2Source
                    InputSource,
                cmdExcInpAutoReadyAfterChangeOv
                    SwitchOnOff,
                cmdExcInputFailDelayTime
                    Integer32,
                cmdExcTransmitterType
                    INTEGER,
                cmdExcTimeScheduler
                    SwitchOnOff,
                cmdExcMuteCondition
                    INTEGER,
                cmdExcRfWarningLimit
                    FloatingPoint,
                cmdExcRfFailLimit
                    FloatingPoint,
                cmdExcOutputPower
                    FloatingPoint,
                cmdOstRefVoltageVision
                    FloatingPoint,
                cmdOstMaxOutletTempThreshold
                    Integer32,
                cmdExcMonitoringOutput
                    INTEGER,
                cmdExcOcxoAdjust
                    Integer32,
                cmdExcExpectInputReserve
                    SwitchOnOff,
                cmdExcEnablePcrReset
                    SwitchOnOff,
                cmdExcTimeForDailyPcrReset
                    TimeOfDay,
                cmdExcFailDelayMode
                    FailDelayMode,
                cmdExcTransparentTs
                    SwitchOnOff
             }

        cmdTxResetSumFault OBJECT-TYPE
            SYNTAX Trigger
            MAX-ACCESS read-write
            STATUS current
            DESCRIPTION
                "Reset all faults (in all modules) of the transmitter.
                
                You reset a designated transmitter (NetCCU, Exciters, Outputstages).
                An equivalent would be pressing RESET at this transmitters frontpanel.
                
                A GET will always return idle(1). A SET idle(1) will return NO_ERROR without doing anything."
            ::= { commandsTxEntry 1 }

        
        cmdTxParametersetLoad OBJECT-TYPE
            SYNTAX Integer32 (1..8)
            MAX-ACCESS read-write
            STATUS current
            DESCRIPTION
                "This loads the desired parameter set."
            ::= { commandsTxEntry 2 }

        
        cmdTxParametersetSave OBJECT-TYPE
            SYNTAX Integer32 (1..8)
            MAX-ACCESS read-write
            STATUS current
            DESCRIPTION
                "This saves the current settings to a designated parameter set."
            ::= { commandsTxEntry 3 }

        
        cmdTxParametersetReSave OBJECT-TYPE
            SYNTAX Trigger
            MAX-ACCESS read-write
            STATUS obsolete
            DESCRIPTION
                "This saves the changes to the current parameter set."
            ::= { commandsTxEntry 4 }

        
        cmdTxOperationModeProgram OBJECT-TYPE
            SYNTAX SwitchOnOff
            MAX-ACCESS read-write
            STATUS current
            DESCRIPTION
                "This switches the program path of the transmitter on/off."
            ::= { commandsTxEntry 5 }

        
        cmdTxOperationModeReserve OBJECT-TYPE
            SYNTAX SwitchOnOff
            MAX-ACCESS read-write
            STATUS current
            DESCRIPTION
                "This switches the reserve path of the transmitter on/off."
            ::= { commandsTxEntry 6 }

        
        cmdTxOpModeExcAutomatic OBJECT-TYPE
            SYNTAX SwitchOnOff
            MAX-ACCESS read-write
            STATUS current
            DESCRIPTION
                "This switches the exciter automatic on/off."
            ::= { commandsTxEntry 7 }

        
        cmdTxOpModeOstAutomatic OBJECT-TYPE
            SYNTAX SwitchOnOff
            MAX-ACCESS read-write
            STATUS current
            DESCRIPTION
                "This switches the outputstage automatic on/off.
                
                This paramter is only available for systems with an automatic output switch."
            ::= { commandsTxEntry 8 }

        
        cmdTxPreselectExciter OBJECT-TYPE
            SYNTAX IndexAB
            MAX-ACCESS read-write
            STATUS current
            DESCRIPTION
                "This sets exciterA or exciterB to program path (antenna) of the transmitter."
            ::= { commandsTxEntry 9 }

        
        cmdTxPreselectOutputstage OBJECT-TYPE
            SYNTAX INTEGER
                {
                outputstageA(1),
                outputstageB(2),
                bothToAntenna(3),
                bothToDummyLoad(4)
                }
            MAX-ACCESS read-write
            STATUS current
            DESCRIPTION
                "This sets 
                - outputstageA or 
                - outputstageB or
                - both
                to program path (antenna) of the transmitter,
                or it sets both to dummyload.
                
                The settings bothToAntenna(3) and bothToDummyLoad(4) are only settable 
                for ActiveReserve systems.
                
                This paramter is only available for systems with an automatic output switch."
            ::= { commandsTxEntry 10 }

        
        cmdTxDelayTimeExcAutomatic OBJECT-TYPE
            SYNTAX Integer32 (1..60)
            UNITS "seconds"
            MAX-ACCESS read-write
            STATUS current
            DESCRIPTION
                "This sets the exciter automatic delay time."
            ::= { commandsTxEntry 11 }

        
        cmdTxDelayTimeOstAutomatic OBJECT-TYPE
            SYNTAX Integer32 (1..60)
            UNITS "seconds"
            MAX-ACCESS read-write
            STATUS current
            DESCRIPTION
                "This sets the outputstage automatic delay time.
                
                This paramter is only available for systems with an automatic output switch."
            ::= { commandsTxEntry 12 }

        
        cmdTxRfSwitch OBJECT-TYPE
            SYNTAX INTEGER
                {
                antenna(1),
                dummyLoad(2)
                }
            MAX-ACCESS read-write
            STATUS current
            DESCRIPTION
                "RF switch for single-ended systems."
            ::= { commandsTxEntry 13 }

        
        cmdTxSystemMode OBJECT-TYPE
            SYNTAX TvStandard
            MAX-ACCESS read-write
            STATUS current
            DESCRIPTION
                "This object gives you the possibility of switching the TV standard
                of a whole system with NetCCU with only one command.
                Not applicable for N+1 or NTx systems.
                The value 'test' cannot be written."
            ::= { commandsTxEntry 15 }

        
        cmdTxProgramExciterPrio OBJECT-TYPE
            SYNTAX SwitchOnOff
            MAX-ACCESS read-write
            STATUS current
            DESCRIPTION
                "Enables/Disables priority usage of program exciter"
            ::= { commandsTxEntry 20 }

        
        cmdTxChangeOver OBJECT-TYPE
            SYNTAX Trigger
            MAX-ACCESS read-write
            STATUS current
            DESCRIPTION
                "Performs a change over"
            ::= { commandsTxEntry 21 }

        
        cmdTxSwitchPosition OBJECT-TYPE
            SYNTAX INTEGER
                {
                undefined(1),
                controlExcOnAmp(2),
                programExcOnAmp(3)
                }
            MAX-ACCESS read-only
            STATUS current
            DESCRIPTION
                "Shows the actual switch position.
                The program exciter is connected to input 1 (RF IN 1),
                the control exciter is connected to input 2 (RF IN 2) of the base amplifier."
            ::= { commandsTxEntry 22 }

        
        cmdDeviceIdx OBJECT-TYPE
            SYNTAX IndexAB
            MAX-ACCESS not-accessible
            STATUS current
            DESCRIPTION
                "This column is used to show parameters for both exiters, if you have 
                dualdrive transmitters."
            ::= { commandsTxEntry 30 }

        
        cmdExcOpModeInputAutomatic OBJECT-TYPE
            SYNTAX SwitchOnOff
            MAX-ACCESS read-write
            STATUS current
            DESCRIPTION
                "Activates/deactivates the input automatic.
                If input automatic is active 
                and a loss of input signal is detected on the current input
                the reserve input will be used instead."
            ::= { commandsTxEntry 31 }

        
        cmdExcPreselectInput OBJECT-TYPE
            SYNTAX INTEGER
                {
                input1(1),
                input2(2)
                }
            MAX-ACCESS read-write
            STATUS current
            DESCRIPTION
                "This sets the preselection of a transmitters input."
            ::= { commandsTxEntry 32 }

        
        cmdExcMode OBJECT-TYPE
            SYNTAX INTEGER
                {
                dvbT(1),
                dvbH(2)
                }
            MAX-ACCESS read-write
            STATUS current
            DESCRIPTION
                "Switch between DVB-T and DVB-H."
            ::= { commandsTxEntry 33 }

        
        cmdExcNetworkMode OBJECT-TYPE
            SYNTAX INTEGER
                {
                mfn(1),
                sfn(2)
                }
            MAX-ACCESS read-write
            STATUS current
            DESCRIPTION
                "Switch between Single Frequency Networks (SFN) and 
                Multiple Frequency Networks (MFN)."
            ::= { commandsTxEntry 34 }

        
        cmdExcTPSSource OBJECT-TYPE
            SYNTAX INTEGER
                {
                manualPresets(1),
                mip(2)
                }
            MAX-ACCESS read-write
            STATUS current
            DESCRIPTION
                "Transmitted TPS parameters can be adjusted manually inside 
                the transmitter or automatically via MIP from the SFN adaptor."
            ::= { commandsTxEntry 35 }

        
        cmdExcEnableCellID OBJECT-TYPE
            SYNTAX SwitchOnOff
            MAX-ACCESS read-write
            STATUS current
            DESCRIPTION
                "This enables the Cell ID insertion. 
                The length indicator will be adjusted."
            ::= { commandsTxEntry 36 }

        
        cmdExcTxAddress OBJECT-TYPE
            SYNTAX Integer32 (0..65535)
            MAX-ACCESS read-write
            STATUS current
            DESCRIPTION
                "This is the unique address of the transmitter 
                to reference specific settings in the MIP."
            ::= { commandsTxEntry 37 }

        
        cmdExcTxAutomatic OBJECT-TYPE
            SYNTAX SwitchOnOff
            MAX-ACCESS read-write
            STATUS current
            DESCRIPTION
                "This enables Tx specific parameters from the 
                MIP data caroussel (e.g. time offset, frequency offset)."
            ::= { commandsTxEntry 38 }

        
        cmdExcInputAutoSwitch OBJECT-TYPE
            SYNTAX SwitchOnOff
            MAX-ACCESS read-write
            STATUS deprecated
            DESCRIPTION
                "Activates/deactivates the input automatic.
                If input automatic is active 
                and a loss of input signal is detected on the current input
                the reserve input will be used instead.
                
                This object is deprecated. It's recommended to use cmdExcOpModeInputAutomatic instead."
            ::= { commandsTxEntry 39 }

        
        cmdExcInputSeamless OBJECT-TYPE
            SYNTAX SwitchOnOff
            MAX-ACCESS read-write
            STATUS current
            DESCRIPTION
                "If the datastreams on both inputs are syncronised a seamless switch is possible. 
                With this parameter the seamless switch can be suppressed to enable a check of the input automatic."
            ::= { commandsTxEntry 40 }

        
        cmdExcInputPriority OBJECT-TYPE
            SYNTAX INTEGER
                {
                equal(1),
                prior(2)
                }
            MAX-ACCESS read-write
            STATUS current
            DESCRIPTION
                "Equal: There are no differences between both inputs. 
                       If a failure on the current input is detected it will be switched to the reserve input. 
                       It stays there until the reserve shows a failure. 
                Prior: Whenever possible a certain input shall be used. 
                       If a failure is detected the reserve will be used as short as possible."
            ::= { commandsTxEntry 41 }

        
        cmdExcInputCheckTimeForward OBJECT-TYPE
            SYNTAX Integer32 (0..600)
            UNITS "seconds"
            MAX-ACCESS read-write
            STATUS current
            DESCRIPTION
                "This time has to elapse before the current input switches 
                to the reserve input."
            ::= { commandsTxEntry 42 }

        
        cmdExcInputCheckTimeSwitchback OBJECT-TYPE
            SYNTAX Integer32 (0..600)
            UNITS "seconds"
            MAX-ACCESS read-write
            STATUS current
            DESCRIPTION
                "This time has to elapse before the automatic switches back 
                from the reserve to a preselected input. 
                This value has no effect if the priority is set to equal."
            ::= { commandsTxEntry 43 }

        
        cmdExcInputMuteOnFail OBJECT-TYPE
            SYNTAX INTEGER
                {
                mute(1),
                noMute(2)
                }
            MAX-ACCESS read-write
            STATUS current
            DESCRIPTION
                "If a loss of input signal is detected, the exciter mutes."
            ::= { commandsTxEntry 44 }

        
        cmdExcInputManualPreseletionHP1 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 45 }

        
        cmdExcInputManualPreseletionHP2 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 46 }

        
        cmdExcInputManualPreseletionLP1 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 47 }

        
        cmdExcInputManualPreseletionLP2 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 48 }

        
        cmdExcTPSManualBandwidth OBJECT-TYPE
            SYNTAX INTEGER
                {
                mhz5(1),
                mhz6(2),
                mhz7(3),
                mhz8(4)
                }
            MAX-ACCESS read-write
            STATUS current
            DESCRIPTION
                "The bandwidth used by the RF channel."
            ::= { commandsTxEntry 49 }

        
        cmdExcTPSManualFFTLength OBJECT-TYPE
            SYNTAX INTEGER
                {
                k2(1),
                k8(2),
                k4(3)
                }
            MAX-ACCESS read-write
            STATUS current
            DESCRIPTION
                "The used FFT length (depends on the DVB network)."
            ::= { commandsTxEntry 50 }

        
        cmdExcTPSManualGuardInterval OBJECT-TYPE
            SYNTAX INTEGER
                {
                oneOf32(1),
                oneOf16(2),
                oneOf8(3),
                oneOf4(4)
                }
            MAX-ACCESS read-write
            STATUS current
            DESCRIPTION
                "The Guard interval affects the error correction in multipath receiving situations.
                A long Guard Interval reduces the amount of payload data."
            ::= { commandsTxEntry 51 }

        
        cmdExcTPSManualConstellation OBJECT-TYPE
            SYNTAX INTEGER
                {
                qpsk(1),
                qam16(2),
                qam64(3)
                }
            MAX-ACCESS read-write
            STATUS current
            DESCRIPTION
                "This parameter sets the modulation mode."
            ::= { commandsTxEntry 52 }

        
        cmdExcTPSManualAlpha OBJECT-TYPE
            SYNTAX INTEGER
                {
                noHierarchy(1),
                one(2),
                two(3),
                four(4)
                }
            MAX-ACCESS read-write
            STATUS obsolete
            DESCRIPTION
                "An alpha greater than noHierarchy(1) enables the hierarchical coding mode.
                obsoleted - always returns noHierarchy(1)"
            ::= { commandsTxEntry 53 }

        
        cmdExcTPSManualCellID OBJECT-TYPE
            SYNTAX Integer32 (0..65535)
            MAX-ACCESS read-write
            STATUS current
            DESCRIPTION
                "Via Cell ID the receiver knows the current network."
            ::= { commandsTxEntry 54 }

        
        cmdExcTPSManualInterleaver OBJECT-TYPE
            SYNTAX INTEGER
                {
                indepth(1),
                nat(2)
                }
            MAX-ACCESS read-write
            STATUS current
            DESCRIPTION
                "Enables the bit interleaver for hierarchical coding"
            ::= { commandsTxEntry 55 }

        
        cmdExcTPSManualCoderateHP OBJECT-TYPE
            SYNTAX INTEGER
                {
                oneOf2(1),
                twoOf3(2),
                threeOf4(3),
                fiveOf6(4),
                sevenOf8(5)
                }
            MAX-ACCESS read-write
            STATUS current
            DESCRIPTION
                "The Code Rate sets the ratio between payload and error correction information."
            ::= { commandsTxEntry 56 }

        
        cmdExcTPSManualCoderateLP OBJECT-TYPE
            SYNTAX INTEGER
                {
                oneOf2(1),
                twoOf3(2),
                threeOf4(3),
                fiveOf6(4),
                sevenOf8(5)
                }
            MAX-ACCESS read-write
            STATUS current
            DESCRIPTION
                "The Code Rate sets the ratio between payload and error correction information."
            ::= { commandsTxEntry 57 }

        
        cmdExcTPSManualTimeSlicingHP OBJECT-TYPE
            SYNTAX SwitchOnOff
            MAX-ACCESS read-write
            STATUS current
            DESCRIPTION
                "Enables the time slicing for hierarchical coding."
            ::= { commandsTxEntry 58 }

        
        cmdExcTPSManualTimeSlicingLP OBJECT-TYPE
            SYNTAX SwitchOnOff
            MAX-ACCESS read-write
            STATUS current
            DESCRIPTION
                "Enables the time slicing for hierarchical coding."
            ::= { commandsTxEntry 59 }

        
        cmdExcTPSManualFECHP OBJECT-TYPE
            SYNTAX SwitchOnOff
            MAX-ACCESS read-write
            STATUS current
            DESCRIPTION
                "Enables the forward error correction (FEC) for hierarchical coding."
            ::= { commandsTxEntry 60 }

        
        cmdExcTPSManualFECLP OBJECT-TYPE
            SYNTAX SwitchOnOff
            MAX-ACCESS read-write
            STATUS current
            DESCRIPTION
                "Enables the forward error correction (FEC) for hierarchical coding."
            ::= { commandsTxEntry 61 }

        
        cmdExcSFNStaticDelay OBJECT-TYPE
            SYNTAX FloatingPoint
            UNITS "Microseconds"
            MAX-ACCESS read-write
            STATUS current
            DESCRIPTION
                "A constant adjustable delay for tuning a SFN (-999999.9 ... 999999.9)."
            ::= { commandsTxEntry 62 }

        
        cmdExcSFNDeviationTime OBJECT-TYPE
            SYNTAX Integer32 (1..100)
            UNITS "Microseconds"
            MAX-ACCESS read-write
            STATUS current
            DESCRIPTION
                "Leap In Time.
                This parameter sets the deviation in time when a readjustment 
                of the dynamic delay is necessary."
            ::= { commandsTxEntry 63 }

        
        cmdExcFrequency OBJECT-TYPE
            SYNTAX Integer32 (47000000..1500000000)
            UNITS "Hertz"
            MAX-ACCESS read-write
            STATUS current
            DESCRIPTION
                "This is the RF frequency."
            ::= { commandsTxEntry 64 }

        
        cmdExcReferenceSource OBJECT-TYPE
            SYNTAX INTEGER
                {
                intern(1),
                extern5Mhz(2),
                extern10Mhz(3),
                extern1PPS(4),
                internGPS(5)
                }
            MAX-ACCESS read-write
            STATUS current
            DESCRIPTION
                "The Source of the reference signal.
                The value internGPS is not valid for SX800."
            ::= { commandsTxEntry 65 }

        
        cmdExcMuteOnPPSFail OBJECT-TYPE
            SYNTAX INTEGER
                {
                off(1),
                onlyAtStartup(2),
                afterFailDelayTime(3)
                }
            MAX-ACCESS read-write
            STATUS current
            DESCRIPTION
                "Select the behaviour if the external second pulse is not available."
            ::= { commandsTxEntry 66 }

        
        cmdExcMuteOnReferenceFail OBJECT-TYPE
            SYNTAX INTEGER
                {
                off(1),
                onlyAtStartup(2),
                afterFailDelayTime(3)
                }
            MAX-ACCESS read-write
            STATUS current
            DESCRIPTION
                "Select the behaviour if the external reference is not available."
            ::= { commandsTxEntry 67 }

        
        cmdExcRefFailDelayTime OBJECT-TYPE
            SYNTAX Integer32 (0..24)
            UNITS "Hours"
            MAX-ACCESS read-write
            STATUS current
            DESCRIPTION
                "Adjusts the time after the RF will be muted in case of a reference problem.
                Zero hours means react immediately."
            ::= { commandsTxEntry 68 }

        
        cmdExcTypeLossOfInput OBJECT-TYPE
            SYNTAX INTEGER
                {
                warning(1),
                fault(2)
                }
            MAX-ACCESS read-write
            STATUS current
            DESCRIPTION
                "If the input signal is lost, either a warning or a fault can be generated.
                If you select fault here, a switchover to the reserve exciter will be executed 
                when input signal is lost."
            ::= { commandsTxEntry 69 }

        
        cmdExcRfOutput OBJECT-TYPE
            SYNTAX SwitchOnOff
            MAX-ACCESS read-write
            STATUS current
            DESCRIPTION
                "Turns on/switches off the output signal. This switch takes the same effect as the switch on the frontpanel of the exciter."
            ::= { commandsTxEntry 70 }

        
        cmdExcRfOutputRegulation OBJECT-TYPE
            SYNTAX SwitchOnOff
            MAX-ACCESS read-write
            STATUS current
            DESCRIPTION
                "Turns on/switches off the automatic output level regulation."
            ::= { commandsTxEntry 71 }

        
        cmdExcRfOutputManualRfLevel OBJECT-TYPE
            SYNTAX FloatingPoint
            UNITS "Percent"
            MAX-ACCESS read-write
            STATUS current
            DESCRIPTION
                "Adjusts the RF level (0.0 ... 100.0). The value relates to an attenuation of 0 dB."
            ::= { commandsTxEntry 72 }

        
        cmdExcRfOutputAttenuation OBJECT-TYPE
            SYNTAX Integer32 (0..9)
            UNITS "dB"
            MAX-ACCESS read-write
            STATUS current
            DESCRIPTION
                "Activates internal attenuators to reduce the output level of the exciter.
                Adjustable in steps of 3 dB only."
            ::= { commandsTxEntry 73 }

        
        cmdExcRfOutputRfSlope OBJECT-TYPE
            SYNTAX FloatingPoint
            UNITS "Percent"
            MAX-ACCESS read-write
            STATUS current
            DESCRIPTION
                "Adjusts a slope in the RF signal (-50.0 ... 50.0)."
            ::= { commandsTxEntry 74 }

        
        cmdExcRfOutputModulationSlope OBJECT-TYPE
            SYNTAX FloatingPoint
            UNITS "Percent"
            MAX-ACCESS read-write
            STATUS current
            DESCRIPTION
                "Modulation slope (-50.0 ... 50.0)."
            ::= { commandsTxEntry 75 }

        
        cmdExcRfIqAdjustStart OBJECT-TYPE
            SYNTAX INTEGER
                {
                break(1),
                start(2)
                }
            MAX-ACCESS read-write
            STATUS current
            DESCRIPTION
                "Starts the automatic IQ adjustment. It works for the current used local 1 frequency and lasts up to 5 minutes. In this time the output will be muted. During the adjustment no transmitter parameter shall be changed. Break will stop the automatic immediately. The IQ modulator looses its adjustment!
                Read values mean idle(1) and started(2)."
            ::= { commandsTxEntry 77 }

        
        cmdExcRfIqAdjustTestsignal OBJECT-TYPE
            SYNTAX SwitchOnOff
            MAX-ACCESS read-write
            STATUS current
            DESCRIPTION
                "Generates a test signal to adjust the IQ modulation. It is necessary to disconnect the rf-cable to the output stages."
            ::= { commandsTxEntry 78 }

        
        cmdExcRfIqAdjustBiasCoarseI OBJECT-TYPE
            SYNTAX Integer32 (-1023..1023)
            MAX-ACCESS read-write
            STATUS current
            DESCRIPTION
                "Adjusts the offset for I in huge steps."
            ::= { commandsTxEntry 79 }

        
        cmdExcRfIqAdjustBiasCoarseQ OBJECT-TYPE
            SYNTAX Integer32 (-1023..1023)
            MAX-ACCESS read-write
            STATUS current
            DESCRIPTION
                "Adjusts the offset for Q in huge steps."
            ::= { commandsTxEntry 80 }

        
        cmdExcRfIqAdjustBiasFineI OBJECT-TYPE
            SYNTAX Integer32 (-32767..32767)
            MAX-ACCESS read-write
            STATUS current
            DESCRIPTION
                "Adjusts the offset for I in small steps."
            ::= { commandsTxEntry 81 }

        
        cmdExcRfIqAdjustBiasFineQ OBJECT-TYPE
            SYNTAX Integer32 (-32767..32767)
            MAX-ACCESS read-write
            STATUS current
            DESCRIPTION
                "Adjusts the offset for Q in small steps."
            ::= { commandsTxEntry 82 }

        
        cmdExcRfIqAdjustGainI OBJECT-TYPE
            SYNTAX Integer32 (0..255)
            MAX-ACCESS read-write
            STATUS current
            DESCRIPTION
                "Adjusts the gain for I in small steps."
            ::= { commandsTxEntry 83 }

        
        cmdExcRfIqAdjustGainQ OBJECT-TYPE
            SYNTAX Integer32 (0..255)
            MAX-ACCESS read-write
            STATUS current
            DESCRIPTION
                "Adjusts the gain for Q in small steps."
            ::= { commandsTxEntry 84 }

        
        cmdExcRfIqAdjustPhase OBJECT-TYPE
            SYNTAX FloatingPoint
            MAX-ACCESS read-write
            STATUS current
            DESCRIPTION
                "Adjusts the phase between I and Q (-14.000 ... 14.000)."
            ::= { commandsTxEntry 85 }

        
        cmdExcInput1Source OBJECT-TYPE
            SYNTAX InputSource
            MAX-ACCESS read-write
            STATUS current
            DESCRIPTION
                "Source for input 1."
            ::= { commandsTxEntry 86 }

        
        cmdExcInput2Source OBJECT-TYPE
            SYNTAX InputSource
            MAX-ACCESS read-write
            STATUS current
            DESCRIPTION
                "Source for input 2."
            ::= { commandsTxEntry 87 }

        
        cmdExcInpAutoReadyAfterChangeOv OBJECT-TYPE
            SYNTAX SwitchOnOff
            MAX-ACCESS read-write
            STATUS current
            DESCRIPTION
                "Input automatic ready after change over."
            ::= { commandsTxEntry 88 }

        
        cmdExcInputFailDelayTime OBJECT-TYPE
            SYNTAX Integer32 (0..600)
            UNITS "Seconds"
            MAX-ACCESS read-write
            STATUS current
            DESCRIPTION
                "The time between detecting a loss of input signal and displaying a failure."
            ::= { commandsTxEntry 89 }

        
        cmdExcTransmitterType OBJECT-TYPE
            SYNTAX INTEGER
                {
                atv(1),
                dvb(2),
                atsc(3)
                }
            MAX-ACCESS read-write
            STATUS current
            DESCRIPTION
                "the TV standard of the transmitter
                The transmitter is rebooted automatically when the TV standard is
                changed. Signal processing is also switched over."
            ::= { commandsTxEntry 90 }

        
        cmdExcTimeScheduler OBJECT-TYPE
            SYNTAX SwitchOnOff
            MAX-ACCESS read-write
            STATUS current
            DESCRIPTION
                "If on, the time scheduler controls the tx type. When switching on the scheduler 
                it may instantly set the correct TV standard and reboot the device."
            ::= { commandsTxEntry 91 }

        
        cmdExcMuteCondition OBJECT-TYPE
            SYNTAX INTEGER
                {
                onAllFaults(1),
                notBeforeSyncLoss(2)
                }
            MAX-ACCESS read-write
            STATUS current
            DESCRIPTION
                "When notBeforeSyncLoss(2) is selected,
                it relativizes the cmdExcInputMuteOnFail setting mute(1):
                If a DVB receiver is the last valid input, an existing transport stream,
                even if it is faulty shall not be muted.
                
                Only for SLx/Sx801"
            ::= { commandsTxEntry 92 }

        
        cmdExcRfWarningLimit OBJECT-TYPE
            SYNTAX FloatingPoint
            UNITS "dB"
            MAX-ACCESS read-write
            STATUS current
            DESCRIPTION
                "Warning limit for the RF control.
                min: -15.0, max: 0.0"
            ::= { commandsTxEntry 97 }

        
        cmdExcRfFailLimit OBJECT-TYPE
            SYNTAX FloatingPoint
            UNITS "dB"
            MAX-ACCESS read-write
            STATUS current
            DESCRIPTION
                "Fault limit for the RF control.
                min: -15.0, max: 0.0"
            ::= { commandsTxEntry 98 }

        
        cmdExcOutputPower OBJECT-TYPE
            SYNTAX FloatingPoint
            UNITS "W"
            MAX-ACCESS read-write
            STATUS current
            DESCRIPTION
                "amplifier output power
                0 ... 400 W"
            ::= { commandsTxEntry 99 }

        
        cmdOstRefVoltageVision OBJECT-TYPE
            SYNTAX FloatingPoint
            UNITS "Percent"
            MAX-ACCESS read-write
            STATUS current
            DESCRIPTION
                "This adjusts the output power of the amplifier.
                This value is settable with maximal 1 position after point (example 11.2)."
            ::= { commandsTxEntry 100 }

        
        cmdOstMaxOutletTempThreshold OBJECT-TYPE
            SYNTAX Integer32 (45..65)
            UNITS "Degree Celsius"
            MAX-ACCESS read-write
            STATUS current
            DESCRIPTION
                "This sets the threshold for the outlet temperature."
            ::= { commandsTxEntry 101 }

        
        cmdExcMonitoringOutput OBJECT-TYPE
            SYNTAX INTEGER
                {
                off(1),
                reference10MHz(2),
                generated1PPS(3),
                kHz1(4),
                pulse1PPS(5)
                }
            MAX-ACCESS read-write
            STATUS current
            DESCRIPTION
                "Selects which signal appears at the monitoring output."
            ::= { commandsTxEntry 110 }

        
        cmdExcOcxoAdjust OBJECT-TYPE
            SYNTAX Integer32 (0..65535)
            MAX-ACCESS read-write
            STATUS current
            DESCRIPTION
                "Adjusts the frequency of the internal 10 MHz reference.
                This value only takes effect if the reference source 'internal' is selected."
            ::= { commandsTxEntry 111 }

        
        cmdExcExpectInputReserve OBJECT-TYPE
            SYNTAX SwitchOnOff
            MAX-ACCESS read-write
            STATUS current
            DESCRIPTION
                "If on(1) the warning txExcInputReseveMissing will be generated
                in case second input is missing."
            ::= { commandsTxEntry 112 }

        
        cmdExcEnablePcrReset OBJECT-TYPE
            SYNTAX SwitchOnOff
            MAX-ACCESS read-write
            STATUS obsolete
            DESCRIPTION
                "Enables/disables daily PCR resets.
                This option is valid only in MFN operation.
                The reset time is given in cmdExcTimeForDailyPcrReset."
            ::= { commandsTxEntry 113 }

        
        cmdExcTimeForDailyPcrReset OBJECT-TYPE
            SYNTAX TimeOfDay
            MAX-ACCESS read-write
            STATUS obsolete
            DESCRIPTION
                "Sets the time of day for daily PCR reset."
            ::= { commandsTxEntry 114 }

        
        cmdExcFailDelayMode OBJECT-TYPE
            SYNTAX FailDelayMode
            MAX-ACCESS read-write
            STATUS current
            DESCRIPTION
                "Condition when the fail delay time is used."
            ::= { commandsTxEntry 115 }

        
        cmdExcTransparentTs OBJECT-TYPE
            SYNTAX SwitchOnOff
            MAX-ACCESS read-write
            STATUS current
            DESCRIPTION
                "If enabled in MFN, then stuffing and PCR restamping is off;
                output datarate is controlled by input datarate.
                In SFN this option is always enabled."
            ::= { commandsTxEntry 116 }

        
        summaryInfo OBJECT IDENTIFIER ::= { rsXx8000DvbTxObjs 2 }

        
        summaryFaultTx OBJECT-TYPE
            SYNTAX TruthValue
            MAX-ACCESS read-only
            STATUS current
            DESCRIPTION
                "This indicates a summary fault of the transmitter.
                   true(1)  --> summary fault
                   false(2) --> no summary fault
                
                There is a fault of at least one module (e.g. Exciter) which causes this summary fault.
                
                An equivalent would be the LED Fault at the transmitters frontpanel."
            ::= { summaryInfo 1 }

        
        summaryWarningTx OBJECT-TYPE
            SYNTAX TruthValue
            MAX-ACCESS read-only
            STATUS current
            DESCRIPTION
                "This indicates a summary warning of the transmitter.
                   true(1)  --> summary warning
                   false(2) --> no summary warning
                
                There is a fault of at least one module (e.g. Exciter) which causes this summary warning.
                
                An equivalent would be the LED Warning at the transmitters frontpanel."
            ::= { summaryInfo 2 }

        
        localModeTx OBJECT-TYPE
            SYNTAX TruthValue
            MAX-ACCESS read-only
            STATUS current
            DESCRIPTION
                "This indicates the local/remote-mode of the transmitter.
                   true(1)  --> local
                   false(2) --> remote
                
                The transmitter is eigther in local-mode or in remote-mode. 
                For security reasons it is not possible to set this value!
                
                An equivalent would the LED Local at the transmitters frontpanel."
            ::= { summaryInfo 3 }

        
        rfOnTx OBJECT-TYPE
            SYNTAX TruthValue
            MAX-ACCESS read-only
            STATUS current
            DESCRIPTION
                "The RF is present for the corresponding transmitter."
            ::= { summaryInfo 4 }

        
        forwardPower OBJECT-TYPE
            SYNTAX FloatingPoint
            UNITS "Watt"
            MAX-ACCESS read-only
            STATUS current
            DESCRIPTION
                "The measured forwarded power [W] of the transmitter. 
                For Active Reserve systems it is the sum of both outputstages."
            ::= { summaryInfo 5 }

        
        reflectedPower OBJECT-TYPE
            SYNTAX FloatingPoint
            UNITS "Watt"
            MAX-ACCESS read-only
            STATUS current
            DESCRIPTION
                "The measured reflected power [W] of the transmitter. 
                For Active Reserve systems it is the sum of both outputstages.
                
                Not available for lowpower systems."
            ::= { summaryInfo 6 }

        
        summaryFaultExcA OBJECT-TYPE
            SYNTAX TruthValue
            MAX-ACCESS read-only
            STATUS current
            DESCRIPTION
                "This indicates a summary fault of exciter."
            ::= { summaryInfo 7 }

        
        summaryFaultOstA OBJECT-TYPE
            SYNTAX TruthValue
            MAX-ACCESS read-only
            STATUS current
            DESCRIPTION
                "This indicates a summary fault of outputstage."
            ::= { summaryInfo 8 }

        
        summaryFaultExcB OBJECT-TYPE
            SYNTAX TruthValue
            MAX-ACCESS read-only
            STATUS current
            DESCRIPTION
                "This indicates a summary fault of exciter."
            ::= { summaryInfo 9 }

        
        summaryFaultOstB OBJECT-TYPE
            SYNTAX TruthValue
            MAX-ACCESS read-only
            STATUS current
            DESCRIPTION
                "This indicates a summary fault of outputstage."
            ::= { summaryInfo 10 }

        
        exciterAutomaticReady OBJECT-TYPE
            SYNTAX TruthValue
            MAX-ACCESS read-only
            STATUS current
            DESCRIPTION
                "The Exciter Automatic is Ready. 
                In case of any fault on one exciter, there will be a switchover to the other exciter."
            ::= { summaryInfo 11 }

        
        exciterAutomaticChanged OBJECT-TYPE
            SYNTAX TruthValue
            MAX-ACCESS read-only
            STATUS current
            DESCRIPTION
                "The Exciter Automatic has changed. 
                There was a fault on one exciter which lead to this changeover."
            ::= { summaryInfo 12 }

        
        exciterAutomaticFault OBJECT-TYPE
            SYNTAX TruthValue
            MAX-ACCESS read-only
            STATUS current
            DESCRIPTION
                "The Exciter Automatic is faulty. 
                In case of any fault on one exciter, there will be no switchover to the other exciter,
                because of this fault."
            ::= { summaryInfo 13 }

        
        outputstageAutomaticReady OBJECT-TYPE
            SYNTAX TruthValue
            MAX-ACCESS read-only
            STATUS current
            DESCRIPTION
                "The Outputstage Automatic is Ready. 
                In case of any fault on one outputstage, there will be a switchover to the other outputstage.
                
                This paramter is only available for systems with an automatic output switch."
            ::= { summaryInfo 14 }

        
        outputstageAutomaticChanged OBJECT-TYPE
            SYNTAX TruthValue
            MAX-ACCESS read-only
            STATUS current
            DESCRIPTION
                "The Outputstage Automatic has changed. 
                There was a fault on one outputstage which lead to this changeover.
                
                This paramter is only available for systems with an automatic output switch."
            ::= { summaryInfo 15 }

        
        outputstageAutomaticFault OBJECT-TYPE
            SYNTAX TruthValue
            MAX-ACCESS read-only
            STATUS current
            DESCRIPTION
                "The Outputstage Automatic is faulty. 
                In case of any fault on one outputstage, there will be no switchover to the other outputstage,
                because of this fault.
                
                This paramter is only available for systems with an automatic output switch."
            ::= { summaryInfo 16 }

        
        noConnectionExcA OBJECT-TYPE
            SYNTAX TruthValue
            MAX-ACCESS read-only
            STATUS current
            DESCRIPTION
                "No Connection between NetCCU and Exciter."
            ::= { summaryInfo 17 }

        
        noConnectionOstA OBJECT-TYPE
            SYNTAX TruthValue
            MAX-ACCESS read-only
            STATUS current
            DESCRIPTION
                "No Connection between NetCCU and Outputstage."
            ::= { summaryInfo 18 }

        
        noConnectionExcB OBJECT-TYPE
            SYNTAX TruthValue
            MAX-ACCESS read-only
            STATUS current
            DESCRIPTION
                "No Connection between NetCCU and Exciter."
            ::= { summaryInfo 19 }

        
        noConnectionOstB OBJECT-TYPE
            SYNTAX TruthValue
            MAX-ACCESS read-only
            STATUS current
            DESCRIPTION
                "No Connection between NetCCU and Outputstage."
            ::= { summaryInfo 20 }

        
        activeExcA OBJECT-TYPE
            SYNTAX TruthValue
            MAX-ACCESS read-only
            STATUS current
            DESCRIPTION
                "ExciterA is currently active."
            ::= { summaryInfo 21 }

        
        activeOstA OBJECT-TYPE
            SYNTAX TruthValue
            MAX-ACCESS read-only
            STATUS current
            DESCRIPTION
                "OutputstageA is currently active."
            ::= { summaryInfo 22 }

        
        activeExcB OBJECT-TYPE
            SYNTAX TruthValue
            MAX-ACCESS read-only
            STATUS current
            DESCRIPTION
                "ExciterB is currently active."
            ::= { summaryInfo 23 }

        
        activeOstB OBJECT-TYPE
            SYNTAX TruthValue
            MAX-ACCESS read-only
            STATUS current
            DESCRIPTION
                "OutputstageB is currently active."
            ::= { summaryInfo 24 }

        
        forwardPowerOstA OBJECT-TYPE
            SYNTAX FloatingPoint
            UNITS "Watt"
            MAX-ACCESS read-only
            STATUS current
            DESCRIPTION
                "The measured forwarded power [W] of the OutputstageA."
            ::= { summaryInfo 25 }

        
        reflectedPowerOstA OBJECT-TYPE
            SYNTAX FloatingPoint
            UNITS "Watt"
            MAX-ACCESS read-only
            STATUS current
            DESCRIPTION
                "The measured reflected power [W] of the OutputstageA.
                
                Not available for lowpower systems."
            ::= { summaryInfo 26 }

        
        forwardPowerOstB OBJECT-TYPE
            SYNTAX FloatingPoint
            UNITS "Watt"
            MAX-ACCESS read-only
            STATUS current
            DESCRIPTION
                "The measured forwarded power [W] of the OutputstageB."
            ::= { summaryInfo 27 }

        
        reflectedPowerOstB OBJECT-TYPE
            SYNTAX FloatingPoint
            UNITS "Watt"
            MAX-ACCESS read-only
            STATUS current
            DESCRIPTION
                "The measured reflected power [W] of the OutputstageB.
                
                Not available for lowpower systems."
            ::= { summaryInfo 28 }

        
        powerSupply OBJECT-TYPE
            SYNTAX FloatingPoint
            UNITS "volt"
            MAX-ACCESS read-only
            STATUS current
            DESCRIPTION
                "Monitoring value of the output voltages of the power supply."
            ::= { summaryInfo 29 }

        
        additionalPowerSupply OBJECT-TYPE
            SYNTAX TruthValue
            MAX-ACCESS read-only
            STATUS current
            DESCRIPTION
                "Shows whether the NetCCU has an additional (external) power supply."
            ::= { summaryInfo 30 }

        
        internalPowerSupply OBJECT-TYPE
            SYNTAX FloatingPoint
            UNITS "volt"
            MAX-ACCESS read-only
            STATUS current
            DESCRIPTION
                "Monitoring value of the output voltages of the internal power supply."
            ::= { summaryInfo 31 }

        
        externalPowerSupply OBJECT-TYPE
            SYNTAX FloatingPoint
            UNITS "volt"
            MAX-ACCESS read-only
            STATUS current
            DESCRIPTION
                "Monitoring value of the output voltages of the external power supply."
            ::= { summaryInfo 32 }

        
        detailedInfo OBJECT IDENTIFIER ::= { rsXx8000DvbTxObjs 3 }

        
        excInputTable OBJECT-TYPE
            SYNTAX SEQUENCE OF ExcInputEntry
            MAX-ACCESS not-accessible
            STATUS current
            DESCRIPTION
                "A table for more detailed information about the exciter.
                These values are all read-only. For settings, refer to commands."
            ::= { detailedInfo 2 }

        
        excInputEntry OBJECT-TYPE
            SYNTAX ExcInputEntry
            MAX-ACCESS not-accessible
            STATUS current
            DESCRIPTION
                "An entry for a designated input channel."
            INDEX { excInputExcIdx, excInputChannelIdx }
            ::= { excInputTable 1 }

        
        ExcInputEntry ::=
            SEQUENCE { 
                excInputExcIdx
                    IndexAB,
                excInputChannelIdx
                    Integer32,
                excInputChannelName
                    INTEGER,
                excInputConnected
                    TruthValue,
                excInputSeamless
                    TruthValue,
                excInputPreselected
                    TruthValue,
                excInputActive
                    TruthValue,
                excInputMipFail
                    TruthValue,
                excInputBandwidth
                    INTEGER,
                excInputFFTLength
                    INTEGER,
                excInputGuardInterval
                    INTEGER,
                excInputConstellation
                    INTEGER,
                excInputAlpha
                    INTEGER,
                excInputCellID
                    Integer32,
                excInputInterleaver
                    INTEGER,
                excInputCodeRate
                    INTEGER,
                excInputPacketLength
                    Integer32,
                excInputMeasuredDatarate
                    Integer32,
                excInputRequiredDatarate
                    Integer32,
                excInputMaximumDelay
                    Integer32
             }

        excInputExcIdx OBJECT-TYPE
            SYNTAX IndexAB
            MAX-ACCESS not-accessible
            STATUS current
            DESCRIPTION
                "The index for exciterA (and exciterB if there are DualDrive systems)."
            ::= { excInputEntry 1 }

        
        excInputChannelIdx OBJECT-TYPE
            SYNTAX Integer32 (1..6)
            MAX-ACCESS not-accessible
            STATUS current
            DESCRIPTION
                "The index for the different input channels."
            ::= { excInputEntry 2 }

        
        excInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { excInputEntry 3 }

        
        excInputConnected OBJECT-TYPE
            SYNTAX TruthValue
            MAX-ACCESS read-only
            STATUS current
            DESCRIPTION
                "The input channel is connected."
            ::= { excInputEntry 4 }

        
        excInputSeamless OBJECT-TYPE
            SYNTAX TruthValue
            MAX-ACCESS read-only
            STATUS current
            DESCRIPTION
                "The input channel is in seamless mode."
            ::= { excInputEntry 5 }

        
        excInputPreselected OBJECT-TYPE
            SYNTAX TruthValue
            MAX-ACCESS read-only
            STATUS current
            DESCRIPTION
                "The input channel is the preselected."
            ::= { excInputEntry 6 }

        
        excInputActive OBJECT-TYPE
            SYNTAX TruthValue
            MAX-ACCESS read-only
            STATUS current
            DESCRIPTION
                "The input channel is active."
            ::= { excInputEntry 7 }

        
        excInputMipFail OBJECT-TYPE
            SYNTAX TruthValue
            MAX-ACCESS read-only
            STATUS current
            DESCRIPTION
                "Input channel MIP fail."
            ::= { excInputEntry 8 }

        
        excInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { excInputEntry 9 }

        
        excInputFFTLength OBJECT-TYPE
            SYNTAX INTEGER
                {
                k2(1),
                k8(2),
                k4(3)
                }
            MAX-ACCESS read-only
            STATUS current
            DESCRIPTION
                "The used FFT length (depends on the DVB network)."
            ::= { excInputEntry 10 }

        
        excInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { excInputEntry 11 }

        
        excInputConstellation OBJECT-TYPE
            SYNTAX INTEGER
                {
                qpsk(1),
                qam16(2),
                qam64(3)
                }
            MAX-ACCESS read-only
            STATUS current
            DESCRIPTION
                "This parameter sets the modulation mode."
            ::= { excInputEntry 12 }

        
        excInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { excInputEntry 13 }

        
        excInputCellID OBJECT-TYPE
            SYNTAX Integer32 (0..65535)
            MAX-ACCESS read-only
            STATUS current
            DESCRIPTION
                "Via Cell ID the receiver knows the current network."
            ::= { excInputEntry 14 }

        
        excInputInterleaver OBJECT-TYPE
            SYNTAX INTEGER
                {
                indepth(1),
                nat(2)
                }
            MAX-ACCESS read-only
            STATUS current
            DESCRIPTION
                "Enables the bit interleaver for hierarchical coding"
            ::= { excInputEntry 15 }

        
        excInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { excInputEntry 16 }

        
        excInputPacketLength OBJECT-TYPE
            SYNTAX Integer32 (188..208)
            MAX-ACCESS read-only
            STATUS current
            DESCRIPTION
                "The Packet length for the channel."
            ::= { excInputEntry 17 }

        
        excInputMeasuredDatarate OBJECT-TYPE
            SYNTAX Integer32
            MAX-ACCESS read-only
            STATUS current
            DESCRIPTION
                "The measured datarate of the input."
            ::= { excInputEntry 18 }

        
        excInputRequiredDatarate OBJECT-TYPE
            SYNTAX Integer32
            MAX-ACCESS read-only
            STATUS current
            DESCRIPTION
                "The required datarate of the input."
            ::= { excInputEntry 19 }

        
        excInputMaximumDelay OBJECT-TYPE
            SYNTAX Integer32 (0..100000000)
            UNITS "Nanoseconds"
            MAX-ACCESS read-only
            STATUS current
            DESCRIPTION
                "Period of time between the signal leaving the play-out center (MIP inserter)
                and its regular transmission at the antenna.
                This delay is set in the MIP inserter and serves as a basis
                for all the transmitters in the SFN."
            ::= { excInputEntry 20 }

        
        ostTable OBJECT-TYPE
            SYNTAX SEQUENCE OF OstEntry
            MAX-ACCESS not-accessible
            STATUS current
            DESCRIPTION
                "The table of racks."
            ::= { detailedInfo 3 }

        
        ostEntry OBJECT-TYPE
            SYNTAX OstEntry
            MAX-ACCESS not-accessible
            STATUS current
            DESCRIPTION
                "A row (an entry) for one rack."
            INDEX { ostIdx, ostRackIdx, ostRackAmpIdx }
            ::= { ostTable 1 }

        
        OstEntry ::=
            SEQUENCE { 
                ostIdx
                    IndexAB,
                ostRackIdx
                    IndexRack,
                ostRackInletTemperature
                    FloatingPoint,
                ostRackOutletTemperature
                    FloatingPoint,
                ostRackAuxPowerSupply
                    FloatingPoint,
                ostRackAmpIdx
                    IndexAmplifier,
                ostRackAmpI1A
                    FloatingPoint,
                ostRackAmpI2A
                    FloatingPoint,
                ostRackAmpI3A
                    FloatingPoint,
                ostRackAmpI4A
                    FloatingPoint,
                ostRackAmpI1B
                    FloatingPoint,
                ostRackAmpI2B
                    FloatingPoint,
                ostRackAmpI3B
                    FloatingPoint,
                ostRackAmpI4B
                    FloatingPoint,
                ostRackAmpIDrv
                    FloatingPoint,
                ostRackAmpUDc
                    FloatingPoint,
                ostRackAmpIDc
                    FloatingPoint,
                ostRackAmpUDcControl
                    FloatingPoint,
                ostRackAmpUReg
                    FloatingPoint,
                ostRackAmpPowerA
                    FloatingPoint,
                ostRackAmpPowerB
                    FloatingPoint,
                ostRackAmpPowerOut
                    FloatingPoint,
                ostRackAmpPowerReflection
                    FloatingPoint,
                ostRackAmpPowerReference
                    FloatingPoint,
                ostRackAmpDeltaPhase
                    FloatingPoint,
                ostRackAmpCmdDeltaPhase
                    FloatingPoint
             }

        ostIdx OBJECT-TYPE
            SYNTAX IndexAB
            MAX-ACCESS not-accessible
            STATUS current
            DESCRIPTION
                "The dedicated outputstage (A/B)."
            ::= { ostEntry 1 }

        
        ostRackIdx OBJECT-TYPE
            SYNTAX IndexRack
            MAX-ACCESS not-accessible
            STATUS current
            DESCRIPTION
                "The rack number (1..10)."
            ::= { ostEntry 2 }

        
        ostRackInletTemperature OBJECT-TYPE
            SYNTAX FloatingPoint
            UNITS "Degree Celsius"
            MAX-ACCESS read-only
            STATUS current
            DESCRIPTION
                "The inlet temperature."
            ::= { ostEntry 3 }

        
        ostRackOutletTemperature OBJECT-TYPE
            SYNTAX FloatingPoint
            UNITS "Degree Celsius"
            MAX-ACCESS read-only
            STATUS current
            DESCRIPTION
                "The outlet temperature."
            ::= { ostEntry 4 }

        
        ostRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { ostEntry 5 }

        
        ostRackAmpIdx OBJECT-TYPE
            SYNTAX IndexAmplifier
            MAX-ACCESS not-accessible
            STATUS current
            DESCRIPTION
                "Amplifier Index"
            ::= { ostEntry 400 }

        
        ostRackAmpI1A OBJECT-TYPE
            SYNTAX FloatingPoint
            UNITS "Ampere"
            MAX-ACCESS read-only
            STATUS current
            DESCRIPTION
                "The power amplifier module current (I_1A)."
            ::= { ostEntry 401 }

        
        ostRackAmpI2A OBJECT-TYPE
            SYNTAX FloatingPoint
            UNITS "Ampere"
            MAX-ACCESS read-only
            STATUS current
            DESCRIPTION
                "The power amplifier module current (I_2A)."
            ::= { ostEntry 402 }

        
        ostRackAmpI3A OBJECT-TYPE
            SYNTAX FloatingPoint
            UNITS "Ampere"
            MAX-ACCESS read-only
            STATUS current
            DESCRIPTION
                "The power amplifier module current (I_3A)."
            ::= { ostEntry 403 }

        
        ostRackAmpI4A OBJECT-TYPE
            SYNTAX FloatingPoint
            UNITS "Ampere"
            MAX-ACCESS read-only
            STATUS current
            DESCRIPTION
                "The power amplifier module current (I_4A)."
            ::= { ostEntry 404 }

        
        ostRackAmpI1B OBJECT-TYPE
            SYNTAX FloatingPoint
            UNITS "Ampere"
            MAX-ACCESS read-only
            STATUS current
            DESCRIPTION
                "The power amplifier module current (I_1B)."
            ::= { ostEntry 405 }

        
        ostRackAmpI2B OBJECT-TYPE
            SYNTAX FloatingPoint
            UNITS "Ampere"
            MAX-ACCESS read-only
            STATUS current
            DESCRIPTION
                "The power amplifier module current (I_2B)."
            ::= { ostEntry 406 }

        
        ostRackAmpI3B OBJECT-TYPE
            SYNTAX FloatingPoint
            UNITS "Ampere"
            MAX-ACCESS read-only
            STATUS current
            DESCRIPTION
                "The power amplifier module current (I_3B)."
            ::= { ostEntry 407 }

        
        ostRackAmpI4B OBJECT-TYPE
            SYNTAX FloatingPoint
            UNITS "Ampere"
            MAX-ACCESS read-only
            STATUS current
            DESCRIPTION
                "The power amplifier module current (I_4B)."
            ::= { ostEntry 408 }

        
        ostRackAmpIDrv OBJECT-TYPE
            SYNTAX FloatingPoint
            UNITS "Ampere"
            MAX-ACCESS read-only
            STATUS current
            DESCRIPTION
                "The driver module current (I_DRV)."
            ::= { ostEntry 409 }

        
        ostRackAmpUDc OBJECT-TYPE
            SYNTAX FloatingPoint
            UNITS "Volt"
            MAX-ACCESS read-only
            STATUS current
            DESCRIPTION
                "The power amplifier supply voltage."
            ::= { ostEntry 410 }

        
        ostRackAmpIDc OBJECT-TYPE
            SYNTAX FloatingPoint
            UNITS "Ampere"
            MAX-ACCESS read-only
            STATUS current
            DESCRIPTION
                "The power amplifier supply current."
            ::= { ostEntry 411 }

        
        ostRackAmpUDcControl OBJECT-TYPE
            SYNTAX FloatingPoint
            UNITS "Volt"
            MAX-ACCESS read-only
            STATUS current
            DESCRIPTION
                "The power supply control voltage."
            ::= { ostEntry 412 }

        
        ostRackAmpUReg OBJECT-TYPE
            SYNTAX FloatingPoint
            UNITS "Volt"
            MAX-ACCESS read-only
            STATUS current
            DESCRIPTION
                "The power amplifier AGC voltage."
            ::= { ostEntry 413 }

        
        ostRackAmpPowerA OBJECT-TYPE
            SYNTAX FloatingPoint
            UNITS "Volt"
            MAX-ACCESS read-only
            STATUS current
            DESCRIPTION
                "The voltage power detector A."
            ::= { ostEntry 414 }

        
        ostRackAmpPowerB OBJECT-TYPE
            SYNTAX FloatingPoint
            UNITS "Volt"
            MAX-ACCESS read-only
            STATUS current
            DESCRIPTION
                "The voltage power detector B."
            ::= { ostEntry 415 }

        
        ostRackAmpPowerOut OBJECT-TYPE
            SYNTAX FloatingPoint
            UNITS "Volt"
            MAX-ACCESS read-only
            STATUS current
            DESCRIPTION
                "The voltage forward power detector."
            ::= { ostEntry 416 }

        
        ostRackAmpPowerReflection OBJECT-TYPE
            SYNTAX FloatingPoint
            UNITS "Volt"
            MAX-ACCESS read-only
            STATUS current
            DESCRIPTION
                "The voltage reflected power detector."
            ::= { ostEntry 417 }

        
        ostRackAmpPowerReference OBJECT-TYPE
            SYNTAX FloatingPoint
            UNITS "Volt"
            MAX-ACCESS read-only
            STATUS current
            DESCRIPTION
                "The reference voltage for output power."
            ::= { ostEntry 418 }

        
        ostRackAmpDeltaPhase OBJECT-TYPE
            SYNTAX FloatingPoint
            UNITS "Percent"
            MAX-ACCESS read-only
            STATUS current
            DESCRIPTION
                "The measured phase delta for output power."
            ::= { ostEntry 419 }

        
        ostRackAmpCmdDeltaPhase OBJECT-TYPE
            SYNTAX FloatingPoint
            UNITS "Percent"
            MAX-ACCESS read-write
            STATUS current
            DESCRIPTION
                "The phase delta setting for output power.
                The range is -50.0% to 50.0%."
            ::= { ostEntry 420 }

        
        exciterStatusTable OBJECT-TYPE
            SYNTAX SEQUENCE OF ExciterStatusEntry
            MAX-ACCESS not-accessible
            STATUS current
            DESCRIPTION
                "Exciter status values."
            ::= { detailedInfo 20 }

        
        exciterStatusEntry OBJECT-TYPE
            SYNTAX ExciterStatusEntry
            MAX-ACCESS not-accessible
            STATUS current
            DESCRIPTION
                "A row (an entry) for one exciter."
            INDEX { excStatusExcIdx }
            ::= { exciterStatusTable 1 }

        
        ExciterStatusEntry ::=
            SEQUENCE { 
                excStatusExcIdx
                    IndexAB,
                excStatusRfOutputAgcRegulation
                    FloatingPoint,
                excStatusRfIqAdjustAuto
                    INTEGER,
                excStatusRfIqAdjustLO1Frequency
                    FloatingPoint,
                excStatusNominalPower
                    Integer32,
                excStatusVSWR
                    FloatingPoint,
                excStatusSfnDelayProcessing
                    FloatingPoint,
                excStatusSfnDelayDynamic
                    FloatingPoint,
                excStatusSfnDelayNetwork
                    FloatingPoint,
                excStatusSfnDelayTxOffset
                    FloatingPoint,
                excStatusSfnDelayMaximum
                    FloatingPoint,
                excStatusSfnDelayTotal
                    FloatingPoint,
                excStatusAmplifierControl
                    INTEGER,
                excStatusReqDataRateHP
                    Integer32,
                excStatusReqDataRateLP
                    Integer32,
                excStatusFailDelay
                    FailDelayStatus
             }

        excStatusExcIdx OBJECT-TYPE
            SYNTAX IndexAB
            MAX-ACCESS not-accessible
            STATUS current
            DESCRIPTION
                "The dedicated exciter (A/B)."
            ::= { exciterStatusEntry 3 }

        
        excStatusRfOutputAgcRegulation OBJECT-TYPE
            SYNTAX FloatingPoint
            UNITS "Percent"
            MAX-ACCESS read-only
            STATUS current
            DESCRIPTION
                "Shows the operating point of the RF regulator. The shown value should be around 50 per cent."
            ::= { exciterStatusEntry 4 }

        
        excStatusRfIqAdjustAuto OBJECT-TYPE
            SYNTAX INTEGER
                {
                notAdjusted(1),
                inProgress(2),
                adjusted(3)
                }
            UNITS "Percent"
            MAX-ACCESS read-only
            STATUS current
            DESCRIPTION
                "Automatic I/Q-Adjust."
            ::= { exciterStatusEntry 5 }

        
        excStatusRfIqAdjustLO1Frequency OBJECT-TYPE
            SYNTAX FloatingPoint
            UNITS "MHz"
            MAX-ACCESS read-only
            STATUS current
            DESCRIPTION
                "Modulator LO1."
            ::= { exciterStatusEntry 6 }

        
        excStatusNominalPower OBJECT-TYPE
            SYNTAX Integer32
            UNITS "W"
            MAX-ACCESS read-write
            STATUS current
            DESCRIPTION
                "Description."
            ::= { exciterStatusEntry 7 }

        
        excStatusVSWR OBJECT-TYPE
            SYNTAX FloatingPoint
            MAX-ACCESS read-only
            STATUS current
            DESCRIPTION
                "Voltage Standing Wave Ratio"
            ::= { exciterStatusEntry 9 }

        
        excStatusSfnDelayProcessing OBJECT-TYPE
            SYNTAX FloatingPoint
            UNITS "Microseconds"
            MAX-ACCESS read-only
            STATUS current
            DESCRIPTION
                "The Minimum signal transmit time through the exciter.
                This delay depends on the DVB transmission parameters."
            ::= { exciterStatusEntry 13 }

        
        excStatusSfnDelayDynamic OBJECT-TYPE
            SYNTAX FloatingPoint
            UNITS "Microseconds"
            MAX-ACCESS read-only
            STATUS current
            DESCRIPTION
                "The period of time by which signal processing is artificially delayed
                so that the desired time of transmission is obtained."
            ::= { exciterStatusEntry 14 }

        
        excStatusSfnDelayNetwork OBJECT-TYPE
            SYNTAX FloatingPoint
            UNITS "Microseconds"
            MAX-ACCESS read-only
            STATUS current
            DESCRIPTION
                "The signal propagation time between the play-out center
                (MIP inserter) and the exciter input. This delay depends
                on the transmission path used."
            ::= { exciterStatusEntry 15 }

        
        excStatusSfnDelayTxOffset OBJECT-TYPE
            SYNTAX FloatingPoint
            UNITS "Microseconds"
            MAX-ACCESS read-only
            STATUS current
            DESCRIPTION
                "An individual transmitter specific delay. It can be adjusted
                via data carousel of the SFN adapter. It is true for a
                specific transmitter address."
            ::= { exciterStatusEntry 16 }

        
        excStatusSfnDelayMaximum OBJECT-TYPE
            SYNTAX FloatingPoint
            UNITS "Microseconds"
            MAX-ACCESS read-only
            STATUS current
            DESCRIPTION
                "The period of time between the signal leaving the play-out center
                (MIP inserter) and its regular transmission at the antenna.
                This delay is set in the MIP inserter and serves as a basis for
                all the transmitters in the SFN."
            ::= { exciterStatusEntry 17 }

        
        excStatusSfnDelayTotal OBJECT-TYPE
            SYNTAX FloatingPoint
            UNITS "Microseconds"
            MAX-ACCESS read-only
            STATUS current
            DESCRIPTION
                "The actual signal transit time through the exciter.
                This is derived from the sum of static-, dynamic-, 
                offset- and processing delay."
            ::= { exciterStatusEntry 18 }

        
        excStatusAmplifierControl OBJECT-TYPE
            SYNTAX INTEGER
                {
                on(1),
                off(2)
                }
            MAX-ACCESS read-only
            STATUS current
            DESCRIPTION
                "Amplifier control status"
            ::= { exciterStatusEntry 20 }

        
        excStatusReqDataRateHP OBJECT-TYPE
            SYNTAX Integer32
            UNITS "bit per seconds"
            MAX-ACCESS read-only
            STATUS current
            DESCRIPTION
                "Required data rate on HP input
                with respect to the current TPS settings."
            ::= { exciterStatusEntry 30 }

        
        excStatusReqDataRateLP OBJECT-TYPE
            SYNTAX Integer32
            UNITS "bit per seconds"
            MAX-ACCESS read-only
            STATUS current
            DESCRIPTION
                "Required data rate on LP input
                with respect to the current TPS settings."
            ::= { exciterStatusEntry 31 }

        
        excStatusFailDelay OBJECT-TYPE
            SYNTAX FailDelayStatus
            MAX-ACCESS read-only
            STATUS current
            DESCRIPTION
                "Shows whether the fail delay time is qualified."
            ::= { exciterStatusEntry 40 }

        
        exciterPrecorrectionTable OBJECT-TYPE
            SYNTAX SEQUENCE OF ExciterPrecorrectionEntry
            MAX-ACCESS not-accessible
            STATUS current
            DESCRIPTION
                "Exciter status values."
            ::= { detailedInfo 21 }

        
        exciterPrecorrectionEntry OBJECT-TYPE
            SYNTAX ExciterPrecorrectionEntry
            MAX-ACCESS not-accessible
            STATUS current
            DESCRIPTION
                "A row (an entry) for one exciter."
            INDEX { excPrecExcIdx }
            ::= { exciterPrecorrectionTable 1 }

        
        ExciterPrecorrectionEntry ::=
            SEQUENCE { 
                excPrecExcIdx
                    IndexAB,
                excPrecLinCorrection
                    SwitchOnOff,
                excPrecLinAutomaticADE
                    INTEGER,
                excPrecLinMaxAmplitudeRipple
                    FloatingPoint,
                excPrecLinMaxGroupDelayRipple
                    Integer32,
                excPrecLinAmplitudeRipple
                    FloatingPoint,
                excPrecLinGroupDelayRipple
                    Integer32,
                excPrecLinInputLevel
                    INTEGER,
                excPrecLinAutomatic
                    INTEGER,
                excPrecNonlinCorrection
                    SwitchOnOff,
                excPrecNonlinAutomaticADE
                    INTEGER,
                excPrecNonlinThresholdShoulders
                    FloatingPoint,
                excPrecNonlinShoulderLeft
                    FloatingPoint,
                excPrecNonlinShoulderRight
                    FloatingPoint,
                excPrecNonlinInputLevel
                    INTEGER,
                excPrecNonlinAutomatic
                    INTEGER,
                excPrecUserState
                    EqualizerCalibrationState,
                excPrecFactoryState
                    EqualizerCalibrationState,
                excPrecRestoreCurrentSettings
                    INTEGER,
                excPrecRestoreAllSettings
                    INTEGER
             }

        excPrecExcIdx OBJECT-TYPE
            SYNTAX IndexAB
            MAX-ACCESS not-accessible
            STATUS current
            DESCRIPTION
                "The dedicated exciter (A/B)."
            ::= { exciterPrecorrectionEntry 3 }

        
        excPrecLinCorrection OBJECT-TYPE
            SYNTAX SwitchOnOff
            MAX-ACCESS read-write
            STATUS current
            DESCRIPTION
                "Switches on/turns off the linear precorrector."
            ::= { exciterPrecorrectionEntry 4 }

        
        excPrecLinAutomaticADE OBJECT-TYPE
            SYNTAX INTEGER
                {
                manual(1),
                automatic(2),
                adaptive(3)
                }
            MAX-ACCESS read-write
            STATUS current
            DESCRIPTION
                "Enables /disables the automatic precorrector. To get the ADE in work linear precorrection has to be switched on."
            ::= { exciterPrecorrectionEntry 5 }

        
        excPrecLinMaxAmplitudeRipple OBJECT-TYPE
            SYNTAX FloatingPoint
            UNITS "dB"
            MAX-ACCESS read-write
            STATUS current
            DESCRIPTION
                "Sets te maximum ripple for automatic amplitude correction (0.0 ... 2.0)."
            ::= { exciterPrecorrectionEntry 6 }

        
        excPrecLinMaxGroupDelayRipple OBJECT-TYPE
            SYNTAX Integer32 (0..500)
            UNITS "Nanoseconds"
            MAX-ACCESS read-write
            STATUS current
            DESCRIPTION
                "Sets the maximum ripple for automatic group delay correction."
            ::= { exciterPrecorrectionEntry 7 }

        
        excPrecLinAmplitudeRipple OBJECT-TYPE
            SYNTAX FloatingPoint
            UNITS "dB"
            MAX-ACCESS read-only
            STATUS current
            DESCRIPTION
                "Shows the current amplitude ripple."
            ::= { exciterPrecorrectionEntry 8 }

        
        excPrecLinGroupDelayRipple OBJECT-TYPE
            SYNTAX Integer32
            UNITS "Nanoseconds"
            MAX-ACCESS read-only
            STATUS current
            DESCRIPTION
                "Shows the current group delay ripple."
            ::= { exciterPrecorrectionEntry 9 }

        
        excPrecLinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { exciterPrecorrectionEntry 10 }

        
        excPrecLinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 11 }

        
        excPrecNonlinCorrection OBJECT-TYPE
            SYNTAX SwitchOnOff
            MAX-ACCESS read-write
            STATUS current
            DESCRIPTION
                "Switches on/turns off the nonlinear precorrector."
            ::= { exciterPrecorrectionEntry 12 }

        
        excPrecNonlinAutomaticADE OBJECT-TYPE
            SYNTAX INTEGER
                {
                manual(1),
                automatic(2),
                adaptive(3)
                }
            MAX-ACCESS read-write
            STATUS current
            DESCRIPTION
                "Enables /disables the automatic precorrector. To get the ADE in work nonlinear precorrection has to be switched on."
            ::= { exciterPrecorrectionEntry 13 }

        
        excPrecNonlinThresholdShoulders OBJECT-TYPE
            SYNTAX FloatingPoint
            UNITS "dB"
            MAX-ACCESS read-write
            STATUS current
            DESCRIPTION
                "The target shoulder distance for ADE (0.0 ... 40.0)."
            ::= { exciterPrecorrectionEntry 14 }

        
        excPrecNonlinShoulderLeft OBJECT-TYPE
            SYNTAX FloatingPoint
            UNITS "dB"
            MAX-ACCESS read-only
            STATUS current
            DESCRIPTION
                "Displays the current measurement for the left handed shoulder distance."
            ::= { exciterPrecorrectionEntry 15 }

        
        excPrecNonlinShoulderRight OBJECT-TYPE
            SYNTAX FloatingPoint
            UNITS "dB"
            MAX-ACCESS read-only
            STATUS current
            DESCRIPTION
                "Displays the current measurement of the right handed shoulder."
            ::= { exciterPrecorrectionEntry 16 }

        
        excPrecNonlinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { exciterPrecorrectionEntry 17 }

        
        excPrecNonlinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 18 }

        
        excPrecUserState OBJECT-TYPE
            SYNTAX EqualizerCalibrationState
            MAX-ACCESS read-only
            STATUS current
            DESCRIPTION
                "status of the user precorrection settings"
            ::= { exciterPrecorrectionEntry 100 }

        
        excPrecFactoryState OBJECT-TYPE
            SYNTAX EqualizerCalibrationState
            MAX-ACCESS read-only
            STATUS current
            DESCRIPTION
                "status of the factory precorrection settings"
            ::= { exciterPrecorrectionEntry 101 }

        
        excPrecRestoreCurrentSettings OBJECT-TYPE
            SYNTAX INTEGER
                {
                stop(1),
                start(2)
                }
            MAX-ACCESS read-write
            STATUS current
            DESCRIPTION
                "restores current factory precorrection setting"
            ::= { exciterPrecorrectionEntry 102 }

        
        excPrecRestoreAllSettings OBJECT-TYPE
            SYNTAX INTEGER
                {
                stop(1),
                start(2)
                }
            MAX-ACCESS read-write
            STATUS current
            DESCRIPTION
                "restores all factory precorrection settings"
            ::= { exciterPrecorrectionEntry 103 }

        
        configurationTable OBJECT-TYPE
            SYNTAX SEQUENCE OF ConfigurationEntry
            MAX-ACCESS not-accessible
            STATUS current
            DESCRIPTION
                "Table for Type Configuration parameters."
            ::= { detailedInfo 30 }

        
        configurationEntry OBJECT-TYPE
            SYNTAX ConfigurationEntry
            MAX-ACCESS not-accessible
            STATUS current
            DESCRIPTION
                "An entry for the Type Configuration parameters."
            INDEX { configTvStandardIdx }
            ::= { configurationTable 1 }

        
        ConfigurationEntry ::=
            SEQUENCE { 
                configTvStandardIdx
                    TvStandard,
                configTvStandardName
                    TvStandard,
                configRxFrequency
                    Integer32,
                configFrequency
                    Integer32,
                configPower
                    FloatingPoint,
                configInputSource
                    InputSource
             }

        configTvStandardIdx OBJECT-TYPE
            SYNTAX TvStandard
            MAX-ACCESS not-accessible
            STATUS current
            DESCRIPTION
                "The index for the TV standard."
            ::= { configurationEntry 3 }

        
        configTvStandardName OBJECT-TYPE
            SYNTAX TvStandard
            MAX-ACCESS read-only
            STATUS current
            DESCRIPTION
                "The name of the TV standard as a text."
            ::= { configurationEntry 5 }

        
        configRxFrequency OBJECT-TYPE
            SYNTAX Integer32 (160000000..910000000)
            UNITS "Hz"
            MAX-ACCESS read-write
            STATUS current
            DESCRIPTION
                "The input frequency for input 1."
            ::= { configurationEntry 6 }

        
        configFrequency OBJECT-TYPE
            SYNTAX Integer32 (47000000..1500000000)
            UNITS "Hz"
            MAX-ACCESS read-write
            STATUS current
            DESCRIPTION
                "The output frequency for input 1."
            ::= { configurationEntry 7 }

        
        configPower OBJECT-TYPE
            SYNTAX FloatingPoint
            UNITS "W"
            MAX-ACCESS read-write
            STATUS current
            DESCRIPTION
                "The output power (0.0 ... 2500.0)  for input 1."
            ::= { configurationEntry 8 }

        
        configInputSource OBJECT-TYPE
            SYNTAX InputSource
            MAX-ACCESS read-write
            STATUS current
            DESCRIPTION
                "The source for input 1."
            ::= { configurationEntry 9 }

        
        timeSchedulerTable OBJECT-TYPE
            SYNTAX SEQUENCE OF TimeSchedulerEntry
            MAX-ACCESS not-accessible
            STATUS current
            DESCRIPTION
                "Table for Time Scheduler parameters."
            ::= { detailedInfo 31 }

        
        timeSchedulerEntry OBJECT-TYPE
            SYNTAX TimeSchedulerEntry
            MAX-ACCESS not-accessible
            STATUS current
            DESCRIPTION
                "An entry in the table for the Time Scheduler parameters.
                
                A row in this table is created by setting the value of schedulerRowStatus to 
                'createAndGo' or 'createAndWait'.
                
                A row in this table is deleted by setting the value of schedulerRowStatus to 
                'destroy'."
            INDEX { schedulerDateTimeIdx }
            ::= { timeSchedulerTable 1 }

        
        TimeSchedulerEntry ::=
            SEQUENCE { 
                schedulerDateTimeIdx
                    DateAndTime,
                schedulerRowStatus
                    RowStatus,
                schedulerEvent
                    INTEGER,
                schedulerDateTime
                    DateAndTime,
                schedulerTvStandard
                    TvStandard
             }

        schedulerDateTimeIdx OBJECT-TYPE
            SYNTAX DateAndTime
            MAX-ACCESS not-accessible
            STATUS current
            DESCRIPTION
                "The DateAndTime index.
                
                Note: Deci-seconds different from 0 and UTC values are ignored.
                      The index is implemented as a Fixed length string of 8 components. The last
                      component (Deci-seconds) is always 0.
                Example:
                      The DateTime of 2008-9-15,17:45:30.0 
                      has the index: 7.216.9.15.17.45.30.0
                "
            ::= { timeSchedulerEntry 3 }

        
        schedulerRowStatus OBJECT-TYPE
            SYNTAX RowStatus
            MAX-ACCESS read-create
            STATUS current
            DESCRIPTION
                "This object is used to create and delete rows in the timeSchedulerTable."
            ::= { timeSchedulerEntry 5 }

        
        schedulerEvent OBJECT-TYPE
            SYNTAX INTEGER
                {
                daily(1),
                once(2)
                }
            MAX-ACCESS read-create
            STATUS current
            DESCRIPTION
                "The event type."
            ::= { timeSchedulerEntry 6 }

        
        schedulerDateTime OBJECT-TYPE
            SYNTAX DateAndTime
            MAX-ACCESS read-only
            STATUS current
            DESCRIPTION
                "The start date and the time of a daily or one-time event."
            ::= { timeSchedulerEntry 7 }

        
        schedulerTvStandard OBJECT-TYPE
            SYNTAX TvStandard
            MAX-ACCESS read-create
            STATUS current
            DESCRIPTION
                "The TV standard."
            ::= { timeSchedulerEntry 8 }

        
        configuration2Table OBJECT-TYPE
            SYNTAX SEQUENCE OF Configuration2Entry
            MAX-ACCESS not-accessible
            STATUS current
            DESCRIPTION
                "Table for Type Configuration parameters of input 2."
            ::= { detailedInfo 32 }

        
        configuration2Entry OBJECT-TYPE
            SYNTAX Configuration2Entry
            MAX-ACCESS not-accessible
            STATUS current
            DESCRIPTION
                "An entry for the Type Configuration parameters of input 2."
            AUGMENTS { configurationEntry }
            ::= { configuration2Table 1 }

        
        Configuration2Entry ::=
            SEQUENCE { 
                config2TvStandardName
                    TvStandard,
                config2RxFrequency
                    Integer32,
                config2Frequency
                    Integer32,
                config2Power
                    FloatingPoint,
                config2InputSource
                    InputSource
             }

        config2TvStandardName OBJECT-TYPE
            SYNTAX TvStandard
            MAX-ACCESS read-only
            STATUS current
            DESCRIPTION
                "The name of the TV standard as a text."
            ::= { configuration2Entry 5 }

        
        config2RxFrequency OBJECT-TYPE
            SYNTAX Integer32 (160000000..910000000)
            UNITS "Hz"
            MAX-ACCESS read-write
            STATUS current
            DESCRIPTION
                "The input frequency for input 2."
            ::= { configuration2Entry 6 }

        
        config2Frequency OBJECT-TYPE
            SYNTAX Integer32 (47000000..1500000000)
            UNITS "Hz"
            MAX-ACCESS read-write
            STATUS current
            DESCRIPTION
                "The output frequency for input 2."
            ::= { configuration2Entry 7 }

        
        config2Power OBJECT-TYPE
            SYNTAX FloatingPoint
            UNITS "W"
            MAX-ACCESS read-write
            STATUS current
            DESCRIPTION
                "The output power (0.0 ... 2500.0)  for input 2."
            ::= { configuration2Entry 8 }

        
        config2InputSource OBJECT-TYPE
            SYNTAX InputSource
            MAX-ACCESS read-write
            STATUS current
            DESCRIPTION
                "The source for input 2."
            ::= { configuration2Entry 9 }

        
        productInfoTable OBJECT-TYPE
            SYNTAX SEQUENCE OF ProductInfoEntry
            MAX-ACCESS not-accessible
            STATUS current
            DESCRIPTION
                "The table for product typeplates."
            ::= { detailedInfo 100 }

        
        productInfoEntry OBJECT-TYPE
            SYNTAX ProductInfoEntry
            MAX-ACCESS not-accessible
            STATUS current
            DESCRIPTION
                "A row (an entry) for one typeplate."
            INDEX { prodInfoModuleIdx, prodInfoDeviceIdx, prodInfoRackIdx, prodInfoAmpIdx }
            ::= { productInfoTable 1 }

        
        ProductInfoEntry ::=
            SEQUENCE { 
                prodInfoModuleIdx
                    ProdInfoModuleNameTv,
                prodInfoDeviceIdx
                    IndexAB,
                prodInfoRackIdx
                    IndexRack,
                prodInfoAmpIdx
                    IndexAmplifier,
                prodInfoModuleName
                    ProdInfoModuleNameTv,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime
             }

        prodInfoModuleIdx OBJECT-TYPE
            SYNTAX ProdInfoModuleNameTv
            MAX-ACCESS not-accessible
            STATUS current
            DESCRIPTION
                "The module index."
            ::= { productInfoEntry 1 }

        
        prodInfoDeviceIdx OBJECT-TYPE
            SYNTAX IndexAB
            MAX-ACCESS not-accessible
            STATUS current
            DESCRIPTION
                "The dedicated device (A/B)."
            ::= { productInfoEntry 2 }

        
        prodInfoRackIdx OBJECT-TYPE
            SYNTAX IndexRack
            MAX-ACCESS not-accessible
            STATUS current
            DESCRIPTION
                "The rack number (1..10)."
            ::= { productInfoEntry 3 }

        
        prodInfoAmpIdx OBJECT-TYPE
            SYNTAX IndexAmplifier
            MAX-ACCESS not-accessible
            STATUS current
            DESCRIPTION
                "Amplifier Index"
            ::= { productInfoEntry 4 }

        
        prodInfoModuleName OBJECT-TYPE
            SYNTAX ProdInfoModuleNameTv
            MAX-ACCESS read-only
            STATUS current
            DESCRIPTION
                "The name of the module as a text."
            ::= { productInfoEntry 5 }

        
        prodInfoSerialNumber OBJECT-TYPE
            SYNTAX ReadableString
            MAX-ACCESS read-only
            STATUS current
            DESCRIPTION
                "The serial number of the subdevice."
            ::= { productInfoEntry 6 }

        
        prodInfoIdentNumberSW OBJECT-TYPE
            SYNTAX ReadableString
            MAX-ACCESS read-only
            STATUS current
            DESCRIPTION
                "The Rohde&Schwarz identification number of the software, for example 2094.2090.02."
            ::= { productInfoEntry 7 }

        
        prodInfoVersionNumberSW OBJECT-TYPE
            SYNTAX ReadableString
            MAX-ACCESS read-only
            STATUS current
            DESCRIPTION
                "The Rohde&Schwarz revision number of the software, for example 1.2.1."
            ::= { productInfoEntry 8 }

        
        prodInfoIdentNumberHW OBJECT-TYPE
            SYNTAX ReadableString
            MAX-ACCESS read-only
            STATUS current
            DESCRIPTION
                "The Rohde&Schwarz identification number of the hardware, for example 2095.8007.02 (NetCCU)."
            ::= { productInfoEntry 9 }

        
        prodInfoVersionNumberHW OBJECT-TYPE
            SYNTAX ReadableString
            MAX-ACCESS read-only
            STATUS current
            DESCRIPTION
                "The Rohde&Schwarz revision number (product index) of the hardware, for example 03.03."
            ::= { productInfoEntry 10 }

        
        productInfoProductDateHW OBJECT-TYPE
            SYNTAX DateAndTime
            MAX-ACCESS read-only
            STATUS current
            DESCRIPTION
                "The Rohde&Schwarz production date of the hardware,"
            ::= { productInfoEntry 11 }

        
        logbook OBJECT IDENTIFIER ::= { rsXx8000DvbTxObjs 4 }

        
        netCCUNumberOfEntries OBJECT-TYPE
            SYNTAX LogbookMaxEntryNumber
            MAX-ACCESS read-only
            STATUS current
            DESCRIPTION
                "The number of entries in logbook."
            ::= { logbook 1 }

        
        netCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 2 }

        
        netCCULogbookTable OBJECT-TYPE
            SYNTAX SEQUENCE OF NetCCULogbookEntry
            MAX-ACCESS not-accessible
            STATUS current
            DESCRIPTION
                "NetCCU logbook table."
            ::= { logbook 3 }

        
        netCCULogbookEntry OBJECT-TYPE
            SYNTAX NetCCULogbookEntry
            MAX-ACCESS not-accessible
            STATUS current
            DESCRIPTION
                "This is a entry in the logbook."
            INDEX { netCCULogbookEntryIdx }
            ::= { netCCULogbookTable 1 }

        
        NetCCULogbookEntry ::=
            SEQUENCE { 
                netCCULogbookEntryIdx
                    LogbookMaxEntryNumber,
                netCCULogbookEntryNbr
                    LogbookMaxEntryNumber,
                netCCULogbookType
                    EventClass,
                netCCULogbookSlope
                    LogbookEntrySlope,
                netCCULogbookMessage
                    LogbookEntryMessagesNetCCU,
                netCCULogbookDateTime
                    DateAndTime
             }

        netCCULogbookEntryIdx OBJECT-TYPE
            SYNTAX LogbookMaxEntryNumber
            MAX-ACCESS not-accessible
            STATUS current
            DESCRIPTION
                "This is an increasing number from 1 to maximum. It is used as an index column for SNMP."
            ::= { netCCULogbookEntry 1 }

        
        netCCULogbookEntryNbr OBJECT-TYPE
            SYNTAX LogbookMaxEntryNumber
            MAX-ACCESS read-only
            STATUS current
            DESCRIPTION
                "This is the number of the logbook entry. It is an decreasing number from maximum down to 1."
            ::= { netCCULogbookEntry 2 }

        
        netCCULogbookType OBJECT-TYPE
            SYNTAX EventClass
            MAX-ACCESS read-only
            STATUS current
            DESCRIPTION
                "Can either be Fault, Warning or State."
            ::= { netCCULogbookEntry 3 }

        
        netCCULogbookSlope OBJECT-TYPE
            SYNTAX LogbookEntrySlope
            MAX-ACCESS read-only
            STATUS current
            DESCRIPTION
                "Either set (event raises) or reset (event disappears)"
            ::= { netCCULogbookEntry 4 }

        
        netCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { netCCULogbookEntry 5 }

        
        netCCULogbookDateTime OBJECT-TYPE
            SYNTAX DateAndTime
            MAX-ACCESS read-only
            STATUS current
            DESCRIPTION
                "netCCULogbookDateTime"
            ::= { netCCULogbookEntry 6 }

        
        exciterANumberOfEntries OBJECT-TYPE
            SYNTAX LogbookMaxEntryNumber
            MAX-ACCESS read-only
            STATUS current
            DESCRIPTION
                "The number of entries in logbook."
            ::= { logbook 4 }

        
        exciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 5 }

        
        exciterALogbookTable OBJECT-TYPE
            SYNTAX SEQUENCE OF ExciterALogbookEntry
            MAX-ACCESS not-accessible
            STATUS current
            DESCRIPTION
                "ExciterA logbook table."
            ::= { logbook 6 }

        
        exciterALogbookEntry OBJECT-TYPE
            SYNTAX ExciterALogbookEntry
            MAX-ACCESS not-accessible
            STATUS current
            DESCRIPTION
                "This is a entry in the logbook."
            INDEX { excALogbookEntryIdx }
            ::= { exciterALogbookTable 1 }

        
        ExciterALogbookEntry ::=
            SEQUENCE { 
                excALogbookEntryIdx
                    LogbookMaxEntryNumber,
                excALogbookEntryNbr
                    LogbookMaxEntryNumber,
                excALogbookType
                    EventClass,
                excALogbookSlope
                    LogbookEntrySlope,
                excALogbookMessage
                    LogbookEntryMessagesExcTv,
                excALogbookDateTime
                    DateAndTime
             }

        excALogbookEntryIdx OBJECT-TYPE
            SYNTAX LogbookMaxEntryNumber
            MAX-ACCESS not-accessible
            STATUS current
            DESCRIPTION
                "This is an increasing number from 1 to maximum. It is used as an index column for SNMP."
            ::= { exciterALogbookEntry 1 }

        
        excALogbookEntryNbr OBJECT-TYPE
            SYNTAX LogbookMaxEntryNumber
            MAX-ACCESS read-only
            STATUS current
            DESCRIPTION
                "This is the number of the logbook entry. It is an decreasing number from maximum down to 1."
            ::= { exciterALogbookEntry 2 }

        
        excALogbookType OBJECT-TYPE
            SYNTAX EventClass
            MAX-ACCESS read-only
            STATUS current
            DESCRIPTION
                "Can either be Fault, Warning or State."
            ::= { exciterALogbookEntry 3 }

        
        excALogbookSlope OBJECT-TYPE
            SYNTAX LogbookEntrySlope
            MAX-ACCESS read-only
            STATUS current
            DESCRIPTION
                "Either set (event raises) or reset (event disappears)"
            ::= { exciterALogbookEntry 4 }

        
        excALogbookMessage OBJECT-TYPE
            SYNTAX LogbookEntryMessagesExcTv
            MAX-ACCESS read-only
            STATUS current
            DESCRIPTION
                "See RS-XX8000-COMMON-MIB - TextualConvention for details."
            ::= { exciterALogbookEntry 5 }

        
        excALogbookDateTime OBJECT-TYPE
            SYNTAX DateAndTime
            MAX-ACCESS read-only
            STATUS current
            DESCRIPTION
                "The time of the logbook entry."
            ::= { exciterALogbookEntry 6 }

        
        outputstageANumberOfEntries OBJECT-TYPE
            SYNTAX LogbookMaxEntryNumber
            MAX-ACCESS read-only
            STATUS current
            DESCRIPTION
                "The number of entries in logbook."
            ::= { logbook 7 }

        
        outputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 8 }

        
        outputstageALogbookTable OBJECT-TYPE
            SYNTAX SEQUENCE OF OutputstageALogbookEntry
            MAX-ACCESS not-accessible
            STATUS current
            DESCRIPTION
                "OutputstageA logbook table."
            ::= { logbook 9 }

        
        outputstageALogbookEntry OBJECT-TYPE
            SYNTAX OutputstageALogbookEntry
            MAX-ACCESS not-accessible
            STATUS current
            DESCRIPTION
                "This is a entry in the logbook."
            INDEX { ostALogbookEntryIdx }
            ::= { outputstageALogbookTable 1 }

        
        OutputstageALogbookEntry ::=
            SEQUENCE { 
                ostALogbookEntryIdx
                    LogbookMaxEntryNumber,
                ostALogbookEntryNbr
                    LogbookMaxEntryNumber,
                ostALogbookType
                    EventClass,
                ostALogbookSlope
                    LogbookEntrySlope,
                ostALogbookMessage
                    LogbookEntryMessagesOST,
                ostALogbookDateTime
                    DateAndTime
             }

        ostALogbookEntryIdx OBJECT-TYPE
            SYNTAX LogbookMaxEntryNumber
            MAX-ACCESS not-accessible
            STATUS current
            DESCRIPTION
                "This is an increasing number from 1 to maximum. It is used as an index column for SNMP."
            ::= { outputstageALogbookEntry 1 }

        
        ostALogbookEntryNbr OBJECT-TYPE
            SYNTAX LogbookMaxEntryNumber
            MAX-ACCESS read-only
            STATUS current
            DESCRIPTION
                "This is the number of the logbook entry. It is an decreasing number from maximum down to 1."
            ::= { outputstageALogbookEntry 2 }

        
        ostALogbookType OBJECT-TYPE
            SYNTAX EventClass
            MAX-ACCESS read-only
            STATUS current
            DESCRIPTION
                "Can either be Fault, Warning or State."
            ::= { outputstageALogbookEntry 3 }

        
        ostALogbookSlope OBJECT-TYPE
            SYNTAX LogbookEntrySlope
            MAX-ACCESS read-only
            STATUS current
            DESCRIPTION
                "Either set (event raises) or reset (event disappears)"
            ::= { outputstageALogbookEntry 4 }

        
        ostALogbookMessage OBJECT-TYPE
            SYNTAX LogbookEntryMessagesOST
            MAX-ACCESS read-only
            STATUS current
            DESCRIPTION
                "See RS-XX8000-COMMON-MIB - TextualConvention for details."
            ::= { outputstageALogbookEntry 5 }

        
        ostALogbookDateTime OBJECT-TYPE
            SYNTAX DateAndTime
            MAX-ACCESS read-only
            STATUS current
            DESCRIPTION
                "The time of the logbook entry."
            ::= { outputstageALogbookEntry 6 }

        
        exciterBNumberOfEntries OBJECT-TYPE
            SYNTAX LogbookMaxEntryNumber
            MAX-ACCESS read-only
            STATUS current
            DESCRIPTION
                "The number of entries in logbook."
            ::= { logbook 10 }

        
        exciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 11 }

        
        exciterBLogbookTable OBJECT-TYPE
            SYNTAX SEQUENCE OF ExciterBLogbookEntry
            MAX-ACCESS not-accessible
            STATUS current
            DESCRIPTION
                "ExciterB logbook table."
            ::= { logbook 12 }

        
        exciterBLogbookEntry OBJECT-TYPE
            SYNTAX ExciterBLogbookEntry
            MAX-ACCESS not-accessible
            STATUS current
            DESCRIPTION
                "This is a entry in the logbook."
            INDEX { excBLogbookEntryIdx }
            ::= { exciterBLogbookTable 1 }

        
        ExciterBLogbookEntry ::=
            SEQUENCE { 
                excBLogbookEntryIdx
                    LogbookMaxEntryNumber,
                excBLogbookEntryNbr
                    LogbookMaxEntryNumber,
                excBLogbookType
                    EventClass,
                excBLogbookSlope
                    LogbookEntrySlope,
                excBLogbookMessage
                    LogbookEntryMessagesExcTv,
                excBLogbookDateTime
                    DateAndTime
             }

        excBLogbookEntryIdx OBJECT-TYPE
            SYNTAX LogbookMaxEntryNumber
            MAX-ACCESS not-accessible
            STATUS current
            DESCRIPTION
                "This is an increasing number from 1 to maximum. It is used as an index column for SNMP."
            ::= { exciterBLogbookEntry 1 }

        
        excBLogbookEntryNbr OBJECT-TYPE
            SYNTAX LogbookMaxEntryNumber
            MAX-ACCESS read-only
            STATUS current
            DESCRIPTION
                "This is the number of the logbook entry. It is an decreasing number from maximum down to 1."
            ::= { exciterBLogbookEntry 2 }

        
        excBLogbookType OBJECT-TYPE
            SYNTAX EventClass
            MAX-ACCESS read-only
            STATUS current
            DESCRIPTION
                "Can either be Fault, Warning or State."
            ::= { exciterBLogbookEntry 3 }

        
        excBLogbookSlope OBJECT-TYPE
            SYNTAX LogbookEntrySlope
            MAX-ACCESS read-only
            STATUS current
            DESCRIPTION
                "Either set (event raises) or reset (event disappears)"
            ::= { exciterBLogbookEntry 4 }

        
        excBLogbookMessage OBJECT-TYPE
            SYNTAX LogbookEntryMessagesExcTv
            MAX-ACCESS read-only
            STATUS current
            DESCRIPTION
                "See RS-XX8000-COMMON-MIB - TextualConvention for details."
            ::= { exciterBLogbookEntry 5 }

        
        excBLogbookDateTime OBJECT-TYPE
            SYNTAX DateAndTime
            MAX-ACCESS read-only
            STATUS current
            DESCRIPTION
                "The time of the logbook entry."
            ::= { exciterBLogbookEntry 6 }

        
        outputstageBNumberOfEntries OBJECT-TYPE
            SYNTAX LogbookMaxEntryNumber
            MAX-ACCESS read-only
            STATUS current
            DESCRIPTION
                "The number of entries in logbook."
            ::= { logbook 13 }

        
        outputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 14 }

        
        outputstageBLogbookTable OBJECT-TYPE
            SYNTAX SEQUENCE OF OutputstageBLogbookEntry
            MAX-ACCESS not-accessible
            STATUS current
            DESCRIPTION
                "OutputstageB logbook table."
            ::= { logbook 15 }

        
        outputstageBLogbookEntry OBJECT-TYPE
            SYNTAX OutputstageBLogbookEntry
            MAX-ACCESS not-accessible
            STATUS current
            DESCRIPTION
                "This is a entry in the logbook."
            INDEX { ostBLogbookEntryIdx }
            ::= { outputstageBLogbookTable 1 }

        
        OutputstageBLogbookEntry ::=
            SEQUENCE { 
                ostBLogbookEntryIdx
                    LogbookMaxEntryNumber,
                ostBLogbookEntryNbr
                    LogbookMaxEntryNumber,
                ostBLogbookType
                    EventClass,
                ostBLogbookSlope
                    LogbookEntrySlope,
                ostBLogbookMessage
                    LogbookEntryMessagesOST,
                ostBLogbookDateTime
                    DateAndTime
             }

        ostBLogbookEntryIdx OBJECT-TYPE
            SYNTAX LogbookMaxEntryNumber
            MAX-ACCESS not-accessible
            STATUS current
            DESCRIPTION
                "This is an increasing number from 1 to 128. It is used as an index column for SNMP."
            ::= { outputstageBLogbookEntry 1 }

        
        ostBLogbookEntryNbr OBJECT-TYPE
            SYNTAX LogbookMaxEntryNumber
            MAX-ACCESS read-only
            STATUS current
            DESCRIPTION
                "This is the number of the logbook entry. It is an decreasing number from max 128 down to 1."
            ::= { outputstageBLogbookEntry 2 }

        
        ostBLogbookType OBJECT-TYPE
            SYNTAX EventClass
            MAX-ACCESS read-only
            STATUS current
            DESCRIPTION
                "Can either be Fault, Warning or State."
            ::= { outputstageBLogbookEntry 3 }

        
        ostBLogbookSlope OBJECT-TYPE
            SYNTAX LogbookEntrySlope
            MAX-ACCESS read-only
            STATUS current
            DESCRIPTION
                "Either set (event raises) or reset (event disappears)"
            ::= { outputstageBLogbookEntry 4 }

        
        ostBLogbookMessage OBJECT-TYPE
            SYNTAX LogbookEntryMessagesOST
            MAX-ACCESS read-only
            STATUS current
            DESCRIPTION
                "See RS-XX8000-COMMON-MIB - TextualConvention for details."
            ::= { outputstageBLogbookEntry 5 }

        
        ostBLogbookDateTime OBJECT-TYPE
            SYNTAX DateAndTime
            MAX-ACCESS read-only
            STATUS current
            DESCRIPTION
                "The time of the logbook entry."
            ::= { outputstageBLogbookEntry 6 }

        
        rfProbesTable OBJECT-TYPE
            SYNTAX SEQUENCE OF RfProbesEntry
            MAX-ACCESS not-accessible
            STATUS current
            DESCRIPTION
                "This table contains all commands for the RF probes."
            ::= { rsXx8000DvbTxObjs 5 }

        
        rfProbesEntry OBJECT-TYPE
            SYNTAX RfProbesEntry
            MAX-ACCESS not-accessible
            STATUS current
            DESCRIPTION
                "An entry for a designated transmitter and device."
            INDEX { rfProbesOstIdx }
            ::= { rfProbesTable 1 }

        
        RfProbesEntry ::=
            SEQUENCE { 
                rfProbesNetCCURfProbe1
                    FloatingPoint,
                rfProbesNetCCURfProbe2
                    FloatingPoint,
                rfProbesAntFwdNominal
                    FloatingPoint,
                rfProbesAntFwdWarningLimit
                    FloatingPoint,
                rfProbesAntFwdFailLimit
                    FloatingPoint,
                rfProbesAntFwdDelayTimeRfFail
                    Integer32,
                rfProbesAntFwdSetOffset
                    Trigger,
                rfProbesAntFwdSetGain
                    Trigger,
                rfProbesAntReflWarningLimit
                    FloatingPoint,
                rfProbesAntReflSetOffset
                    Trigger,
                rfProbesAntReflSetGain
                    Trigger,
                rfProbesDLFwdNominal
                    FloatingPoint,
                rfProbesDLFwdWarningLimit
                    FloatingPoint,
                rfProbesDLFwdFailLimit
                    FloatingPoint,
                rfProbesDLFwdDelayTimeRfFail
                    Integer32,
                rfProbesDLFwdSetOffset
                    Trigger,
                rfProbesDLFwdSetGain
                    Trigger,
                rfProbesDLReflWarningLimit
                    FloatingPoint,
                rfProbesDLReflSetOffset
                    Trigger,
                rfProbesDLReflSetGain
                    Trigger,
                rfProbesOstIdx
                    IndexAB,
                rfProbesOstFwdNominal
                    FloatingPoint,
                rfProbesOstFwdWarningLimit
                    FloatingPoint,
                rfProbesOstFwdFailLimit
                    FloatingPoint,
                rfProbesOstFwdDelayTimeRfFail
                    Integer32,
                rfProbesOstFwdSetOffset
                    Trigger,
                rfProbesOstFwdSetGain
                    Trigger,
                rfProbesOstReflWarningLimit
                    FloatingPoint,
                rfProbesOstReflSetOffset
                    Trigger,
                rfProbesOstReflSetGain
                    Trigger
             }

        rfProbesNetCCURfProbe1 OBJECT-TYPE
            SYNTAX FloatingPoint
            UNITS "Volt"
            MAX-ACCESS read-only
            STATUS current
            DESCRIPTION
                "Current voltage on RF Probe 1."
            ::= { rfProbesEntry 1 }

        
        rfProbesNetCCURfProbe2 OBJECT-TYPE
            SYNTAX FloatingPoint
            UNITS "Volt"
            MAX-ACCESS read-only
            STATUS current
            DESCRIPTION
                "Current voltage on RF Probe 2."
            ::= { rfProbesEntry 2 }

        
        rfProbesAntFwdNominal OBJECT-TYPE
            SYNTAX FloatingPoint
            UNITS "Watt"
            MAX-ACCESS read-write
            STATUS current
            DESCRIPTION
                "This sets the nominal value [W] of the transmitter (to antenna)."
            ::= { rfProbesEntry 3 }

        
        rfProbesAntFwdWarningLimit OBJECT-TYPE
            SYNTAX FloatingPoint
            UNITS "dB"
            MAX-ACCESS read-write
            STATUS current
            DESCRIPTION
                "This sets the warning limit for the transmitters RF control (to antenna)."
            ::= { rfProbesEntry 4 }

        
        rfProbesAntFwdFailLimit OBJECT-TYPE
            SYNTAX FloatingPoint
            UNITS "dB"
            MAX-ACCESS read-write
            STATUS current
            DESCRIPTION
                "This sets the fault limit for the transmitters RF control (to antenna)."
            ::= { rfProbesEntry 5 }

        
        rfProbesAntFwdDelayTimeRfFail OBJECT-TYPE
            SYNTAX Integer32 (1..20)
            UNITS "seconds"
            MAX-ACCESS read-write
            STATUS current
            DESCRIPTION
                "This sets the delay time for the RF Fail control (to antenna)."
            ::= { rfProbesEntry 6 }

        
        rfProbesAntFwdSetOffset OBJECT-TYPE
            SYNTAX Trigger
            MAX-ACCESS read-write
            STATUS current
            DESCRIPTION
                "This triggers Set Offset."
            ::= { rfProbesEntry 7 }

        
        rfProbesAntFwdSetGain OBJECT-TYPE
            SYNTAX Trigger
            MAX-ACCESS read-write
            STATUS current
            DESCRIPTION
                "This triggers Set Gain."
            ::= { rfProbesEntry 8 }

        
        rfProbesAntReflWarningLimit OBJECT-TYPE
            SYNTAX FloatingPoint
            UNITS "dB"
            MAX-ACCESS read-write
            STATUS current
            DESCRIPTION
                "This sets the warning limit for the transmitters reflection control (to antenna)."
            ::= { rfProbesEntry 9 }

        
        rfProbesAntReflSetOffset OBJECT-TYPE
            SYNTAX Trigger
            MAX-ACCESS read-write
            STATUS current
            DESCRIPTION
                "This triggers Set Offset."
            ::= { rfProbesEntry 10 }

        
        rfProbesAntReflSetGain OBJECT-TYPE
            SYNTAX Trigger
            MAX-ACCESS read-write
            STATUS current
            DESCRIPTION
                "This triggers Set Gain."
            ::= { rfProbesEntry 11 }

        
        rfProbesDLFwdNominal OBJECT-TYPE
            SYNTAX FloatingPoint
            UNITS "Watt"
            MAX-ACCESS read-write
            STATUS current
            DESCRIPTION
                "This sets the nominal value [W] of the transmitter (to dummyload)."
            ::= { rfProbesEntry 12 }

        
        rfProbesDLFwdWarningLimit OBJECT-TYPE
            SYNTAX FloatingPoint
            UNITS "dB"
            MAX-ACCESS read-write
            STATUS current
            DESCRIPTION
                "This sets the warning limit for the transmitters RF control (to dummyload)."
            ::= { rfProbesEntry 13 }

        
        rfProbesDLFwdFailLimit OBJECT-TYPE
            SYNTAX FloatingPoint
            UNITS "dB"
            MAX-ACCESS read-write
            STATUS current
            DESCRIPTION
                "This sets the fault limit for the transmitters RF control (to dummyload)."
            ::= { rfProbesEntry 14 }

        
        rfProbesDLFwdDelayTimeRfFail OBJECT-TYPE
            SYNTAX Integer32 (1..20)
            UNITS "seconds"
            MAX-ACCESS read-write
            STATUS current
            DESCRIPTION
                "This sets the delay time for the RF Fail control (to dummyload)."
            ::= { rfProbesEntry 15 }

        
        rfProbesDLFwdSetOffset OBJECT-TYPE
            SYNTAX Trigger
            MAX-ACCESS read-write
            STATUS current
            DESCRIPTION
                "This triggers Set Offset."
            ::= { rfProbesEntry 16 }

        
        rfProbesDLFwdSetGain OBJECT-TYPE
            SYNTAX Trigger
            MAX-ACCESS read-write
            STATUS current
            DESCRIPTION
                "This triggers Set Gain."
            ::= { rfProbesEntry 17 }

        
        rfProbesDLReflWarningLimit OBJECT-TYPE
            SYNTAX FloatingPoint
            UNITS "dB"
            MAX-ACCESS read-write
            STATUS current
            DESCRIPTION
                "This sets the warning limit for the transmitters reflection control (to dummyload)."
            ::= { rfProbesEntry 18 }

        
        rfProbesDLReflSetOffset OBJECT-TYPE
            SYNTAX Trigger
            MAX-ACCESS read-write
            STATUS current
            DESCRIPTION
                "This triggers Set Offset."
            ::= { rfProbesEntry 19 }

        
        rfProbesDLReflSetGain OBJECT-TYPE
            SYNTAX Trigger
            MAX-ACCESS read-write
            STATUS current
            DESCRIPTION
                "This triggers Set Gain."
            ::= { rfProbesEntry 20 }

        
        rfProbesOstIdx OBJECT-TYPE
            SYNTAX IndexAB
            MAX-ACCESS not-accessible
            STATUS current
            DESCRIPTION
                "The dedicated outputstage (A/B)."
            ::= { rfProbesEntry 21 }

        
        rfProbesOstFwdNominal OBJECT-TYPE
            SYNTAX FloatingPoint
            UNITS "Watt"
            MAX-ACCESS read-write
            STATUS current
            DESCRIPTION
                "This sets the nominal value [W] of the outputstage."
            ::= { rfProbesEntry 22 }

        
        rfProbesOstFwdWarningLimit OBJECT-TYPE
            SYNTAX FloatingPoint
            UNITS "dB"
            MAX-ACCESS read-write
            STATUS current
            DESCRIPTION
                "This sets the warning limit for the outputstage RF control."
            ::= { rfProbesEntry 23 }

        
        rfProbesOstFwdFailLimit OBJECT-TYPE
            SYNTAX FloatingPoint
            UNITS "dB"
            MAX-ACCESS read-write
            STATUS current
            DESCRIPTION
                "This sets the fault limit for the outputstage RF control."
            ::= { rfProbesEntry 24 }

        
        rfProbesOstFwdDelayTimeRfFail OBJECT-TYPE
            SYNTAX Integer32 (1..20)
            UNITS "seconds"
            MAX-ACCESS read-write
            STATUS current
            DESCRIPTION
                "This sets the delay time for the outputstage RF Fail control."
            ::= { rfProbesEntry 25 }

        
        rfProbesOstFwdSetOffset OBJECT-TYPE
            SYNTAX Trigger
            MAX-ACCESS read-write
            STATUS current
            DESCRIPTION
                "This triggers Set Offset."
            ::= { rfProbesEntry 26 }

        
        rfProbesOstFwdSetGain OBJECT-TYPE
            SYNTAX Trigger
            MAX-ACCESS read-write
            STATUS current
            DESCRIPTION
                "This triggers Set Gain."
            ::= { rfProbesEntry 27 }

        
        rfProbesOstReflWarningLimit OBJECT-TYPE
            SYNTAX FloatingPoint
            UNITS "dB"
            MAX-ACCESS read-write
            STATUS current
            DESCRIPTION
                "This sets the warning limit for the outputstage reflection control."
            ::= { rfProbesEntry 28 }

        
        rfProbesOstReflSetOffset OBJECT-TYPE
            SYNTAX Trigger
            MAX-ACCESS read-write
            STATUS current
            DESCRIPTION
                "This triggers Set Offset."
            ::= { rfProbesEntry 29 }

        
        rfProbesOstReflSetGain OBJECT-TYPE
            SYNTAX Trigger
            MAX-ACCESS read-write
            STATUS current
            DESCRIPTION
                "This triggers Set Gain."
            ::= { rfProbesEntry 30 }

        
        rackTable OBJECT-TYPE
            SYNTAX SEQUENCE OF RackEntry
            MAX-ACCESS not-accessible
            STATUS current
            DESCRIPTION
                "This table contains important commands for the racks."
            ::= { rsXx8000DvbTxObjs 6 }

        
        rackEntry OBJECT-TYPE
            SYNTAX RackEntry
            MAX-ACCESS not-accessible
            STATUS current
            DESCRIPTION
                "An entry for a designated rack or rack's rf probe."
            INDEX { ostDeviceIdx, rackIdx, rackRfProbeIdx }
            ::= { rackTable 1 }

        
        RackEntry ::=
            SEQUENCE { 
                ostDeviceIdx
                    IndexAB,
                rackIdx
                    IndexRack,
                rackRfProbeIdx
                    INTEGER,
                amplifiersPerRack
                    Integer32,
                rackRfEventSignalling
                    TruthValue,
                rackReferenceVoltage
                    FloatingPoint,
                amplifiersPowerSupply
                    FloatingPoint,
                rackGeneralPurposeInput
                    INTEGER,
                rackOnOff
                    SwitchOnOff,
                rfProbePresent
                    TruthValue,
                rfProbeConfigurationLabel
                    ReadableString,
                rfProbeConfigurationNominalValue
                    Integer32,
                rfProbeThresholdRfFailLimit
                    FloatingPoint,
                rfProbeThresholdTimeoutRfFailCtr
                    Integer32,
                rfProbeThresholdWarningLimit
                    FloatingPoint,
                rfProbeCalibrationGain
                    FloatingPoint,
                rfProbeCalibrationOffset
                    FloatingPoint,
                rfProbeCalibrationSetGain
                    Trigger,
                rfProbeCalibrationSetOffset
                    Trigger,
                rfProbeMeasuredValue
                    FloatingPoint
             }

        ostDeviceIdx OBJECT-TYPE
            SYNTAX IndexAB
            MAX-ACCESS not-accessible
            STATUS current
            DESCRIPTION
                "The index to address outputstageA and outputstageB."
            ::= { rackEntry 2 }

        
        rackIdx OBJECT-TYPE
            SYNTAX IndexRack
            MAX-ACCESS not-accessible
            STATUS current
            DESCRIPTION
                "The index to address the racks."
            ::= { rackEntry 3 }

        
        rackRfProbeIdx OBJECT-TYPE
            SYNTAX INTEGER
                {
                forward(1),
                reflected(2)
                }
            MAX-ACCESS not-accessible
            STATUS current
            DESCRIPTION
                "The index to address forward and reflected RF probes.
                For not RF probe parameters this index is always 1."
            ::= { rackEntry 4 }

        
        amplifiersPerRack OBJECT-TYPE
            SYNTAX Integer32 (1..10)
            MAX-ACCESS read-only
            STATUS current
            DESCRIPTION
                "The number of amplifiers of a rack."
            ::= { rackEntry 6 }

        
        rackRfEventSignalling OBJECT-TYPE
            SYNTAX TruthValue
            MAX-ACCESS read-write
            STATUS current
            DESCRIPTION
                "This configures whether to signal rf events or not."
            ::= { rackEntry 7 }

        
        rackReferenceVoltage OBJECT-TYPE
            SYNTAX FloatingPoint
            UNITS "percent"
            MAX-ACCESS read-write
            STATUS current
            DESCRIPTION
                "This parameter controls the reference voltage (31.0 ... 100.0)."
            ::= { rackEntry 8 }

        
        amplifiersPowerSupply OBJECT-TYPE
            SYNTAX FloatingPoint
            UNITS "percent"
            MAX-ACCESS read-write
            STATUS current
            DESCRIPTION
                "This parameter controls the power supplies of the amplifier 
                within the rack (31.0 ... 100.0)."
            ::= { rackEntry 9 }

        
        rackGeneralPurposeInput OBJECT-TYPE
            SYNTAX INTEGER
                {
                unused(1),
                doorOpen(2),
                extCoolingWarning(3),
                extCoolingFault(4)
                }
            MAX-ACCESS read-write
            STATUS current
            DESCRIPTION
                "Setting of the general purpose input behaviour."
            ::= { rackEntry 10 }

        
        rackOnOff OBJECT-TYPE
            SYNTAX SwitchOnOff
            MAX-ACCESS read-write
            STATUS current
            DESCRIPTION
                "This switches the rack on/off."
            ::= { rackEntry 20 }

        
        rfProbePresent OBJECT-TYPE
            SYNTAX TruthValue
            MAX-ACCESS read-only
            STATUS current
            DESCRIPTION
                "If the RF probe of this rack is present."
            ::= { rackEntry 50 }

        
        rfProbeConfigurationLabel OBJECT-TYPE
            SYNTAX ReadableString (SIZE (0..12))
            MAX-ACCESS read-write
            STATUS obsolete
            DESCRIPTION
                "Name for the measured signal on RF Probe."
            ::= { rackEntry 51 }

        
        rfProbeConfigurationNominalValue OBJECT-TYPE
            SYNTAX Integer32 (0..100000)
            UNITS "W"
            MAX-ACCESS read-write
            STATUS current
            DESCRIPTION
                "The nominal value of the measured signal."
            ::= { rackEntry 52 }

        
        rfProbeThresholdRfFailLimit OBJECT-TYPE
            SYNTAX FloatingPoint
            UNITS "dB"
            MAX-ACCESS read-write
            STATUS current
            DESCRIPTION
                "Fault limit for the RF control (-20.0 ... 0.0)."
            ::= { rackEntry 55 }

        
        rfProbeThresholdTimeoutRfFailCtr OBJECT-TYPE
            SYNTAX Integer32 (1..20)
            UNITS "s"
            MAX-ACCESS read-write
            STATUS current
            DESCRIPTION
                "Timeout for RF Fail Control."
            ::= { rackEntry 56 }

        
        rfProbeThresholdWarningLimit OBJECT-TYPE
            SYNTAX FloatingPoint
            UNITS "dB"
            MAX-ACCESS read-write
            STATUS current
            DESCRIPTION
                "Warning limit for the RF control (-20.0 ... 0.0).
                
                For reflected probes:
                Warning limit for the reflection control. This limit is added to the 
                fault limit to generate the real warning limit; e.g. the fault limit 
                is -17.0dB and the warning limit is -3.0dB, so the warning is active 
                on a reflected power higher than -20.0 dB."
            ::= { rackEntry 57 }

        
        rfProbeCalibrationGain OBJECT-TYPE
            SYNTAX FloatingPoint
            UNITS "V"
            MAX-ACCESS read-only
            STATUS current
            DESCRIPTION
                "Measured value of gain calibration."
            ::= { rackEntry 60 }

        
        rfProbeCalibrationOffset OBJECT-TYPE
            SYNTAX FloatingPoint
            UNITS "V"
            MAX-ACCESS read-only
            STATUS current
            DESCRIPTION
                "Measured value of offset calibration."
            ::= { rackEntry 61 }

        
        rfProbeCalibrationSetGain OBJECT-TYPE
            SYNTAX Trigger
            MAX-ACCESS read-write
            STATUS current
            DESCRIPTION
                "Sets the gain calibration."
            ::= { rackEntry 62 }

        
        rfProbeCalibrationSetOffset OBJECT-TYPE
            SYNTAX Trigger
            MAX-ACCESS read-write
            STATUS current
            DESCRIPTION
                "Sets the offset calibration."
            ::= { rackEntry 63 }

        
        rfProbeMeasuredValue OBJECT-TYPE
            SYNTAX FloatingPoint
            UNITS "W"
            MAX-ACCESS read-only
            STATUS current
            DESCRIPTION
                "Measured forward/reflected power of antenna signal."
            ::= { rackEntry 65 }

        
        sx801AmplifierTable OBJECT-TYPE
            SYNTAX SEQUENCE OF Sx801AmplifierEntry
            MAX-ACCESS not-accessible
            STATUS current
            DESCRIPTION
                "Amplifier status values for SX801 amplifiers."
            ::= { rsXx8000DvbTxObjs 7 }

        
        sx801AmplifierEntry OBJECT-TYPE
            SYNTAX Sx801AmplifierEntry
            MAX-ACCESS not-accessible
            STATUS current
            DESCRIPTION
                "A row (an entry) for one amplifier."
            INDEX { sx801AmpIdx }
            ::= { sx801AmplifierTable 1 }

        
        Sx801AmplifierEntry ::=
            SEQUENCE { 
                sx801AmpIdx
                    IndexAmplifier,
                sx801AmpRfOut
                    Sx801AmplifierState,
                sx801AmpRfIn
                    Sx801AmplifierState,
                sx801AmpReflection
                    INTEGER,
                sx801AmpOn
                    INTEGER,
                sx801AmpAC
                    Sx801AmplifierState,
                sx801AmpCommunication
                    INTEGER,
                sx801AmpTransistor
                    Sx801AmplifierState,
                sx801AmpDriver
                    Sx801AmplifierState,
                sx801AmpTemperature
                    Sx801AmplifierState,
                sx801AmpBlower
                    Sx801AmplifierState,
                sx801AmpRegulation
                    Sx801AmplifierState,
                sx801AmpUpdate
                    TruthValue,
                sx801Supply1Temperature
                    Sx801AmplifierState,
                sx801Supply2Temperature
                    Sx801AmplifierState,
                sx801SupplyRTemperature
                    Sx801AmplifierState,
                sx801Supply1DC
                    Sx801AmplifierState,
                sx801Supply2DC
                    Sx801AmplifierState,
                sx801SupplyRDC
                    Sx801AmplifierState,
                sx801AmpValueI1
                    FloatingPoint,
                sx801AmpValueI2
                    FloatingPoint,
                sx801AmpValueI3
                    FloatingPoint,
                sx801AmpValueI4
                    FloatingPoint,
                sx801AmpValueIPre
                    FloatingPoint,
                sx801AmpValueIDrv1
                    FloatingPoint,
                sx801AmpValueIDrv2
                    FloatingPoint,
                sx801AmpValuePowerOut
                    FloatingPoint,
                sx801AmpValueReflection
                    FloatingPoint,
                sx801AmpValueVRef
                    FloatingPoint,
                sx801AmpValueVReg
                    FloatingPoint,
                sx801AmpValueTemperature
                    FloatingPoint,
                sx801AmpValueMonAtt
                    FloatingPoint,
                sx801AmpValueVAux1
                    FloatingPoint,
                sx801AmpValueVAux2
                    FloatingPoint,
                sx801Supply1ValuePwr
                    FloatingPoint,
                sx801Supply2ValuePwr
                    FloatingPoint,
                sx801Supply1ValueDc
                    FloatingPoint,
                sx801Supply2ValueDc
                    FloatingPoint
             }

        sx801AmpIdx OBJECT-TYPE
            SYNTAX IndexAmplifier
            MAX-ACCESS not-accessible
            STATUS current
            DESCRIPTION
                "The amplifier index."
            ::= { sx801AmplifierEntry 1 }

        
        sx801AmpRfOut OBJECT-TYPE
            SYNTAX Sx801AmplifierState
            MAX-ACCESS read-only
            STATUS current
            DESCRIPTION
                "Shows if the amplifier generates an RF or not.
                off(1): The amplifier output is switched off
                e.g. because the amplifier gets no input signal or the transmitter has been switched off
                warning(2): There is an RF but its level is less than the RF warning limit.
                ok(3): The RF level is greater than the RF warning limit."
            ::= { sx801AmplifierEntry 2 }

        
        sx801AmpRfIn OBJECT-TYPE
            SYNTAX Sx801AmplifierState
            MAX-ACCESS read-only
            STATUS current
            DESCRIPTION
                "Displays the state of the amplifier input.
                off(1): no input signal detected
                warning(2): the level of the input signal is too low or too high.
                ok(3): input signal is OK."
            ::= { sx801AmplifierEntry 3 }

        
        sx801AmpReflection OBJECT-TYPE
            SYNTAX INTEGER
                {
                off(1),
                warning(2),
                unknown(3),
                fault(4)
                }
            MAX-ACCESS read-only
            STATUS current
            DESCRIPTION
                " A reflection on RF output of this Amplifier module has been detected.
                This leads to a reduction of output power of the amplifier.
                
                "
            ::= { sx801AmplifierEntry 4 }

        
        sx801AmpOn OBJECT-TYPE
            SYNTAX INTEGER
                {
                off(1),
                on(3),
                unknown(4)
                }
            MAX-ACCESS read-only
            STATUS current
            DESCRIPTION
                "Shows if the amplifier has been switched on by the control unit."
            ::= { sx801AmplifierEntry 5 }

        
        sx801AmpAC OBJECT-TYPE
            SYNTAX Sx801AmplifierState
            MAX-ACCESS read-only
            STATUS current
            DESCRIPTION
                "Shows the state of primary voltage of the power supply."
            ::= { sx801AmplifierEntry 6 }

        
        sx801AmpCommunication OBJECT-TYPE
            SYNTAX INTEGER
                {
                off(1),
                unknown(2),
                ok(3),
                fault(4)
                }
            MAX-ACCESS read-only
            STATUS current
            DESCRIPTION
                "Displays if the CAN communication between amplifier and Sx801 is working or not."
            ::= { sx801AmplifierEntry 7 }

        
        sx801AmpTransistor OBJECT-TYPE
            SYNTAX Sx801AmplifierState
            MAX-ACCESS read-only
            STATUS current
            DESCRIPTION
                "A transistor fail is displayed here.
                For further information please see the amplifiers service menue."
            ::= { sx801AmplifierEntry 8 }

        
        sx801AmpDriver OBJECT-TYPE
            SYNTAX Sx801AmplifierState
            MAX-ACCESS read-only
            STATUS current
            DESCRIPTION
                "Shows a failure if one of the internal driver transistors does not work properly.
                For further information please see the amplifiers service menue."
            ::= { sx801AmplifierEntry 9 }

        
        sx801AmpTemperature OBJECT-TYPE
            SYNTAX Sx801AmplifierState
            MAX-ACCESS read-only
            STATUS current
            DESCRIPTION
                "Shows a fault if the temperature of amplifier module is too high."
            ::= { sx801AmplifierEntry 10 }

        
        sx801AmpBlower OBJECT-TYPE
            SYNTAX Sx801AmplifierState
            MAX-ACCESS read-only
            STATUS current
            DESCRIPTION
                "Displays the state of the internal blowers."
            ::= { sx801AmplifierEntry 11 }

        
        sx801AmpRegulation OBJECT-TYPE
            SYNTAX Sx801AmplifierState
            MAX-ACCESS read-only
            STATUS current
            DESCRIPTION
                "Shows a fault if the amplifier is not able to control its output power."
            ::= { sx801AmplifierEntry 12 }

        
        sx801AmpUpdate OBJECT-TYPE
            SYNTAX TruthValue
            MAX-ACCESS read-only
            STATUS current
            DESCRIPTION
                "Firmware update is in progress.
                This will be started automatically during a software update procedure of the transmitter."
            ::= { sx801AmplifierEntry 13 }

        
        sx801Supply1Temperature OBJECT-TYPE
            SYNTAX Sx801AmplifierState
            MAX-ACCESS read-only
            STATUS current
            DESCRIPTION
                "Shows a fault if the temperature of power supply one is too high."
            ::= { sx801AmplifierEntry 14 }

        
        sx801Supply2Temperature OBJECT-TYPE
            SYNTAX Sx801AmplifierState
            MAX-ACCESS read-only
            STATUS current
            DESCRIPTION
                "Shows a fault if the temperature of power supply two is too high."
            ::= { sx801AmplifierEntry 15 }

        
        sx801SupplyRTemperature OBJECT-TYPE
            SYNTAX Sx801AmplifierState
            MAX-ACCESS read-only
            STATUS current
            DESCRIPTION
                "Shows a fault if the temperature of the reserve power supply is too high."
            ::= { sx801AmplifierEntry 16 }

        
        sx801Supply1DC OBJECT-TYPE
            SYNTAX Sx801AmplifierState
            MAX-ACCESS read-only
            STATUS current
            DESCRIPTION
                "Shows a fault if the output voltage of power supply one is not ok."
            ::= { sx801AmplifierEntry 17 }

        
        sx801Supply2DC OBJECT-TYPE
            SYNTAX Sx801AmplifierState
            MAX-ACCESS read-only
            STATUS current
            DESCRIPTION
                "Shows a fault if the output voltage of power supply two is not ok."
            ::= { sx801AmplifierEntry 18 }

        
        sx801SupplyRDC OBJECT-TYPE
            SYNTAX Sx801AmplifierState
            MAX-ACCESS read-only
            STATUS current
            DESCRIPTION
                "Shows a fault if the output voltage of the reserve power supply is not ok."
            ::= { sx801AmplifierEntry 19 }

        
        sx801AmpValueI1 OBJECT-TYPE
            SYNTAX FloatingPoint
            UNITS "Ampere"
            MAX-ACCESS read-only
            STATUS current
            DESCRIPTION
                "The internal current from transistor pair 1."
            ::= { sx801AmplifierEntry 50 }

        
        sx801AmpValueI2 OBJECT-TYPE
            SYNTAX FloatingPoint
            UNITS "Ampere"
            MAX-ACCESS read-only
            STATUS current
            DESCRIPTION
                "The internal current from transistor pair 2."
            ::= { sx801AmplifierEntry 51 }

        
        sx801AmpValueI3 OBJECT-TYPE
            SYNTAX FloatingPoint
            UNITS "Ampere"
            MAX-ACCESS read-only
            STATUS current
            DESCRIPTION
                "The internal current from transistor pair 3."
            ::= { sx801AmplifierEntry 52 }

        
        sx801AmpValueI4 OBJECT-TYPE
            SYNTAX FloatingPoint
            UNITS "Ampere"
            MAX-ACCESS read-only
            STATUS current
            DESCRIPTION
                "The internal current from transistor pair 4."
            ::= { sx801AmplifierEntry 53 }

        
        sx801AmpValueIPre OBJECT-TYPE
            SYNTAX FloatingPoint
            UNITS "Ampere"
            MAX-ACCESS read-only
            STATUS current
            DESCRIPTION
                "The internal current from preamplifier."
            ::= { sx801AmplifierEntry 54 }

        
        sx801AmpValueIDrv1 OBJECT-TYPE
            SYNTAX FloatingPoint
            UNITS "Ampere"
            MAX-ACCESS read-only
            STATUS current
            DESCRIPTION
                "The internal current from driver transistor pair 1."
            ::= { sx801AmplifierEntry 55 }

        
        sx801AmpValueIDrv2 OBJECT-TYPE
            SYNTAX FloatingPoint
            UNITS "Ampere"
            MAX-ACCESS read-only
            STATUS current
            DESCRIPTION
                "The internal current from driver transistor pair 2."
            ::= { sx801AmplifierEntry 56 }

        
        sx801AmpValuePowerOut OBJECT-TYPE
            SYNTAX FloatingPoint
            UNITS "Watt"
            MAX-ACCESS read-only
            STATUS current
            DESCRIPTION
                "The base value in Volt to calculate the output power
                of this amplifier module."
            ::= { sx801AmplifierEntry 57 }

        
        sx801AmpValueReflection OBJECT-TYPE
            SYNTAX FloatingPoint
            UNITS "Watt"
            MAX-ACCESS read-only
            STATUS current
            DESCRIPTION
                "The base value in Volt for detection of reflections."
            ::= { sx801AmplifierEntry 58 }

        
        sx801AmpValueVRef OBJECT-TYPE
            SYNTAX FloatingPoint
            UNITS "Volt"
            MAX-ACCESS read-only
            STATUS current
            DESCRIPTION
                "The internal reference voltage to set the output power."
            ::= { sx801AmplifierEntry 59 }

        
        sx801AmpValueVReg OBJECT-TYPE
            SYNTAX FloatingPoint
            UNITS "Volt"
            MAX-ACCESS read-only
            STATUS current
            DESCRIPTION
                "The internal value for output power regulation."
            ::= { sx801AmplifierEntry 60 }

        
        sx801AmpValueTemperature OBJECT-TYPE
            SYNTAX FloatingPoint
            UNITS "degree Celsius"
            MAX-ACCESS read-only
            STATUS current
            DESCRIPTION
                "The internal temperature of Amplifier.
                In case of L-band amplifier, the shown temperature is valid only,
                if the amplifier is switched on."
            ::= { sx801AmplifierEntry 61 }

        
        sx801AmpValueMonAtt OBJECT-TYPE
            SYNTAX FloatingPoint
            UNITS "dB"
            MAX-ACCESS read-only
            STATUS current
            DESCRIPTION
                "The attenuation of monitoring output on the front of the
                amplifier module (Amp RF Mon)."
            ::= { sx801AmplifierEntry 62 }

        
        sx801AmpValueVAux1 OBJECT-TYPE
            SYNTAX FloatingPoint
            UNITS "Volt"
            MAX-ACCESS read-only
            STATUS current
            DESCRIPTION
                "The voltage power detector 1."
            ::= { sx801AmplifierEntry 63 }

        
        sx801AmpValueVAux2 OBJECT-TYPE
            SYNTAX FloatingPoint
            UNITS "Volt"
            MAX-ACCESS read-only
            STATUS current
            DESCRIPTION
                "The voltage power detector 2."
            ::= { sx801AmplifierEntry 64 }

        
        sx801Supply1ValuePwr OBJECT-TYPE
            SYNTAX FloatingPoint
            UNITS "Volt"
            MAX-ACCESS read-only
            STATUS current
            DESCRIPTION
                "The power supply one control voltage."
            ::= { sx801AmplifierEntry 65 }

        
        sx801Supply2ValuePwr OBJECT-TYPE
            SYNTAX FloatingPoint
            UNITS "Volt"
            MAX-ACCESS read-only
            STATUS current
            DESCRIPTION
                "The power supply two control voltage."
            ::= { sx801AmplifierEntry 66 }

        
        sx801Supply1ValueDc OBJECT-TYPE
            SYNTAX FloatingPoint
            UNITS "Volt"
            MAX-ACCESS read-only
            STATUS current
            DESCRIPTION
                "The internal supply voltage of transistor path two.
                In systems with two power supplies this value is equal
                to the output voltage of supply one."
            ::= { sx801AmplifierEntry 67 }

        
        sx801Supply2ValueDc OBJECT-TYPE
            SYNTAX FloatingPoint
            UNITS "Volt"
            MAX-ACCESS read-only
            STATUS current
            DESCRIPTION
                "The internal supply voltage of transistor path two.
                In systems with two power supplies this value is equal
                to the output voltage of supply two."
            ::= { sx801AmplifierEntry 68 }

        
-- *****************************************************************************
-- **          event definitions
-- *****************************************************************************
        rsXx8000DvbTxEvents OBJECT IDENTIFIER ::= { rsXx8000DvbTx 3 }

        
-- *****************************************************************************
-- **          events transmitter
-- *****************************************************************************
        eventTx OBJECT IDENTIFIER ::= { rsXx8000DvbTxEvents 2 }

        
        eventsTxV2 OBJECT-IDENTITY
            STATUS current
            DESCRIPTION 
                "Compatibility to SMIv1."
            ::= { eventTx 0 }

        
        txSummaryFault NOTIFICATION-TYPE
            OBJECTS { eventAlarmPriority, eventAlarmClass, eventEvent }
            STATUS current
            DESCRIPTION 
                "Transmitter Summary Fault"
            ::= { eventsTxV2 1 }

        
        txSummaryWarning NOTIFICATION-TYPE
            OBJECTS { eventAlarmPriority, eventAlarmClass, eventEvent }
            STATUS current
            DESCRIPTION 
                "Transmitter Summary Warning"
            ::= { eventsTxV2 2 }

        
        txLocal NOTIFICATION-TYPE
            OBJECTS { eventAlarmPriority, eventAlarmClass, eventEvent }
            STATUS current
            DESCRIPTION 
                "Transmitter Local/Remote"
            ::= { eventsTxV2 3 }

        
        txRfOn NOTIFICATION-TYPE
            OBJECTS { eventAlarmPriority, eventAlarmClass, eventEvent }
            STATUS current
            DESCRIPTION 
                "Transmitter RF On/Off"
            ::= { eventsTxV2 4 }

        
        txRfOk NOTIFICATION-TYPE
            OBJECTS { eventAlarmPriority, eventAlarmClass, eventEvent }
            STATUS current
            DESCRIPTION 
                "Transmitter RF Ok / Not OK"
            ::= { eventsTxV2 5 }

        
        txParamSetSubDeviceDiffers NOTIFICATION-TYPE
            OBJECTS { eventAlarmPriority, eventAlarmClass, eventEvent }
            STATUS obsolete
            DESCRIPTION 
                "Parameterset of subdevice is different.
                The currently loaded parameterset is inconsistent because
                a subdevice (e.g. an exciter) has a different configuration than expected.
                To correct this, save settings to the current or save a complete new."
            ::= { eventsTxV2 6 }

        
        txParamSetValuesChanged NOTIFICATION-TYPE
            OBJECTS { eventAlarmPriority, eventAlarmClass, eventEvent }
            STATUS current
            DESCRIPTION 
                "Value Of Current Parameterset Changed.
                The currently loaded parameterset is inconsistent because
                there were changes happening since the load/save of it.
                To correct this, save settings to the current or save a complete new."
            ::= { eventsTxV2 7 }

        
        txRfLoopProgram NOTIFICATION-TYPE
            OBJECTS { eventAlarmPriority, eventAlarmClass, eventEvent }
            STATUS current
            DESCRIPTION 
                "NetCCU Loop Program"
            ::= { eventsTxV2 8 }

        
        txRfLoopReserve NOTIFICATION-TYPE
            OBJECTS { eventAlarmPriority, eventAlarmClass, eventEvent }
            STATUS current
            DESCRIPTION 
                "NetCCU Loop Reserve"
            ::= { eventsTxV2 9 }

        
        txRfWarning NOTIFICATION-TYPE
            OBJECTS { eventAlarmPriority, eventAlarmClass, eventEvent }
            STATUS current
            DESCRIPTION 
                "NetCCU RF Warning"
            ::= { eventsTxV2 10 }

        
        txReflectionWarning NOTIFICATION-TYPE
            OBJECTS { eventAlarmPriority, eventAlarmClass, eventEvent }
            STATUS current
            DESCRIPTION 
                "NetCCU Reflection Warning"
            ::= { eventsTxV2 11 }

        
        txNetCCUFanFault NOTIFICATION-TYPE
            OBJECTS { eventAlarmPriority, eventAlarmClass, eventEvent }
            STATUS current
            DESCRIPTION 
                "NetCCU Fan Fault.
                This is valid, if Fan Control is switched on (see menu NetCCU Setup - Common)."
            ::= { eventsTxV2 12 }

        
        txNetCCUPowerSupply NOTIFICATION-TYPE
            OBJECTS { eventAlarmPriority, eventAlarmClass, eventEvent }
            STATUS current
            DESCRIPTION 
                "NetCCU Power Supply"
            ::= { eventsTxV2 13 }

        
        txRfFail NOTIFICATION-TYPE
            OBJECTS { eventAlarmPriority, eventAlarmClass, eventEvent }
            STATUS current
            DESCRIPTION 
                "NetCCU RF Fail"
            ::= { eventsTxV2 14 }

        
        txReflectionFault NOTIFICATION-TYPE
            OBJECTS { eventAlarmPriority, eventAlarmClass, eventEvent }
            STATUS current
            DESCRIPTION 
                "NetCCU Reflection Fault"
            ::= { eventsTxV2 15 }

        
        txNetCCUBoardTemperatureFault NOTIFICATION-TYPE
            OBJECTS { eventAlarmPriority, eventAlarmClass, eventEvent }
            STATUS deprecated
            DESCRIPTION 
                "NetCCU Board Temperature Fault
                
                deprecated: this information is now handled as a warning
                (txNetCCUBoardTemperatureWarning)"
            ::= { eventsTxV2 16 }

        
        txNetCCUNoConnectionToExcA NOTIFICATION-TYPE
            OBJECTS { eventAlarmPriority, eventAlarmClass, eventEvent }
            STATUS current
            DESCRIPTION 
                "NetCCU Connection To ExciterA Faulty"
            ::= { eventsTxV2 17 }

        
        txNetCCUNoConnectionToOstA NOTIFICATION-TYPE
            OBJECTS { eventAlarmPriority, eventAlarmClass, eventEvent }
            STATUS current
            DESCRIPTION 
                "NetCCU Connection To OutputstageA Faulty"
            ::= { eventsTxV2 18 }

        
        txNetCCUNoConnectionToExcB NOTIFICATION-TYPE
            OBJECTS { eventAlarmPriority, eventAlarmClass, eventEvent }
            STATUS current
            DESCRIPTION 
                "NetCCU Connection To ExciterB Faulty"
            ::= { eventsTxV2 19 }

        
        txNetCCUNoConnectionToOstB NOTIFICATION-TYPE
            OBJECTS { eventAlarmPriority, eventAlarmClass, eventEvent }
            STATUS current
            DESCRIPTION 
                "NetCCU Connection To OutputstageB Faulty"
            ::= { eventsTxV2 20 }

        
        txAutomaticExcReady NOTIFICATION-TYPE
            OBJECTS { eventAlarmPriority, eventAlarmClass, eventEvent }
            STATUS current
            DESCRIPTION 
                "Exciter Automatic Ready."
            ::= { eventsTxV2 21 }

        
        txAutomaticExcChanged NOTIFICATION-TYPE
            OBJECTS { eventAlarmPriority, eventAlarmClass, eventEvent }
            STATUS current
            DESCRIPTION 
                "Exciter Automatic Changed."
            ::= { eventsTxV2 22 }

        
        txAutomaticExcFault NOTIFICATION-TYPE
            OBJECTS { eventAlarmPriority, eventAlarmClass, eventEvent }
            STATUS current
            DESCRIPTION 
                "Exciter Automatic Fault."
            ::= { eventsTxV2 23 }

        
        txAutomaticOstReady NOTIFICATION-TYPE
            OBJECTS { eventAlarmPriority, eventAlarmClass, eventEvent }
            STATUS current
            DESCRIPTION 
                "Outputstage Automatic Ready.
                
                This paramter is only available for systems with an automatic output switch."
            ::= { eventsTxV2 24 }

        
        txAutomaticOstChanged NOTIFICATION-TYPE
            OBJECTS { eventAlarmPriority, eventAlarmClass, eventEvent }
            STATUS current
            DESCRIPTION 
                "Outputstage Automatic Changed.
                
                This paramter is only available for systems with an automatic output switch."
            ::= { eventsTxV2 25 }

        
        txAutomaticOstFault NOTIFICATION-TYPE
            OBJECTS { eventAlarmPriority, eventAlarmClass, eventEvent }
            STATUS current
            DESCRIPTION 
                "Outputstage Automatic Fault.
                
                This paramter is only available for systems with an automatic output switch."
            ::= { eventsTxV2 26 }

        
        txNetCCUBoardTemperatureWarning NOTIFICATION-TYPE
            OBJECTS { eventAlarmPriority, eventAlarmClass, eventEvent }
            STATUS current
            DESCRIPTION 
                "NetCCU Board Temperature Warning"
            ::= { eventsTxV2 27 }

        
        txInternalPowerSupplyWarning NOTIFICATION-TYPE
            OBJECTS { eventAlarmPriority, eventAlarmClass, eventEvent }
            STATUS current
            DESCRIPTION 
                "NetCCU internal Power Supply warning"
            ::= { eventsTxV2 30 }

        
        txExternalPowerSupplyWarning NOTIFICATION-TYPE
            OBJECTS { eventAlarmPriority, eventAlarmClass, eventEvent }
            STATUS current
            DESCRIPTION 
                "NetCCU external (additional) Power Supply warning"
            ::= { eventsTxV2 31 }

        
        txModeSwitchOverStarted NOTIFICATION-TYPE
            OBJECTS { eventAlarmPriority, eventAlarmClass, eventEvent }
            STATUS current
            DESCRIPTION 
                "Switch over of TX mode started."
            ::= { eventsTxV2 35 }

        
        txModeSwitchOverEnded NOTIFICATION-TYPE
            OBJECTS { eventAlarmPriority, eventAlarmClass, eventEvent }
            STATUS current
            DESCRIPTION 
                "Switch over of TX mode ended."
            ::= { eventsTxV2 36 }

        
        txModeInconsistent NOTIFICATION-TYPE
            OBJECTS { eventAlarmPriority, eventAlarmClass, eventEvent }
            STATUS current
            DESCRIPTION 
                "An inconsistency in configuration of TX mode was detected.
                The CCU and exiter configurations are incompatible."
            ::= { eventsTxV2 37 }

        
        txModeSwitchOverFailed NOTIFICATION-TYPE
            OBJECTS { eventAlarmPriority, eventAlarmClass, eventEvent }
            STATUS current
            DESCRIPTION 
                "Switch over of TX mode failed.
                Please check whether the configurations of CCU and exciter are correct."
            ::= { eventsTxV2 38 }

        
        txExcSummaryFault NOTIFICATION-TYPE
            OBJECTS { eventAlarmPriority, eventAlarmClass, eventEvent, indexAB }
            STATUS current
            DESCRIPTION 
                "Exciter Summary Fault"
            ::= { eventsTxV2 100 }

        
        txExcSummaryWarning NOTIFICATION-TYPE
            OBJECTS { eventAlarmPriority, eventAlarmClass, eventEvent, indexAB }
            STATUS current
            DESCRIPTION 
                "Exciter Summary Warning"
            ::= { eventsTxV2 101 }

        
        txExcLocal NOTIFICATION-TYPE
            OBJECTS { eventAlarmPriority, eventAlarmClass, eventEvent, indexAB }
            STATUS current
            DESCRIPTION 
                "Exciter Local/Remote"
            ::= { eventsTxV2 102 }

        
        txExcRfOk NOTIFICATION-TYPE
            OBJECTS { eventAlarmPriority, eventAlarmClass, eventEvent, indexAB }
            STATUS current
            DESCRIPTION 
                "Exciter RF Ok"
            ::= { eventsTxV2 104 }

        
        txExcInputNoConnectHP1 NOTIFICATION-TYPE
            OBJECTS { eventAlarmPriority, eventAlarmClass, eventEvent, indexAB }
            STATUS current
            DESCRIPTION 
                "Exciter Input HP1 has no connected input signal"
            ::= { eventsTxV2 105 }

        
        txExcInputNoConnectLP1 NOTIFICATION-TYPE
            OBJECTS { eventAlarmPriority, eventAlarmClass, eventEvent, indexAB }
            STATUS current
            DESCRIPTION 
                "Exciter Input LP1 has no connected input signal"
            ::= { eventsTxV2 106 }

        
        txExcInputNoConnectHP2 NOTIFICATION-TYPE
            OBJECTS { eventAlarmPriority, eventAlarmClass, eventEvent, indexAB }
            STATUS current
            DESCRIPTION 
                "Exciter Input HP2 has no connected input signal"
            ::= { eventsTxV2 107 }

        
        txExcInputNoConnectLP2 NOTIFICATION-TYPE
            OBJECTS { eventAlarmPriority, eventAlarmClass, eventEvent, indexAB }
            STATUS current
            DESCRIPTION 
                "Exciter Input LP2 has no connected input signal"
            ::= { eventsTxV2 108 }

        
        txExcInputActiveHP1 NOTIFICATION-TYPE
            OBJECTS { eventAlarmPriority, eventAlarmClass, eventEvent, indexAB }
            STATUS current
            DESCRIPTION 
                "Exciter Input HP1 is active"
            ::= { eventsTxV2 109 }

        
        txExcInputActiveLP1 NOTIFICATION-TYPE
            OBJECTS { eventAlarmPriority, eventAlarmClass, eventEvent, indexAB }
            STATUS current
            DESCRIPTION 
                "Exciter Input LP1 is active"
            ::= { eventsTxV2 110 }

        
        txExcInputActiveHP2 NOTIFICATION-TYPE
            OBJECTS { eventAlarmPriority, eventAlarmClass, eventEvent, indexAB }
            STATUS current
            DESCRIPTION 
                "Exciter Input HP2 is active"
            ::= { eventsTxV2 111 }

        
        txExcInputActiveLP2 NOTIFICATION-TYPE
            OBJECTS { eventAlarmPriority, eventAlarmClass, eventEvent, indexAB }
            STATUS current
            DESCRIPTION 
                "Exciter Input LP2 is active"
            ::= { eventsTxV2 112 }

        
        txExcOn NOTIFICATION-TYPE
            OBJECTS { eventAlarmPriority, eventAlarmClass, eventEvent, indexAB }
            STATUS current
            DESCRIPTION 
                "Exciter On"
            ::= { eventsTxV2 113 }

        
        txExcRfOn NOTIFICATION-TYPE
            OBJECTS { eventAlarmPriority, eventAlarmClass, eventEvent, indexAB }
            STATUS current
            DESCRIPTION 
                "Exciter RF On"
            ::= { eventsTxV2 114 }

        
        txExcNoInput NOTIFICATION-TYPE
            OBJECTS { eventAlarmPriority, eventAlarmClass, eventEvent, indexAB }
            STATUS current
            DESCRIPTION 
                "Exciter has no valid input signal."
            ::= { eventsTxV2 115 }

        
        txExcRfLoop NOTIFICATION-TYPE
            OBJECTS { eventAlarmPriority, eventAlarmClass, eventEvent, indexAB }
            STATUS current
            DESCRIPTION 
                "Exciter RF loop"
            ::= { eventsTxV2 116 }

        
        txExcRfFail NOTIFICATION-TYPE
            OBJECTS { eventAlarmPriority, eventAlarmClass, eventEvent, indexAB }
            STATUS current
            DESCRIPTION 
                "Exciter RF Fail"
            ::= { eventsTxV2 117 }

        
        txExcSelfTest NOTIFICATION-TYPE
            OBJECTS { eventAlarmPriority, eventAlarmClass, eventEvent, indexAB }
            STATUS current
            DESCRIPTION 
                "Exciter hardware self test"
            ::= { eventsTxV2 118 }

        
        txExcOutputOpen NOTIFICATION-TYPE
            OBJECTS { eventAlarmPriority, eventAlarmClass, eventEvent, indexAB }
            STATUS current
            DESCRIPTION 
                "Exciter output open"
            ::= { eventsTxV2 119 }

        
        txExcBoardTemperatureWarning NOTIFICATION-TYPE
            OBJECTS { eventAlarmPriority, eventAlarmClass, eventEvent, indexAB }
            STATUS current
            DESCRIPTION 
                "Exciter Board Temperature"
            ::= { eventsTxV2 120 }

        
        txExcFanWarning NOTIFICATION-TYPE
            OBJECTS { eventAlarmPriority, eventAlarmClass, eventEvent, indexAB }
            STATUS current
            DESCRIPTION 
                "Exciter has one faulty fan"
            ::= { eventsTxV2 121 }

        
        txExcFanFault NOTIFICATION-TYPE
            OBJECTS { eventAlarmPriority, eventAlarmClass, eventEvent, indexAB }
            STATUS current
            DESCRIPTION 
                "Both exciter fans are faulty."
            ::= { eventsTxV2 122 }

        
        txExcFifoWarning NOTIFICATION-TYPE
            OBJECTS { eventAlarmPriority, eventAlarmClass, eventEvent, indexAB }
            STATUS current
            DESCRIPTION 
                "Exciter Fifo"
            ::= { eventsTxV2 123 }

        
        txExcTestSignal NOTIFICATION-TYPE
            OBJECTS { eventAlarmPriority, eventAlarmClass, eventEvent, indexAB }
            STATUS current
            DESCRIPTION 
                "Exciter Testsignal Active"
            ::= { eventsTxV2 124 }

        
        txExcSFNDelay NOTIFICATION-TYPE
            OBJECTS { eventAlarmPriority, eventAlarmClass, eventEvent, indexAB }
            STATUS current
            DESCRIPTION 
                "Exciter SFN Delay Fault"
            ::= { eventsTxV2 125 }

        
        txExcWrongDatarate NOTIFICATION-TYPE
            OBJECTS { eventAlarmPriority, eventAlarmClass, eventEvent, indexAB }
            STATUS current
            DESCRIPTION 
                "Exciter Wrong Datarate"
            ::= { eventsTxV2 126 }

        
        txExcMute NOTIFICATION-TYPE
            OBJECTS { eventAlarmPriority, eventAlarmClass, eventEvent, indexAB }
            STATUS current
            DESCRIPTION 
                "Exciter Mute"
            ::= { eventsTxV2 127 }

        
        txExcPPSFail NOTIFICATION-TYPE
            OBJECTS { eventAlarmPriority, eventAlarmClass, eventEvent, indexAB }
            STATUS current
            DESCRIPTION 
                "Exciter PPS Fail"
            ::= { eventsTxV2 128 }

        
        txExcReferenceFail NOTIFICATION-TYPE
            OBJECTS { eventAlarmPriority, eventAlarmClass, eventEvent, indexAB }
            STATUS current
            DESCRIPTION 
                "Exciter Reference Fail"
            ::= { eventsTxV2 129 }

        
        txExcMIPFail NOTIFICATION-TYPE
            OBJECTS { eventAlarmPriority, eventAlarmClass, eventEvent, indexAB }
            STATUS current
            DESCRIPTION 
                "Exciter MIP Fail"
            ::= { eventsTxV2 130 }

        
        txExcInputAutomaticSwitchReady NOTIFICATION-TYPE
            OBJECTS { eventAlarmPriority, eventAlarmClass, eventEvent, indexAB }
            STATUS current
            DESCRIPTION 
                "Input automatic is ready."
            ::= { eventsTxV2 131 }

        
        txExcInputAutomaticChangedOver NOTIFICATION-TYPE
            OBJECTS { eventAlarmPriority, eventAlarmClass, eventEvent, indexAB }
            STATUS current
            DESCRIPTION 
                "Input automatic changed over."
            ::= { eventsTxV2 132 }

        
        txExcInputReseveMissing NOTIFICATION-TYPE
            STATUS current
            DESCRIPTION 
                "Missing input, or automatic switching enabled with only one input present.
                Disable automatic switching or press reset fault to remove this warning.
                Monitoring of a second input will start automatically if two input signals have been detected.
                
                This event will be generated only if cmdExcExpectInputReserve is set to on(1)."
            ::= { eventsTxV2 133 }

        
        txOstSummaryFault NOTIFICATION-TYPE
            OBJECTS { eventAlarmPriority, eventAlarmClass, eventEvent, indexAB }
            STATUS current
            DESCRIPTION 
                "Outputstage Summary Fault"
            ::= { eventsTxV2 200 }

        
        txOstSummaryWarning NOTIFICATION-TYPE
            OBJECTS { eventAlarmPriority, eventAlarmClass, eventEvent, indexAB }
            STATUS current
            DESCRIPTION 
                "Outputstage Summary Warning"
            ::= { eventsTxV2 201 }

        
        txOstRfOn NOTIFICATION-TYPE
            OBJECTS { eventAlarmPriority, eventAlarmClass, eventEvent, indexAB }
            STATUS current
            DESCRIPTION 
                "Outputstage RF On"
            ::= { eventsTxV2 202 }

        
        txOstRfOk NOTIFICATION-TYPE
            OBJECTS { eventAlarmPriority, eventAlarmClass, eventEvent, indexAB }
            STATUS current
            DESCRIPTION 
                "Outputstage RF Ok"
            ::= { eventsTxV2 203 }

        
        txOstNoInput NOTIFICATION-TYPE
            OBJECTS { eventAlarmPriority, eventAlarmClass, eventEvent, indexAB }
            STATUS current
            DESCRIPTION 
                "Outputstage no input signal"
            ::= { eventsTxV2 204 }

        
        txOstRfWarning NOTIFICATION-TYPE
            OBJECTS { eventAlarmPriority, eventAlarmClass, eventEvent, indexAB }
            STATUS current
            DESCRIPTION 
                "Outputstage RF Warning"
            ::= { eventsTxV2 205 }

        
        txOstReflectionWarning NOTIFICATION-TYPE
            OBJECTS { eventAlarmPriority, eventAlarmClass, eventEvent, indexAB }
            STATUS current
            DESCRIPTION 
                "Outputstage Reflection Warning"
            ::= { eventsTxV2 206 }

        
        txOstRackWarning NOTIFICATION-TYPE
            OBJECTS { eventAlarmPriority, eventAlarmClass, eventEvent, indexAB }
            STATUS current
            DESCRIPTION 
                "Outputstage Rack Warning. At least one rack has an error pending."
            ::= { eventsTxV2 207 }

        
        txOstCoolingWarning NOTIFICATION-TYPE
            OBJECTS { eventAlarmPriority, eventAlarmClass, eventEvent, indexAB }
            STATUS current
            DESCRIPTION 
                "Outputstage Cooling Warning"
            ::= { eventsTxV2 208 }

        
        txOstRfFail NOTIFICATION-TYPE
            OBJECTS { eventAlarmPriority, eventAlarmClass, eventEvent, indexAB }
            STATUS current
            DESCRIPTION 
                "Outputstage RF Fail"
            ::= { eventsTxV2 209 }

        
        txOstReflectionFault NOTIFICATION-TYPE
            OBJECTS { eventAlarmPriority, eventAlarmClass, eventEvent, indexAB }
            STATUS current
            DESCRIPTION 
                "Outputstage Reflection Fault"
            ::= { eventsTxV2 210 }

        
        txOstACFault NOTIFICATION-TYPE
            OBJECTS { eventAlarmPriority, eventAlarmClass, eventEvent, indexAB }
            STATUS current
            DESCRIPTION 
                "Outputstage AC Fault"
            ::= { eventsTxV2 211 }

        
        txOstCoolingFault NOTIFICATION-TYPE
            OBJECTS { eventAlarmPriority, eventAlarmClass, eventEvent, indexAB }
            STATUS current
            DESCRIPTION 
                "Outputstage Cooling Fault"
            ::= { eventsTxV2 212 }

        
        txOstCommFault NOTIFICATION-TYPE
            OBJECTS { eventAlarmPriority, eventAlarmClass, eventEvent, indexAB }
            STATUS current
            DESCRIPTION 
                "Outputstage Communication Fault"
            ::= { eventsTxV2 213 }

        
        txRackSumFault NOTIFICATION-TYPE
            OBJECTS { eventAlarmPriority, eventAlarmClass, eventEvent, indexAB, indexRack
                 }
            STATUS current
            DESCRIPTION 
                "Summary Fault at a designated rack.
                This event automatically leads to txOstRackWarning."
            ::= { eventsTxV2 300 }

        
        txRackSumWarning NOTIFICATION-TYPE
            OBJECTS { eventAlarmPriority, eventAlarmClass, eventEvent, indexAB, indexRack
                 }
            STATUS current
            DESCRIPTION 
                "Summary Warning at a designated rack."
            ::= { eventsTxV2 301 }

        
        txRackOn NOTIFICATION-TYPE
            OBJECTS { eventAlarmPriority, eventAlarmClass, eventEvent, indexAB, indexRack
                 }
            STATUS current
            DESCRIPTION 
                "The designated racks operation mode is on."
            ::= { eventsTxV2 302 }

        
        txRackGpiWarning NOTIFICATION-TYPE
            OBJECTS { eventAlarmPriority, eventAlarmClass, eventEvent, indexAB, indexRack
                 }
            STATUS current
            DESCRIPTION 
                "A warning on the general purpose input occurred.
                This depends on the current configuration of the GPI. (See:Rack Setup/Rack Controller)"
            ::= { eventsTxV2 303 }

        
        txRackFan1Fault NOTIFICATION-TYPE
            OBJECTS { eventAlarmPriority, eventAlarmClass, eventEvent, indexAB, indexRack
                 }
            STATUS current
            DESCRIPTION 
                "The designated rack signals a fault of fan 1."
            ::= { eventsTxV2 304 }

        
        txRackFan2Fault NOTIFICATION-TYPE
            OBJECTS { eventAlarmPriority, eventAlarmClass, eventEvent, indexAB, indexRack
                 }
            STATUS current
            DESCRIPTION 
                "The designated rack signals a fault of fan 2."
            ::= { eventsTxV2 305 }

        
        txRackCoolingSumWarning NOTIFICATION-TYPE
            OBJECTS { eventAlarmPriority, eventAlarmClass, eventEvent, indexAB, indexRack
                 }
            STATUS current
            DESCRIPTION 
                "The designated rack signals a summary cooling warning."
            ::= { eventsTxV2 306 }

        
        txRackAmplifierSumFault NOTIFICATION-TYPE
            OBJECTS { eventAlarmPriority, eventAlarmClass, eventEvent, indexAB, indexRack
                 }
            STATUS current
            DESCRIPTION 
                "The designated rack signals at least one faulty amplifier."
            ::= { eventsTxV2 307 }

        
        txRackNoLink NOTIFICATION-TYPE
            OBJECTS { eventAlarmPriority, eventAlarmClass, eventEvent, indexAB, indexRack
                 }
            STATUS current
            DESCRIPTION 
                "No communication to the designated rack."
            ::= { eventsTxV2 308 }

        
        txRackGpiFault NOTIFICATION-TYPE
            OBJECTS { eventAlarmPriority, eventAlarmClass, eventEvent, indexAB, indexRack
                 }
            STATUS current
            DESCRIPTION 
                "A fault on the general purpose input occurred.
                This depends on the current configuration of the GPI. (See:Rack Setup/Rack Controller)"
            ::= { eventsTxV2 309 }

        
        txRackTemperatureFault NOTIFICATION-TYPE
            OBJECTS { eventAlarmPriority, eventAlarmClass, eventEvent, indexAB, indexRack
                 }
            STATUS current
            DESCRIPTION 
                "The designated rack signals a temperature fault - temperature too high."
            ::= { eventsTxV2 310 }

        
        txRackACFault NOTIFICATION-TYPE
            OBJECTS { eventAlarmPriority, eventAlarmClass, eventEvent, indexAB, indexRack
                 }
            STATUS current
            DESCRIPTION 
                "The designated rack signals an AC (phase) fault."
            ::= { eventsTxV2 311 }

        
        txRackCoolingSumFault NOTIFICATION-TYPE
            OBJECTS { eventAlarmPriority, eventAlarmClass, eventEvent, indexAB, indexRack
                 }
            STATUS current
            DESCRIPTION 
                "The designated rack signals a summary cooling fault."
            ::= { eventsTxV2 312 }

        
        txRackTempFaultAbs1 NOTIFICATION-TYPE
            OBJECTS { eventAlarmPriority, eventAlarmClass, eventEvent, indexAB, indexRack
                 }
            STATUS current
            DESCRIPTION 
                "The designated rack signals a temperature fault of absorber 1."
            ::= { eventsTxV2 313 }

        
        txRackTempFaultAbs2 NOTIFICATION-TYPE
            OBJECTS { eventAlarmPriority, eventAlarmClass, eventEvent, indexAB, indexRack
                 }
            STATUS current
            DESCRIPTION 
                "The designated rack signals a temperature fault of absorber 2."
            ::= { eventsTxV2 314 }

        
        txRackDCFault NOTIFICATION-TYPE
            OBJECTS { eventAlarmPriority, eventAlarmClass, eventEvent, indexAB, indexRack
                 }
            STATUS current
            DESCRIPTION 
                "The designated rack signals a DC fault."
            ::= { eventsTxV2 315 }

        
        txRackRfOn NOTIFICATION-TYPE
            OBJECTS { eventAlarmPriority, eventAlarmClass, eventEvent, indexAB, indexRack
                 }
            STATUS current
            DESCRIPTION 
                "RF power is on."
            ::= { eventsTxV2 318 }

        
        txRackRfOk NOTIFICATION-TYPE
            OBJECTS { eventAlarmPriority, eventAlarmClass, eventEvent, indexAB, indexRack
                 }
            STATUS current
            DESCRIPTION 
                "RF power is ok."
            ::= { eventsTxV2 319 }

        
        txRackRfWarning NOTIFICATION-TYPE
            OBJECTS { eventAlarmPriority, eventAlarmClass, eventEvent, indexAB, indexRack
                 }
            STATUS current
            DESCRIPTION 
                "RF power decreased the warning threshold."
            ::= { eventsTxV2 320 }

        
        txRackRfFault NOTIFICATION-TYPE
            OBJECTS { eventAlarmPriority, eventAlarmClass, eventEvent, indexAB, indexRack
                 }
            STATUS current
            DESCRIPTION 
                "RF output power decreased the fault threshold."
            ::= { eventsTxV2 321 }

        
        txRackReflectionWarning NOTIFICATION-TYPE
            OBJECTS { eventAlarmPriority, eventAlarmClass, eventEvent, indexAB, indexRack
                 }
            STATUS current
            DESCRIPTION 
                "The reflected power increased the warning threshold"
            ::= { eventsTxV2 322 }

        
        txRackReflectionFault NOTIFICATION-TYPE
            OBJECTS { eventAlarmPriority, eventAlarmClass, eventEvent, indexAB, indexRack
                 }
            STATUS current
            DESCRIPTION 
                "The reflected power increased the fault threshold."
            ::= { eventsTxV2 323 }

        
        txRackProbeNotCalibrated NOTIFICATION-TYPE
            OBJECTS { eventAlarmPriority, eventAlarmClass, eventEvent, indexAB, indexRack
                 }
            STATUS current
            DESCRIPTION 
                "At least one probe is not calibrated."
            ::= { eventsTxV2 330 }

        
        txRackTemperatureWarning NOTIFICATION-TYPE
            OBJECTS { eventAlarmPriority, eventAlarmClass, eventEvent, indexAB, indexRack
                 }
            STATUS current
            DESCRIPTION 
                "Rack temperature exceeded the warning threshold."
            ::= { eventsTxV2 331 }

        
        txRackOvervoltProtectWarning NOTIFICATION-TYPE
            OBJECTS { eventAlarmPriority, eventAlarmClass, eventEvent, indexAB, indexRack
                 }
            STATUS current
            DESCRIPTION 
                "Overvoltage protection is out of order."
            ::= { eventsTxV2 335 }

        
        txAmpSumFault NOTIFICATION-TYPE
            OBJECTS { eventAlarmPriority, eventAlarmClass, eventEvent, indexAB, indexRack, 
                indexAmplifier }
            STATUS current
            DESCRIPTION 
                "The designated amplifier signals summary fault."
            ::= { eventsTxV2 400 }

        
        txAmpSumWarning NOTIFICATION-TYPE
            OBJECTS { eventAlarmPriority, eventAlarmClass, eventEvent, indexAB, indexRack, 
                indexAmplifier }
            STATUS current
            DESCRIPTION 
                "The designated amplifier signals summary warning."
            ::= { eventsTxV2 401 }

        
        txAmpPowerOn NOTIFICATION-TYPE
            OBJECTS { eventAlarmPriority, eventAlarmClass, eventEvent, indexAB, indexRack, 
                indexAmplifier }
            STATUS current
            DESCRIPTION 
                "The designated amplifiers power is on."
            ::= { eventsTxV2 402 }

        
        txAmpDCOk NOTIFICATION-TYPE
            OBJECTS { eventAlarmPriority, eventAlarmClass, eventEvent, indexAB, indexRack, 
                indexAmplifier }
            STATUS current
            DESCRIPTION 
                "The designated amplifiers DC is ok."
            ::= { eventsTxV2 403 }

        
        txAmpACOk NOTIFICATION-TYPE
            OBJECTS { eventAlarmPriority, eventAlarmClass, eventEvent, indexAB, indexRack, 
                indexAmplifier }
            STATUS current
            DESCRIPTION 
                "The designated amplifiers AC is ok."
            ::= { eventsTxV2 404 }

        
        txAmpRfInFail NOTIFICATION-TYPE
            OBJECTS { eventAlarmPriority, eventAlarmClass, eventEvent, indexAB, indexRack, 
                indexAmplifier }
            STATUS current
            DESCRIPTION 
                "The designated amplifier signals RF input fail."
            ::= { eventsTxV2 405 }

        
        txAmpRfFail NOTIFICATION-TYPE
            OBJECTS { eventAlarmPriority, eventAlarmClass, eventEvent, indexAB, indexRack, 
                indexAmplifier }
            STATUS current
            DESCRIPTION 
                "The designated amplifier signals RF fail."
            ::= { eventsTxV2 406 }

        
        txAmpReflectionFault NOTIFICATION-TYPE
            OBJECTS { eventAlarmPriority, eventAlarmClass, eventEvent, indexAB, indexRack, 
                indexAmplifier }
            STATUS current
            DESCRIPTION 
                "The designated amplifier signals a reflection fault."
            ::= { eventsTxV2 407 }

        
        txAmpTemperatureFault NOTIFICATION-TYPE
            OBJECTS { eventAlarmPriority, eventAlarmClass, eventEvent, indexAB, indexRack, 
                indexAmplifier }
            STATUS current
            DESCRIPTION 
                "The designated amplifier signals a temperature fault - temperature is too high."
            ::= { eventsTxV2 408 }

        
        txAmpTransistorFault NOTIFICATION-TYPE
            OBJECTS { eventAlarmPriority, eventAlarmClass, eventEvent, indexAB, indexRack, 
                indexAmplifier }
            STATUS current
            DESCRIPTION 
                "The designated amplifier signals at least one faulty transistor."
            ::= { eventsTxV2 409 }

        
        eventsTxTable OBJECT-TYPE
            SYNTAX SEQUENCE OF EventsTxEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventTx 1 }

        
        eventsTxEntry OBJECT-TYPE
            SYNTAX EventsTxEntry
            MAX-ACCESS not-accessible
            STATUS current
            DESCRIPTION
                "An event entry always consists of its indexes
                (used for addressing within redundancy systems) and 3 values:
                - name: an enumerated list of all possible notifications
                - mask: the corresponding mask (enable/disable)
                - priority: the corresponding priority (value in range 0..255)
                - event: the event itself (active/inactive)"
            INDEX { eventTxABIdx, eventTxRackIdx, eventTxAmpIdx, eventTxNameIdx }
            ::= { eventsTxTable 1 }

        
        EventsTxEntry ::=
            SEQUENCE { 
                eventTxABIdx
                    INTEGER,
                eventTxRackIdx
                    Integer32,
                eventTxAmpIdx
                    Integer32,
                eventTxNameIdx
                    EventMaxEntryNumber,
                eventTxName
                    INTEGER,
                eventTxMask
                    EventMask,
                eventTxPriority
                    EventPriority,
                eventTxEvent
                    EventState
             }

        eventTxABIdx OBJECT-TYPE
            SYNTAX INTEGER
                {
                a(1),
                b(2)
                }
            MAX-ACCESS not-accessible
            STATUS current
            DESCRIPTION
                "The value for the module A (exciterA, outputstageA) or 
                B (exciterB, outputstageB) for alarms.
                This is a helper column and therefore not-accessible."
            ::= { eventsTxEntry 1 }

        
        eventTxRackIdx OBJECT-TYPE
            SYNTAX Integer32 (1..10)
            MAX-ACCESS not-accessible
            STATUS current
            DESCRIPTION
                "The number of the designated rack.
                This is a helper column and therefore not-accessible."
            ::= { eventsTxEntry 2 }

        
        eventTxAmpIdx OBJECT-TYPE
            SYNTAX Integer32 (1..10)
            MAX-ACCESS not-accessible
            STATUS current
            DESCRIPTION
                "The number of the designated amplifier.
                This is a helper column and therefore not-accessible."
            ::= { eventsTxEntry 3 }

        
        eventTxNameIdx OBJECT-TYPE
            SYNTAX EventMaxEntryNumber
            MAX-ACCESS not-accessible
            STATUS current
            DESCRIPTION
                "The event number as integer.
                This is a helper column and therefore not-accessible."
            ::= { eventsTxEntry 4 }

        
        eventTxName OBJECT-TYPE
            SYNTAX INTEGER
                {
                txSummaryFault(1),
                txSummaryWarning(2),
                txLocal(3),
                txRfOn(4),
                txRfOk(5),
                txParamSetSubDeviceDiffers(6),
                txParamSetValuesChanged(7),
                txRfLoopProgram(8),
                txRfLoopReserve(9),
                txRfWarning(10),
                txReflectionWarning(11),
                txNetCCUFanFault(12),
                txNetCCUPowerSupply(13),
                txRfFail(14),
                txReflectionFault(15),
                txNetCCUBoardTemperatureFault(16),
                txNetCCUNoConnectionToExcA(17),
                txNetCCUNoConnectionToOstA(18),
                txNetCCUNoConnectionToExcB(19),
                txNetCCUNoConnectionToOstB(20),
                txAutomaticExcReady(21),
                txAutomaticExcChanged(22),
                txAutomaticExcFault(23),
                txAutomaticOstReady(24),
                txAutomaticOstChanged(25),
                txAutomaticOstFault(26),
                txNetCCUBoardTemperatureWarning(27),
                txInternalPowerSupplyWarning(30),
                txExternalPowerSupplyWarning(31),
                txModeSwitchOverStarted(35),
                txModeSwitchOverEnded(36),
                txModeInconsistent(37),
                txModeSwitchOverFailed(38),
                txExcSummaryFault(100),
                txExcSummaryWarning(101),
                txExcLocal(102),
                txExcRfOk(104),
                txExcInputNoConnectHP1(105),
                txExcInputNoConnectLP1(106),
                txExcInputNoConnectHP2(107),
                txExcInputNoConnectLP2(108),
                txExcInputActiveHP1(109),
                txExcInputActiveLP1(110),
                txExcInputActiveHP2(111),
                txExcInputActiveLP2(112),
                txExcOn(113),
                txExcRfOn(114),
                txExcNoInput(115),
                txExcRfLoop(116),
                txExcRfFail(117),
                txExcSelfTest(118),
                txExcOutputOpen(119),
                txExcBoardTemperatureWarning(120),
                txExcFanWarning(121),
                txExcFanFault(122),
                txExcFifoWarning(123),
                txExcTestSignal(124),
                txExcSFNDelay(125),
                txExcWrongDatarate(126),
                txExcMute(127),
                txExcPPSFail(128),
                txExcReferenceFail(129),
                txExcMIPFail(130),
                txExcInputAutomaticSwitchReady(131),
                txExcInputAutomaticChangedOver(132),
                txExcInputReseveMissing(133),
                txOstSummaryFault(200),
                txOstSummaryWarning(201),
                txOstRfOn(202),
                txOstRfOk(203),
                txOstNoInput(204),
                txOstRfWarning(205),
                txOstReflectionWarning(206),
                txOstRackWarning(207),
                txOstCoolingWarning(208),
                txOstRfFail(209),
                txOstReflectionFault(210),
                txOstACFault(211),
                txOstCoolingFault(212),
                txOstCommFault(213),
                txRackSumFault(300),
                txRackSumWarning(301),
                txRackOn(302),
                txRackGpiWarning(303),
                txRackFan1Fault(304),
                txRackFan2Fault(305),
                txRackCoolingSumWarning(306),
                txRackAmplifierSumFault(307),
                txRackNoLink(308),
                txRackGpiFault(309),
                txRackTemperatureFault(310),
                txRackACFault(311),
                txRackCoolingSumFault(312),
                txRackTempFaultAbs1(313),
                txRackTempFaultAbs2(314),
                txRackDCFault(315),
                txRackRfOn(318),
                txRackRfOk(319),
                txRackRfWarning(320),
                txRackRfFault(321),
                txRackReflectionWarning(322),
                txRackReflectionFault(323),
                txRackProbeNotCalibrated(330),
                txRackTemperatureWarning(331),
                txRackOvervoltProtectWarning(335),
                txAmpSumFault(400),
                txAmpSumWarning(401),
                txAmpPowerOn(402),
                txAmpDCOk(403),
                txAmpACOk(404),
                txAmpRfInFail(405),
                txAmpRfFail(406),
                txAmpReflectionFault(407),
                txAmpTemperatureFault(408),
                txAmpTransistorFault(409)
                }
            MAX-ACCESS read-only
            STATUS current
            DESCRIPTION
                "The event number as integer and the value as readable text.
                The enumeration correlates with the notifications under eventsTxV2."
            ::= { eventsTxEntry 5 }

        
        eventTxMask OBJECT-TYPE
            SYNTAX EventMask
            MAX-ACCESS read-write
            STATUS current
            DESCRIPTION
                "See TextualConvention for details."
            ::= { eventsTxEntry 6 }

        
        eventTxPriority OBJECT-TYPE
            SYNTAX EventPriority
            MAX-ACCESS read-write
            STATUS current
            DESCRIPTION
                "See TextualConvention for details."
            ::= { eventsTxEntry 7 }

        
        eventTxEvent OBJECT-TYPE
            SYNTAX EventState
            MAX-ACCESS read-only
            STATUS current
            DESCRIPTION
                "See TextualConvention for details."
            ::= { eventsTxEntry 8 }

        
-- *****************************************************************************
-- **          conformance statements
-- *****************************************************************************
        rsXx8000DvbTxConf OBJECT IDENTIFIER ::= { rsXx8000DvbTx 5 }

        
        rsXx8000DvbTxGroups OBJECT IDENTIFIER ::= { rsXx8000DvbTxConf 1 }

        
        groupEvents OBJECT-GROUP
            OBJECTS { eventTxName, eventTxMask, eventTxPriority, eventTxEvent }
            STATUS current
            DESCRIPTION 
                "This group includes all OIDs for event handling."
            ::= { rsXx8000DvbTxGroups 1 }

        
        groupTxCommon OBJECT-GROUP
            OBJECTS { cmdTxResetSumFault, cmdTxParametersetLoad, cmdTxParametersetSave, cmdTxOperationModeProgram, summaryFaultTx, 
                summaryWarningTx, localModeTx, rfOnTx, forwardPower, summaryFaultExcA
                 }
            STATUS current
            DESCRIPTION 
                "Group for common transmitter objects"
            ::= { rsXx8000DvbTxGroups 2 }

        
        groupEventsTxCommon NOTIFICATION-GROUP
            NOTIFICATIONS { txSummaryFault, txSummaryWarning, txLocal, txRfOn, txParamSetValuesChanged, 
                txRfLoopProgram, txRfFail, txOstSummaryFault, txOstSummaryWarning, txRfOk, 
                txOstRfOn, txRfWarning }
            STATUS current
            DESCRIPTION 
                "This group includes all alarm OIDs that are common for all reserve concepts."
            ::= { rsXx8000DvbTxGroups 3 }

        
        groupDualDrive OBJECT-GROUP
            OBJECTS { cmdTxOperationModeReserve, cmdTxOpModeExcAutomatic, cmdTxPreselectExciter, cmdTxDelayTimeExcAutomatic, exciterBNumberOfEntries, 
                exciterBLogbookClear, excBLogbookEntryNbr, excBLogbookType, excBLogbookSlope, excBLogbookMessage, 
                excBLogbookDateTime, summaryFaultExcB, exciterAutomaticReady, exciterAutomaticChanged, exciterAutomaticFault, 
                noConnectionExcB, activeExcA, activeExcB }
            STATUS current
            DESCRIPTION 
                "This group includes additional objects for reserve concepts
                DualDrive (NetCCU + 2 * exciter + outputstage)
                and
                Active/Passive Reserve (NetCCU + 2 * exciter + 2 * outputstage)
                "
            ::= { rsXx8000DvbTxGroups 4 }

        
        groupEventsDualDrive NOTIFICATION-GROUP
            NOTIFICATIONS { txRfLoopReserve, txNetCCUNoConnectionToExcB, txAutomaticExcReady, txAutomaticExcChanged, txAutomaticExcFault
                 }
            STATUS current
            DESCRIPTION 
                "This group includes additional events for reserve concepts
                DualDrive (NetCCU + 2 * exciter + outputstage)
                and
                Active/Passive Reserve (NetCCU + 2 * exciter + 2 * outputstage)
                "
            ::= { rsXx8000DvbTxGroups 5 }

        
        groupPowerReserve OBJECT-GROUP
            OBJECTS { cmdTxOpModeOstAutomatic, cmdTxPreselectOutputstage, cmdTxDelayTimeOstAutomatic, summaryFaultOstB, outputstageAutomaticReady, 
                outputstageAutomaticChanged, outputstageAutomaticFault, noConnectionOstB, activeOstA, activeOstB
                 }
            STATUS current
            DESCRIPTION 
                "This group includes additional objects for reserve concept
                Active/Passive Reserve (NetCCU + 2 * exciter + 2 * outputstage)
                For more details, refer to manual."
            ::= { rsXx8000DvbTxGroups 6 }

        
        groupEventsPowerReserve NOTIFICATION-GROUP
            NOTIFICATIONS { txNetCCUNoConnectionToOstB, txAutomaticOstReady, txAutomaticOstChanged, txAutomaticOstFault }
            STATUS current
            DESCRIPTION 
                "This group includes additional events for reserve concept
                Active/Passive Reserve (NetCCU + 2 * exciter + 2 * outputstage)
                For more details, refer to manual."
            ::= { rsXx8000DvbTxGroups 7 }

        
        groupCommonMP OBJECT-GROUP
            OBJECTS { cmdOstRefVoltageVision, cmdOstMaxOutletTempThreshold, outputstageANumberOfEntries, outputstageALogbookClear, ostALogbookEntryNbr, 
                ostALogbookType, ostALogbookSlope, ostALogbookMessage, ostALogbookDateTime, reflectedPower, 
                ostRackInletTemperature, ostRackOutletTemperature, ostRackAuxPowerSupply, amplifiersPerRack, rackRfEventSignalling, 
                rackGeneralPurposeInput, rfProbePresent, rfProbeConfigurationNominalValue, rfProbeThresholdRfFailLimit, rfProbeThresholdTimeoutRfFailCtr, 
                rfProbeThresholdWarningLimit, rfProbeCalibrationGain, rfProbeCalibrationOffset, rfProbeCalibrationSetGain, rfProbeCalibrationSetOffset, 
                rfProbeMeasuredValue }
            STATUS current
            DESCRIPTION 
                "additional objects for medium/high power"
            ::= { rsXx8000DvbTxGroups 8 }

        
        groupEventsCommonMP NOTIFICATION-GROUP
            NOTIFICATIONS { txReflectionWarning, txReflectionFault, txOstRfOk, txOstNoInput, txOstRfWarning, 
                txOstReflectionWarning, txOstRackWarning, txOstCoolingWarning, txOstRfFail, txOstReflectionFault, 
                txOstACFault, txOstCoolingFault, txOstCommFault, txRackSumFault, txRackSumWarning, 
                txRackOn, txRackGpiWarning, txRackFan1Fault, txRackFan2Fault, txRackCoolingSumWarning, 
                txRackAmplifierSumFault, txRackNoLink, txRackGpiFault, txRackTemperatureFault, txRackACFault, 
                txRackCoolingSumFault, txRackTempFaultAbs1, txRackTempFaultAbs2, txRackDCFault, txRackRfWarning, 
                txRackRfFault, txRackReflectionWarning, txRackReflectionFault, txRackRfOk, txRackRfOn, 
                txRackOvervoltProtectWarning, txRackTemperatureWarning, txRackProbeNotCalibrated }
            STATUS current
            DESCRIPTION 
                "additional events for medium/high power"
            ::= { rsXx8000DvbTxGroups 9 }

        
        groupCommonNetCCU OBJECT-GROUP
            OBJECTS { netCCUNumberOfEntries, netCCULogbookClear, netCCULogbookEntryNbr, netCCULogbookType, netCCULogbookSlope, 
                netCCULogbookMessage, netCCULogbookDateTime, powerSupply, cmdTxSystemMode, additionalPowerSupply, 
                summaryFaultOstA, noConnectionExcA, noConnectionOstA }
            STATUS current
            DESCRIPTION 
                "additional objects for transmitters with NetCCU"
            ::= { rsXx8000DvbTxGroups 10 }

        
        groupEventsCommonNetCCU NOTIFICATION-GROUP
            NOTIFICATIONS { txNetCCUFanFault, txNetCCUPowerSupply, txNetCCUNoConnectionToExcA, txNetCCUNoConnectionToOstA, txModeSwitchOverStarted, 
                txModeSwitchOverEnded, txModeInconsistent, txModeSwitchOverFailed, txNetCCUBoardTemperatureWarning }
            STATUS current
            DESCRIPTION 
                "additional events for transmitters with NetCCU"
            ::= { rsXx8000DvbTxGroups 11 }

        
        groupOstBLogbook OBJECT-GROUP
            OBJECTS { outputstageBNumberOfEntries, outputstageBLogbookClear, ostBLogbookEntryNbr, ostBLogbookType, ostBLogbookSlope, 
                ostBLogbookMessage, ostBLogbookDateTime }
            STATUS current
            DESCRIPTION 
                "objects of logbook for output stage B"
            ::= { rsXx8000DvbTxGroups 12 }

        
        groupSumProbe OBJECT-GROUP
            OBJECTS { forwardPowerOstA, reflectedPowerOstA, forwardPowerOstB, reflectedPowerOstB }
            STATUS current
            DESCRIPTION 
                "objects that are available only when sum probe exists"
            ::= { rsXx8000DvbTxGroups 14 }

        
        groupProductInfo OBJECT-GROUP
            OBJECTS { prodInfoModuleName, prodInfoSerialNumber, prodInfoIdentNumberSW, prodInfoVersionNumberSW, productInfoProductDateHW, 
                prodInfoIdentNumberHW, prodInfoVersionNumberHW }
            STATUS current
            DESCRIPTION 
                "This group includes all OIDs for device product information."
            ::= { rsXx8000DvbTxGroups 18 }

        
        groupAmpMeasureValues OBJECT-GROUP
            OBJECTS { ostRackAmpI1A, ostRackAmpI2A, ostRackAmpI3A, ostRackAmpI4A, ostRackAmpI1B, 
                ostRackAmpI2B, ostRackAmpI3B, ostRackAmpI4B, ostRackAmpIDrv, ostRackAmpUDc, 
                ostRackAmpIDc, ostRackAmpUDcControl, ostRackAmpUReg, ostRackAmpPowerA, ostRackAmpPowerB, 
                ostRackAmpPowerOut, ostRackAmpPowerReflection, ostRackAmpPowerReference, ostRackAmpDeltaPhase, ostRackAmpCmdDeltaPhase
                 }
            STATUS current
            DESCRIPTION 
                "This group includes all OIDs amplifier measure values.
                Practically, these information are not important to customers, they are needed in manufactory."
            ::= { rsXx8000DvbTxGroups 19 }

        
        groupEventsAmplifier NOTIFICATION-GROUP
            NOTIFICATIONS { txAmpSumFault, txAmpSumWarning, txAmpPowerOn, txAmpDCOk, txAmpACOk, 
                txAmpRfInFail, txAmpRfFail, txAmpReflectionFault, txAmpTemperatureFault, txAmpTransistorFault
                 }
            STATUS current
            DESCRIPTION 
                "events from the amplifier (medium/high power only)"
            ::= { rsXx8000DvbTxGroups 20 }

        
        groupRfProbes OBJECT-GROUP
            OBJECTS { rfProbesNetCCURfProbe1, rfProbesNetCCURfProbe2, rfProbesAntFwdNominal, rfProbesAntFwdWarningLimit, rfProbesAntFwdFailLimit, 
                rfProbesAntFwdDelayTimeRfFail, rfProbesAntFwdSetOffset, rfProbesAntFwdSetGain, rfProbesAntReflWarningLimit, rfProbesAntReflSetOffset, 
                rfProbesAntReflSetGain, rfProbesOstFwdNominal, rfProbesOstFwdWarningLimit, rfProbesOstFwdFailLimit, rfProbesOstFwdDelayTimeRfFail, 
                rfProbesOstFwdSetOffset, rfProbesOstFwdSetGain, rfProbesOstReflWarningLimit, rfProbesOstReflSetOffset, rfProbesOstReflSetGain
                 }
            STATUS current
            DESCRIPTION 
                "This group includes all OIDs regarding RF Probes."
            ::= { rsXx8000DvbTxGroups 21 }

        
        groupDummyLoadRF OBJECT-GROUP
            OBJECTS { rfProbesDLFwdNominal, rfProbesDLFwdWarningLimit, rfProbesDLFwdFailLimit, rfProbesDLFwdDelayTimeRfFail, rfProbesDLFwdSetOffset, 
                rfProbesDLFwdSetGain, rfProbesDLReflWarningLimit, rfProbesDLReflSetOffset, rfProbesDLReflSetGain }
            STATUS current
            DESCRIPTION 
                "This group includes all object types regarding probes from dummy load.
                The object types in this group are defined only when a dummy load measure point exists.
                This can occur in reserve concept active reserve only.
                "
            ::= { rsXx8000DvbTxGroups 22 }

        
        groupExcCommon OBJECT-GROUP
            OBJECTS { cmdExcOpModeInputAutomatic, cmdExcPreselectInput, cmdExcMode, cmdExcNetworkMode, cmdExcTPSSource, 
                cmdExcEnableCellID, cmdExcTxAddress, cmdExcTxAutomatic, cmdExcInputSeamless, cmdExcInputPriority, 
                cmdExcInputCheckTimeForward, cmdExcInputCheckTimeSwitchback, cmdExcInputMuteOnFail, cmdExcInputManualPreseletionHP1, cmdExcInputManualPreseletionHP2, 
                cmdExcInputManualPreseletionLP1, cmdExcInputManualPreseletionLP2, cmdExcTPSManualBandwidth, cmdExcTPSManualFFTLength, cmdExcTPSManualGuardInterval, 
                cmdExcTPSManualConstellation, cmdExcTPSManualCellID, cmdExcTPSManualInterleaver, cmdExcTPSManualCoderateHP, cmdExcTPSManualCoderateLP, 
                cmdExcTPSManualTimeSlicingHP, cmdExcTPSManualTimeSlicingLP, cmdExcTPSManualFECHP, cmdExcTPSManualFECLP, cmdExcSFNStaticDelay, 
                cmdExcSFNDeviationTime, cmdExcFrequency, cmdExcReferenceSource, cmdExcMuteOnPPSFail, cmdExcMuteOnReferenceFail, 
                cmdExcTypeLossOfInput, cmdExcRfOutput, cmdExcRfOutputAttenuation, cmdExcRfOutputRfSlope, cmdExcRfOutputModulationSlope, 
                cmdExcRfIqAdjustTestsignal, cmdExcRfIqAdjustBiasCoarseI, cmdExcRfIqAdjustBiasCoarseQ, cmdExcRfIqAdjustBiasFineI, cmdExcRfIqAdjustBiasFineQ, 
                cmdExcRfIqAdjustGainI, cmdExcRfIqAdjustGainQ, cmdExcRfIqAdjustPhase, cmdExcInpAutoReadyAfterChangeOv, excInputChannelName, 
                excInputConnected, excInputSeamless, excInputPreselected, excInputActive, excInputMipFail, 
                excInputBandwidth, excInputFFTLength, excInputGuardInterval, excInputConstellation, excInputCellID, 
                excInputInterleaver, excInputCodeRate, excInputPacketLength, excInputMeasuredDatarate, excInputRequiredDatarate, 
                excInputMaximumDelay, exciterANumberOfEntries, exciterALogbookClear, excALogbookEntryNbr, excALogbookType, 
                excALogbookSlope, excALogbookMessage, excALogbookDateTime, cmdExcOcxoAdjust, cmdExcExpectInputReserve, 
                excStatusReqDataRateLP, excStatusReqDataRateHP, excStatusAmplifierControl, excStatusFailDelay, cmdExcFailDelayMode, 
                cmdExcTransparentTs, cmdExcInputFailDelayTime, cmdExcRefFailDelayTime }
            STATUS current
            DESCRIPTION 
                "Group for common exciter objects"
            ::= { rsXx8000DvbTxGroups 23 }

        
        groupExcAdditionalSx800 OBJECT-GROUP
            OBJECTS { cmdExcRfOutputRegulation, cmdExcRfOutputManualRfLevel, cmdExcRfIqAdjustStart }
            STATUS current
            DESCRIPTION 
                "Additional exciter objects for the Sx800"
            ::= { rsXx8000DvbTxGroups 24 }

        
        groupExcAdditionalSLx OBJECT-GROUP
            OBJECTS { cmdExcInput1Source, cmdExcInput2Source }
            STATUS current
            DESCRIPTION 
                "Additional exciter objects for the SLx and the Sx801"
            ::= { rsXx8000DvbTxGroups 25 }

        
        groupEventsExciter NOTIFICATION-GROUP
            NOTIFICATIONS { txExcSummaryFault, txExcSummaryWarning, txExcInputNoConnectHP1, txExcInputNoConnectLP1, txExcInputNoConnectHP2, 
                txExcInputNoConnectLP2, txExcInputActiveHP1, txExcInputActiveLP1, txExcInputActiveHP2, txExcInputActiveLP2, 
                txExcOn, txExcRfOn, txExcNoInput, txExcRfLoop, txExcRfFail, 
                txExcSelfTest, txExcOutputOpen, txExcBoardTemperatureWarning, txExcFanWarning, txExcFanFault, 
                txExcFifoWarning, txExcTestSignal, txExcSFNDelay, txExcWrongDatarate, txExcMute, 
                txExcPPSFail, txExcReferenceFail, txExcMIPFail, txExcInputAutomaticSwitchReady, txExcRfOk, 
                txExcInputReseveMissing, txExcInputAutomaticChangedOver, txExcLocal }
            STATUS current
            DESCRIPTION 
                "events from the exciter"
            ::= { rsXx8000DvbTxGroups 26 }

        
        groupExciterStatus OBJECT-GROUP
            OBJECTS { excStatusRfOutputAgcRegulation, excStatusRfIqAdjustAuto, excStatusRfIqAdjustLO1Frequency, excStatusSfnDelayProcessing, excStatusSfnDelayDynamic, 
                excStatusSfnDelayNetwork, excStatusSfnDelayTxOffset, excStatusSfnDelayMaximum, excStatusSfnDelayTotal, excStatusNominalPower
                 }
            STATUS current
            DESCRIPTION 
                "Group for exciterStatusTable."
            ::= { rsXx8000DvbTxGroups 27 }

        
        groupExciterPrecorrection OBJECT-GROUP
            OBJECTS { excPrecLinCorrection, excPrecLinAutomaticADE, excPrecLinMaxAmplitudeRipple, excPrecLinMaxGroupDelayRipple, excPrecLinAmplitudeRipple, 
                excPrecLinGroupDelayRipple, excPrecLinInputLevel, excPrecLinAutomatic, excPrecNonlinCorrection, excPrecNonlinAutomaticADE, 
                excPrecNonlinThresholdShoulders, excPrecNonlinShoulderLeft, excPrecNonlinShoulderRight, excPrecNonlinInputLevel, excPrecNonlinAutomatic
                 }
            STATUS current
            DESCRIPTION 
                "Group for exciterPrecorrectionTable."
            ::= { rsXx8000DvbTxGroups 28 }

        
        groupSLx OBJECT-GROUP
            OBJECTS { cmdExcTransmitterType, cmdExcTimeScheduler, excPrecUserState, excPrecFactoryState, excPrecRestoreCurrentSettings, 
                excPrecRestoreAllSettings, configTvStandardName, configFrequency, configPower, schedulerRowStatus, 
                schedulerEvent, schedulerDateTime, config2InputSource, config2Power, config2Frequency, 
                config2RxFrequency, config2TvStandardName, excStatusVSWR, cmdExcMuteCondition, schedulerTvStandard, 
                configRxFrequency, configInputSource }
            STATUS current
            DESCRIPTION 
                "object types that are relevant for SLx devices only"
            ::= { rsXx8000DvbTxGroups 29 }

        
        groupObjectsACU OBJECT-GROUP
            OBJECTS { cmdExcRfWarningLimit, cmdExcRfFailLimit, cmdExcOutputPower, cmdExcMonitoringOutput }
            STATUS current
            DESCRIPTION 
                "objects from ACU"
            ::= { rsXx8000DvbTxGroups 30 }

        
        groupIndependentRacks OBJECT-GROUP
            OBJECTS { rackReferenceVoltage, amplifiersPowerSupply, rackOnOff }
            STATUS current
            DESCRIPTION 
                "object types that are relevant for NX variants with independent racks only"
            ::= { rsXx8000DvbTxGroups 31 }

        
        groupObjectsRE OBJECT-GROUP
            OBJECTS { summaryFaultExcA }
            STATUS current
            DESCRIPTION 
                "object types for the re-equip kit"
            ::= { rsXx8000DvbTxGroups 32 }

        
        groupEventsControlExciter NOTIFICATION-GROUP
            NOTIFICATIONS { txNetCCUNoConnectionToExcB, txAutomaticExcReady, txAutomaticExcChanged, txAutomaticExcFault }
            STATUS current
            DESCRIPTION 
                "additional events in case Sx801 is control exciter"
            ::= { rsXx8000DvbTxGroups 34 }

        
        groupEventsAdditionalPowerSupply NOTIFICATION-GROUP
            NOTIFICATIONS { txInternalPowerSupplyWarning, txExternalPowerSupplyWarning }
            STATUS current
            DESCRIPTION 
                "Events that are available only when additionalPowerSupply is true."
            ::= { rsXx8000DvbTxGroups 35 }

        
        groupObjsAdditionalPowerSupply OBJECT-GROUP
            OBJECTS { internalPowerSupply, externalPowerSupply }
            STATUS current
            DESCRIPTION 
                "Objects that are available only when additionalPowerSupply is true."
            ::= { rsXx8000DvbTxGroups 36 }

        
        groupObjectsControlExciter OBJECT-GROUP
            OBJECTS { cmdTxOperationModeReserve, cmdTxOpModeExcAutomatic, cmdTxDelayTimeExcAutomatic, summaryFaultExcB, exciterAutomaticReady, 
                exciterAutomaticChanged, exciterAutomaticFault, noConnectionExcB, activeExcB, cmdTxProgramExciterPrio, 
                cmdTxChangeOver, cmdTxSwitchPosition }
            STATUS current
            DESCRIPTION 
                "additional objects in case Sx801 is control exciter"
            ::= { rsXx8000DvbTxGroups 37 }

        
        groupObjectsSingleEnded OBJECT-GROUP
            OBJECTS { cmdTxRfSwitch }
            STATUS current
            DESCRIPTION 
                "Group for objects in case of SingleTx or DualDrive."
            ::= { rsXx8000DvbTxGroups 38 }

        
        groupObjectsSx801Amplifier OBJECT-GROUP
            OBJECTS { sx801AmpRfOut, sx801AmpRfIn, sx801AmpReflection, sx801AmpOn, sx801AmpAC, 
                sx801AmpCommunication, sx801AmpTransistor, sx801AmpDriver, sx801AmpTemperature, sx801AmpBlower, 
                sx801AmpRegulation, sx801AmpUpdate, sx801Supply1Temperature, sx801Supply2Temperature, sx801SupplyRTemperature, 
                sx801Supply1DC, sx801Supply2DC, sx801SupplyRDC, sx801AmpValueI1, sx801AmpValueI2, 
                sx801AmpValueI3, sx801AmpValueI4, sx801AmpValueIPre, sx801AmpValueIDrv1, sx801AmpValueIDrv2, 
                sx801AmpValuePowerOut, sx801AmpValueReflection, sx801AmpValueVRef, sx801AmpValueVReg, sx801AmpValueTemperature, 
                sx801AmpValueMonAtt, sx801AmpValueVAux1, sx801AmpValueVAux2, sx801Supply1ValuePwr, sx801Supply2ValuePwr, 
                sx801Supply1ValueDc, sx801Supply2ValueDc }
            STATUS current
            DESCRIPTION 
                "Objects for Sx801/SA801 amplifier status."
            ::= { rsXx8000DvbTxGroups 39 }

        
        groupObsoleted OBJECT-GROUP
            OBJECTS { cmdTxParametersetReSave, cmdExcTimeForDailyPcrReset, cmdExcEnablePcrReset, excInputAlpha, cmdExcTPSManualAlpha, 
                rfProbeConfigurationLabel, cmdExcInputAutoSwitch }
            STATUS obsolete
            DESCRIPTION 
                "obsoleted or deprecated objects"
            ::= { rsXx8000DvbTxGroups 99 }

        
        groupEventsObsoleted NOTIFICATION-GROUP
            NOTIFICATIONS { txParamSetSubDeviceDiffers, txNetCCUBoardTemperatureFault }
            STATUS obsolete
            DESCRIPTION 
                "obsoleted or deprecated events"
            ::= { rsXx8000DvbTxGroups 100 }

        
        rsXx8000DvbTxCompl OBJECT IDENTIFIER ::= { rsXx8000DvbTxConf 3 }

        
        rsXx8000DVBSingleTxMP MODULE-COMPLIANCE
            STATUS current
            DESCRIPTION 
                "Reserve concept SingleTransmitter for Medium Power."
            MODULE -- this module
                MANDATORY-GROUPS { groupTxCommon, groupCommonMP, groupCommonNetCCU, groupExcCommon, groupEvents, 
                    groupProductInfo, groupRfProbes, groupExciterStatus, groupExciterPrecorrection, groupEventsExciter, 
                    groupEventsCommonNetCCU, groupObjectsSingleEnded, groupEventsCommonMP, groupEventsTxCommon }
                GROUP groupIndependentRacks
                    DESCRIPTION 
                        "for variant with independent racks only"
                OBJECT cmdOstRefVoltageVision
                    MIN-ACCESS not-accessible
                    DESCRIPTION 
                        "not accessible in variant with independent racks"
                GROUP groupExcAdditionalSx800
                    DESCRIPTION 
                        "in case of Sx800 exciter"
                GROUP groupEventsAdditionalPowerSupply
                    DESCRIPTION 
                        "only when additionalPowerSupply is true"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
            ::= { rsXx8000DvbTxCompl 1 }

        
        rsXx8000DVBDualDriveMP MODULE-COMPLIANCE
            STATUS current
            DESCRIPTION 
                "Reserve concept DualDrive for Medium Power."
            MODULE -- this module
                MANDATORY-GROUPS { groupTxCommon, groupCommonMP, groupCommonNetCCU, groupExcCommon, groupDualDrive, 
                    groupEvents, groupProductInfo, groupRfProbes, groupExciterStatus, groupExciterPrecorrection, 
                    groupEventsExciter, groupEventsCommonNetCCU, groupEventsCommonMP, groupObjectsSingleEnded, groupEventsDualDrive, 
                    groupEventsTxCommon }
                GROUP groupIndependentRacks
                    DESCRIPTION 
                        "for variant with independent racks only"
                OBJECT cmdOstRefVoltageVision
                    MIN-ACCESS not-accessible
                    DESCRIPTION 
                        "not accessible in variant with independent racks"
                GROUP groupExcAdditionalSx800
                    DESCRIPTION 
                        "in case of Sx800 exciter"
                GROUP groupEventsAdditionalPowerSupply
                    DESCRIPTION 
                        "only when additionalPowerSupply is true"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
            ::= { rsXx8000DvbTxCompl 2 }

        
        rsXx8000DVBPowerReserveMP MODULE-COMPLIANCE
            STATUS current
            DESCRIPTION 
                "Reserve concept Active/Passive Reserve for Medium Power."
            MODULE -- this module
                MANDATORY-GROUPS { groupTxCommon, groupEvents, groupProductInfo, groupRfProbes, groupExciterStatus, 
                    groupExcCommon, groupExciterPrecorrection, groupDualDrive, groupPowerReserve, groupCommonMP, 
                    groupCommonNetCCU, groupOstBLogbook, groupEventsExciter, groupEventsCommonNetCCU, groupEventsCommonMP, 
                    groupEventsPowerReserve, groupEventsDualDrive, groupEventsTxCommon }
                GROUP groupIndependentRacks
                    DESCRIPTION 
                        "for variant with independent racks only"
                OBJECT cmdOstRefVoltageVision
                    MIN-ACCESS not-accessible
                    DESCRIPTION 
                        "not accessible in variant with independent racks"
                GROUP groupSumProbe
                    DESCRIPTION 
                        "when sum probe exists only"
                GROUP groupExcAdditionalSx800
                    DESCRIPTION 
                        "in case of Sx800 exciter"
                GROUP groupEventsAdditionalPowerSupply
                    DESCRIPTION 
                        "only when additionalPowerSupply is true"
                GROUP groupAmpMeasureValues
                    DESCRIPTION 
                        "not for face-lift configuration"
                GROUP groupEventsAmplifier
                    DESCRIPTION 
                        "not for face-lift configuration"
                GROUP groupObjsAdditionalPowerSupply
                    DESCRIPTION 
                        "only when additionalPowerSupply is true"
                GROUP groupDummyLoadRF
                    DESCRIPTION 
                        "only when a dummy load measure point exists"
            ::= { rsXx8000DvbTxCompl 3 }

        
        rsXx8000DVBSingleTxLP MODULE-COMPLIANCE
            STATUS current
            DESCRIPTION 
                "Reserve concept Low Power SingleTransmitter with NetCCU, meaning there is a NetCCU and a 
                LowPower exciter with one or more (to the exciter) connected amplifiers."
            MODULE -- this module
                MANDATORY-GROUPS { groupEvents, groupExciterStatus, groupExciterPrecorrection, groupExcAdditionalSLx, groupExcCommon, 
                    groupCommonNetCCU, groupTxCommon, groupEventsExciter, groupEventsCommonNetCCU, groupEventsTxCommon
                     }
                GROUP groupEventsAdditionalPowerSupply
                    DESCRIPTION 
                        "only when additionalPowerSupply is true"
                GROUP groupObjsAdditionalPowerSupply
                    DESCRIPTION 
                        "only when additionalPowerSupply is true"
            ::= { rsXx8000DvbTxCompl 5 }

        
        rsXx8000DVBDualDriveLP MODULE-COMPLIANCE
            STATUS current
            DESCRIPTION 
                "Reserve concept DualDrive for Low Power."
            MODULE -- this module
                MANDATORY-GROUPS { groupEvents, groupExciterStatus, groupExciterPrecorrection, groupExcAdditionalSLx, groupExcCommon, 
                    groupCommonNetCCU, groupDualDrive, groupTxCommon, groupEventsExciter, groupEventsCommonNetCCU, 
                    groupEventsDualDrive, groupEventsTxCommon }
                GROUP groupEventsAdditionalPowerSupply
                    DESCRIPTION 
                        "only when additionalPowerSupply is true"
                GROUP groupObjsAdditionalPowerSupply
                    DESCRIPTION 
                        "only when additionalPowerSupply is true"
            ::= { rsXx8000DvbTxCompl 6 }

        
        rsXx8000DVBPowerReserveLP MODULE-COMPLIANCE
            STATUS current
            DESCRIPTION 
                "Reserve concept Active/Passive Reserve for Low Power."
            MODULE -- this module
                MANDATORY-GROUPS { groupEvents, groupExciterStatus, groupExciterPrecorrection, groupExcAdditionalSLx, groupExcCommon, 
                    groupCommonNetCCU, groupPowerReserve, groupDualDrive, groupTxCommon, groupEventsExciter, 
                    groupEventsCommonNetCCU, groupEventsPowerReserve, groupEventsDualDrive, groupEventsTxCommon }
                GROUP groupEventsAdditionalPowerSupply
                    DESCRIPTION 
                        "only when additionalPowerSupply is true"
                GROUP groupObjsAdditionalPowerSupply
                    DESCRIPTION 
                        "only when additionalPowerSupply is true"
            ::= { rsXx8000DvbTxCompl 7 }

        
        rsXx8000DVBSingleTxLPNoNetCCU MODULE-COMPLIANCE
            STATUS current
            DESCRIPTION 
                "Reserve concept Low Power SingleTransmitter without NetCCU, meaning there is only a
                LowPower exciter with one or more (to the exciter) connected amplifiers."
            MODULE -- this module
                MANDATORY-GROUPS { groupEvents, groupExciterStatus, groupExciterPrecorrection, groupExcAdditionalSLx, groupExcCommon, 
                    groupTxCommon, groupEventsExciter, groupEventsTxCommon }
            ::= { rsXx8000DvbTxCompl 9 }

        
        rsXx8000DVBSLx MODULE-COMPLIANCE
            STATUS current
            DESCRIPTION 
                "SLx device"
            MODULE -- this module
                MANDATORY-GROUPS { groupEvents, groupExciterStatus, groupExciterPrecorrection, groupSLx, groupObjectsACU, 
                    groupExcCommon, groupTxCommon, groupEventsExciter, groupEventsTxCommon }
            ::= { rsXx8000DvbTxCompl 10 }

        
        rsXx8000DVBExciterOnly MODULE-COMPLIANCE
            STATUS current
            DESCRIPTION 
                "DVB Exciter of 8000 series in a 7000 environment
                or
                Program Exciter in a Sx801 Backup Exciter environment."
            MODULE -- this module
                MANDATORY-GROUPS { groupProductInfo, groupExciterStatus, groupEvents, groupObjectsRE, groupObjectsSx801Amplifier, 
                    groupExciterPrecorrection, groupExcCommon, groupEventsExciter }
                GROUP groupSLx
                    DESCRIPTION 
                        "in case of SLx device"
            ::= { rsXx8000DvbTxCompl 11 }

        
        rsXx8000DVBSx801ControlExciter MODULE-COMPLIANCE
            STATUS current
            DESCRIPTION 
                "Sx801 as control exciter"
            MODULE -- this module
                MANDATORY-GROUPS { groupTxCommon, groupExcCommon, groupEvents, groupExciterStatus, groupExciterPrecorrection, 
                    groupSLx, groupObjectsACU, groupObjectsSx801Amplifier, groupEventsExciter, groupEventsTxCommon, 
                    groupEventsControlExciter, groupObjectsControlExciter }
            ::= { rsXx8000DvbTxCompl 12 }

        
    
    END
