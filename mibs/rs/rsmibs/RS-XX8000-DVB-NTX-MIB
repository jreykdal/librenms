-- *****************************************************************************
-- *****************************************************************************
-- **
-- **  COPYRIGHT      (c) 2006 Rohde & Schwarz GmbH & Co. KG
-- **                          Muehldorfstrasse 15
-- **    R & S                 D-81671 Muenchen
-- **
-- *****************************************************************************
-- **
-- **  MODULE         RS-XX8000-DVB-NTX-MIB
-- **  
-- **  DESCRIPTION    Rohde & Schwarz SNMP
-- **
-- **  HISTORY
-- **
-- **  2007-05-16 hue - initial version
-- **  2007-12-07  sr - cmdExcSFNStaticDelay to FloatingPoint
-- **                 - cmdExcSFNDeviationTime changed range
-- **                 - new commands cmdExcOpModeInputAutomatic, cmdExcTypeLossOfInput
-- **                 - new exciter commands for RfOutput, RfIqAdjust and Precorrection
-- **                 - productInfoTable
-- **                 - rename ncuFanFault to ncuFanWarning
-- **                 - rename ncuBoardTemperatureWarning to ncuBoardTemperatureFault
-- **                 - update of groups and module-compliances
-- **  2008-07-23  sr - new SFN Delay parameters in exciterStatusTable
-- **  2008-08-26 ks - cmdTxParametersetReSave obsolete
-- **  2008-08-29 hue - Changed TextualConvention for Exciter LogbookEntryMessages
-- **  2008-10-30 sr - cmdExcFrequency range up to 1500 MHz
-- **                - new: cmdExcInpAutoReadyAfterChangeOv,
-- **                       txExcInputAutomaticSwitchReady, txExcInputAutomaticChangedOver
-- **  2009-03-30 ks - txParamSetSubDeviceDiffers obsoleted
-- **  2009-05-07 ks - device info for TC boards
-- **                - add medium/high power support
-- **  2009-05-28 ks - information for additional (external) power supply added
-- **                - txRackRfOn, txRackRfOk, txRackTemperatureWarning added
-- **  2009-07-02 ks - measured values for power supply added
-- **                - cmdExcInputAutoSwitch obsoleted
-- **                - conditional groupDummyLoadRF added
-- **  2009-10-08 ks - txRackOvervoltProtectWarning added
-- **                - cmdExcInputAutoSwitch reactivated
-- **  2009-11-13 ks - ampDeltaPhase, ampCmdDeltaPhase added
-- **  2009-11-27 ks - cmdExcInputFailDelayTime added
-- **  2009-11-30 ks - cmdExcMonitoringOutput, cmdExcOcxoAdjust added
-- **  2009-12-07 ks - excStatusNominalPower added
-- **  2009-12-18 ks - txExcRfOk added
-- **  2010-01-12 ks - excStatusVSWR added
-- **  2010-01-28 ks - ncuBoardTemperatureFault, txNetCCUBoardTemperatureFault deprecated and
-- **                  ncuBoardTemperatureWarning, txNetCCUBoardTemperatureWarning added
-- **  2010-02-02 ks - cmdExcExpectInputReserve, txExcInputReseveMissing added
-- **  2010-20-04 ks - cmdExcMuteCondition added
-- **  2010-06-01 ks - txNoConnection added
-- **  2010-06-30 ks - added the following objects and traps:
-- **                  cmdTxOpModeOstAutomatic, cmdTxPreselectOutputstage, cmdTxDelayTimeOstAutomatic
-- **                  statusTxSummaryFaultOstB, statusTxOstAutomaticReady/Changed/Fault,
-- **                  statusTxNoConnectionOstB, statusTxActiveOstA, statusTxActiveOstB,
-- **                  txAutomaticOstReady/Changed/Fault
-- **  2010-10-11 ks - statusTxExcSwitch, statusTxOstSwitch added
-- **  2010-10-13 ks - cmdExcEnablePcrReset, cmdExcTimeForDailyPcrReset added
-- **  2010-12-02 ks - excStatusAmplifierControl, excStatusReqDataRateHP,
-- **                  excStatusReqDataRateLP added
-- **  2011-02-28 ks - Amplifier status for Sx801 added.
-- **  2011-03-04 ks - statusTxNoConnectionApaIf, statusTxAbsorberFault,
-- **                  txNoConnectionApaIf, txAbsorberFault added
-- **  2011-05-12 ks - cmdExcFailDelayMode, excStatusFailDelay added
-- **  2012-09-03 ks - sx801AmplifierTable measured values added
-- **  2012-11-01 ks - Hierarchical input is no longer supported.
-- *****************************************************************************
-- *****************************************************************************

    RS-XX8000-DVB-NTX-MIB DEFINITIONS ::= BEGIN
 
        IMPORTS
            rsXx8000, eventAlarmPriority, eventAlarmClass, eventEvent, indexTransmitter, 
            indexAB, indexRack, indexAmplifier, rsXx8000MibModule, EventPriority, 
            EventClass, EventState, IndexTransmitter, IndexAB, IndexRack, 
            IndexAmplifier, Trigger, LogbookMaxEntryNumber, LogbookEntrySlope, LogbookEntryMessagesNSU, 
            FloatingPoint, ProdInfoModuleNameNsu, ReadableString, SwitchOnOff, InputSource, 
            TimeOfDay, LogbookEntryMessagesNetCCU, LogbookEntryMessagesExcTv, LogbookEntryMessagesOST, ProdInfoModuleNameTv, 
            EventMaxEntryNumber, EventMask, Sx801AmplifierState, FailDelayMode, FailDelayStatus            
                FROM RS-XX8000-COMMON-MIB            
            OBJECT-GROUP, MODULE-COMPLIANCE, NOTIFICATION-GROUP            
                FROM SNMPv2-CONF            
            Integer32, OBJECT-TYPE, MODULE-IDENTITY, OBJECT-IDENTITY, NOTIFICATION-TYPE            
                FROM SNMPv2-SMI            
            TruthValue, DateAndTime            
                FROM SNMPv2-TC;
    
    
        rsXx8000DvbNTxMibModule MODULE-IDENTITY 
            LAST-UPDATED "201509101100Z"		-- September 10, 2015 at 11:00 GMT
            ORGANIZATION 
                "Rohde&Schwarz GmbH & Co. KG"
            CONTACT-INFO 
                "Torsten Huebscher
                Department 7TS2
                Broadcasting Division
                Muehldorfstrasse 15
                81671 Munich, Germany
                torsten.huebscher@rohde-schwarz.com"
            DESCRIPTION 
                "This MIB defines transmitting systems from Rohde & Schwarz.
                
                Use this MIB if your system meets the following requirements:
                - series XX8000 (NetCCU800),
                - DVB,
                - NTX-system.
                
                The following MIBs are related to this:
                - RS-COMMON-MIB         - mandatory for this MIB
                - RS-XX8000-COMMON-MIB  - mandatory for this MIB"
            REVISION "201509101100Z"		-- September 10, 2015 at 11:00 GMT
            DESCRIPTION 
                "Hierarchical input always returns noHierarchy(1)
                "
            REVISION "201211010800Z"		-- November 01, 2012 at 08:00 GMT
            DESCRIPTION 
                "Hierarchical input is no longer supported."
            REVISION "201209030800Z"		-- September 03, 2012 at 08:00 GMT
            DESCRIPTION 
                "sx801AmplifierTable measured values added"
            REVISION "201105120800Z"		-- May 12, 2011 at 08:00 GMT
            DESCRIPTION 
                "cmdExcFailDelayMode, excStatusFailDelay added"
            REVISION "201103040800Z"		-- March 04, 2011 at 08:00 GMT
            DESCRIPTION 
                "statusTxNoConnectionApaIf, statusTxAbsorberFault,
                txNoConnectionApaIf, txAbsorberFault added"
            REVISION "201102280800Z"		-- February 28, 2011 at 08:00 GMT
            DESCRIPTION 
                "Amplifier status for Sx801 added."
            REVISION "201012020800Z"		-- December 02, 2010 at 08:00 GMT
            DESCRIPTION 
                "excStatusAmplifierControl, excStatusReqDataRateHP,
                excStatusReqDataRateLP added"
            REVISION "201010130800Z"		-- October 13, 2010 at 08:00 GMT
            DESCRIPTION 
                "cmdExcEnablePcrReset, cmdExcTimeForDailyPcrReset added"
            REVISION "201010110800Z"		-- October 11, 2010 at 08:00 GMT
            DESCRIPTION 
                "statusTxExcSwitch, statusTxOstSwitch added"
            REVISION "201006300800Z"		-- June 30, 2010 at 08:00 GMT
            DESCRIPTION 
                "added the following objects and traps:
                cmdTxOpModeOstAutomatic, cmdTxPreselectOutputstage, cmdTxDelayTimeOstAutomatic
                statusTxSummaryFaultOstB, statusTxOstAutomaticReady/Changed/Fault,
                statusTxNoConnectionOstB, statusTxActiveOstA, statusTxActiveOstB,
                txAutomaticOstReady/Changed/Fault"
            REVISION "201006010800Z"		-- June 01, 2010 at 08:00 GMT
            DESCRIPTION 
                "txNoConnection added"
            REVISION "201004260800Z"		-- April 26, 2010 at 08:00 GMT
            DESCRIPTION 
                "added values for output stage reserve.
                The rackTable indices were corrected:
                the additional rackOstIdx selects the output stage.
                This is in accordance with the previous and current
                behaviour of the agent."
            REVISION "201004190800Z"		-- April 19, 2010 at 08:00 GMT
            DESCRIPTION 
                "cmdExcMuteCondition added"
            REVISION "201002020800Z"		-- February 02, 2010 at 08:00 GMT
            DESCRIPTION 
                "cmdExcExpectInputReserve, txExcInputReseveMissing added"
            REVISION "201001280800Z"		-- January 28, 2010 at 08:00 GMT
            DESCRIPTION 
                "ncuBoardTemperatureFault, txNetCCUBoardTemperatureFault deprecated and
                ncuBoardTemperatureWarning, txNetCCUBoardTemperatureWarning added"
            REVISION "201001120800Z"		-- January 12, 2010 at 08:00 GMT
            DESCRIPTION 
                "excStatusVSWR added"
            REVISION "200912180900Z"		-- December 18, 2009 at 09:00 GMT
            DESCRIPTION 
                "txExcRfOk added"
            REVISION "200911270900Z"		-- November 27, 2009 at 09:00 GMT
            DESCRIPTION 
                "cmdExcInputFailDelayTime,
                cmdExcMonitoringOutput, cmdExcOcxoAdjust,
                excStatusNominalPower added"
            REVISION "200911130900Z"		-- November 13, 2009 at 09:00 GMT
            DESCRIPTION 
                "ampDeltaPhase, ampCmdDeltaPhase added"
            REVISION "200910080900Z"		-- October 08, 2009 at 09:00 GMT
            DESCRIPTION 
                "txRackOvervoltProtectWarning added
                cmdExcInputAutoSwitch reactivated"
            REVISION "200907020900Z"		-- July 02, 2009 at 09:00 GMT
            DESCRIPTION 
                "measured values for power supply added,
                cmdExcInputAutoSwitch obsoleted,
                conditional groupDummyLoadRF added
                "
            REVISION "200905280900Z"		-- May 28, 2009 at 09:00 GMT
            DESCRIPTION 
                "information for additional (external) power supply added
                txRackRfOn, txRackRfOk, txRackTemperatureWarning added"
            REVISION "200905070900Z"		-- May 07, 2009 at 09:00 GMT
            DESCRIPTION 
                "device info for TC boards,
                add medium/high power support"
            REVISION "200903300900Z"		-- March 30, 2009 at 09:00 GMT
            DESCRIPTION 
                "txParamSetSubDeviceDiffers obsoleted"
            REVISION "200810301030Z"		-- October 30, 2008 at 10:30 GMT
            DESCRIPTION 
                "cmdExcFrequency range up to 1500 MHz
                new: cmdExcInpAutoReadyAfterChangeOv,
                     txExcInputAutomaticSwitchReady, txExcInputAutomaticChangedOver"
            REVISION "200808291100Z"		-- August 29, 2008 at 11:00 GMT
            DESCRIPTION 
                "Changed TextualConvention for Exciter LogbookEntryMessages"
            REVISION "200808260900Z"		-- August 26, 2008 at 09:00 GMT
            DESCRIPTION 
                "- cmdTxParametersetReSave obsolete"
            REVISION "200807231100Z"		-- July 23, 2008 at 11:00 GMT
            DESCRIPTION 
                "- new SFN Delay parameters in exciterStatusTable"
            REVISION "200712071400Z"		-- December 07, 2007 at 14:00 GMT
            DESCRIPTION 
                "- cmdExcSFNStaticDelay to FloatingPoint
                - cmdExcSFNDeviationTime changed range
                - new commands cmdExcOpModeInputAutomatic, cmdExcTypeLossOfInput
                - new exciter commands for RfOutput, RfIqAdjust and Precorrection
                - productInfoTable
                - rename ncuFanFault to ncuFanWarning
                - rename ncuBoardTemperatureWarning to ncuBoardTemperatureFault
                - update of groups and module-compliances"
            REVISION "200705161000Z"		-- May 16, 2007 at 10:00 GMT
            DESCRIPTION 
                "This is the initial version."
            ::= { rsXx8000MibModule 6 }

        
    
    
--
-- Node definitions
--
    
        rsXx8000DvbNTx OBJECT-IDENTITY
            STATUS current
            DESCRIPTION 
                "Xx8000 DVB Nplus1 system."
            ::= { rsXx8000 6 }

        
-- *****************************************************************************
-- **          object definitions
-- *****************************************************************************
        rsXx8000DvbNTxObjs OBJECT IDENTIFIER ::= { rsXx8000DvbNTx 1 }

        
-- *****************************************************************************
-- **          NetCCU Tx Control Unit
-- *****************************************************************************
        txControlUnit OBJECT IDENTIFIER ::= { rsXx8000DvbNTxObjs 1 }

        
        resetAllFaults OBJECT-TYPE
            SYNTAX Trigger
            MAX-ACCESS read-write
            STATUS current
            DESCRIPTION
                "Reset all faults (for NCU - NetCCU Control Unit).
                
                An equivalent would be pressing RESET at the NCU frontpanel.
                
                A GET will always return idle(1). A SET idle(1) will return NO_ERROR without doing anything."
            ::= { txControlUnit 7 }

        
        summaryFaultNCU OBJECT-TYPE
            SYNTAX TruthValue
            MAX-ACCESS read-only
            STATUS current
            DESCRIPTION
                "This indicates a summary fault of the NCU - NetCCU Control Unit.
                true(1)  --> summary fault
                false(2) --> no summary fault
                
                There is a fault which causes this summary fault.
                
                An equivalent would be the LED Fault at the NCU frontpanel."
            ::= { txControlUnit 8 }

        
        summaryWarningNCU OBJECT-TYPE
            SYNTAX TruthValue
            MAX-ACCESS read-only
            STATUS current
            DESCRIPTION
                "This indicates a summary warning of the NCU - NetCCU Control Unit.
                true(1)  --> summary warning
                false(2) --> no summary warning
                
                There is a warning which causes this summary warning.
                
                An equivalent would be the LED Warning at the NCU frontpanel."
            ::= { txControlUnit 9 }

        
        localModeNCU OBJECT-TYPE
            SYNTAX TruthValue
            MAX-ACCESS read-only
            STATUS current
            DESCRIPTION
                "This indicates the local/remote-mode of the NCU - NetCCU Control Unit.
                true(1)  --> local
                false(2) --> remote
                
                The NCU is eigther in local-mode or in remote-mode. 
                For security reasons it is not possible to set this value!
                
                An equivalent would the LED Local at the NCU frontpanel."
            ::= { txControlUnit 10 }

        
        logbookNCU OBJECT IDENTIFIER ::= { txControlUnit 14 }

        
        ncuNumberOfEntries OBJECT-TYPE
            SYNTAX LogbookMaxEntryNumber
            MAX-ACCESS read-only
            STATUS current
            DESCRIPTION
                "The number of entries in the NCU - NetCCU Control Unit."
            ::= { logbookNCU 1 }

        
        ncuLogbookClear OBJECT-TYPE
            SYNTAX Trigger
            MAX-ACCESS read-write
            STATUS current
            DESCRIPTION
                "Clear logbook of the NCU - NetCCU Control Unit."
            ::= { logbookNCU 2 }

        
        ncuLogbookTable OBJECT-TYPE
            SYNTAX SEQUENCE OF NcuLogbookEntry
            MAX-ACCESS not-accessible
            STATUS current
            DESCRIPTION
                "NCU Logbook"
            ::= { logbookNCU 3 }

        
        ncuLogbookEntry OBJECT-TYPE
            SYNTAX NcuLogbookEntry
            MAX-ACCESS not-accessible
            STATUS current
            DESCRIPTION
                "A row (an entry) of a logbook."
            INDEX { ncuLogbookEntryIdx }
            ::= { ncuLogbookTable 1 }

        
        NcuLogbookEntry ::=
            SEQUENCE { 
                ncuLogbookEntryIdx
                    LogbookMaxEntryNumber,
                ncuLogbookEntryNbr
                    LogbookMaxEntryNumber,
                ncuLogbookType
                    EventClass,
                ncuLogbookSlope
                    LogbookEntrySlope,
                ncuLogbookMessage
                    LogbookEntryMessagesNSU,
                ncuLogbookDateTime
                    DateAndTime
             }

        ncuLogbookEntryIdx OBJECT-TYPE
            SYNTAX LogbookMaxEntryNumber
            MAX-ACCESS not-accessible
            STATUS current
            DESCRIPTION
                "This is an increasing number from 1 to 128. It is used as an index column for SNMP."
            ::= { ncuLogbookEntry 1 }

        
        ncuLogbookEntryNbr OBJECT-TYPE
            SYNTAX LogbookMaxEntryNumber
            MAX-ACCESS read-only
            STATUS current
            DESCRIPTION
                "This is the number of the logbook entry. It is an decreasing number from max 128 down to 1."
            ::= { ncuLogbookEntry 2 }

        
        ncuLogbookType OBJECT-TYPE
            SYNTAX EventClass
            MAX-ACCESS read-only
            STATUS current
            DESCRIPTION
                "Can either be Fault, Warning or State."
            ::= { ncuLogbookEntry 3 }

        
        ncuLogbookSlope OBJECT-TYPE
            SYNTAX LogbookEntrySlope
            MAX-ACCESS read-only
            STATUS current
            DESCRIPTION
                "Either set (event raises) or reset (event disappears)"
            ::= { ncuLogbookEntry 4 }

        
        ncuLogbookMessage OBJECT-TYPE
            SYNTAX LogbookEntryMessagesNSU
            MAX-ACCESS read-only
            STATUS current
            DESCRIPTION
                "See RS-XX8000-COMMON-MIB - TextualConvention - LogbookEntryMessagesNSU for details."
            ::= { ncuLogbookEntry 5 }

        
        ncuLogbookDateTime OBJECT-TYPE
            SYNTAX DateAndTime
            MAX-ACCESS read-only
            STATUS current
            DESCRIPTION
                "The time of the logbook entry."
            ::= { ncuLogbookEntry 6 }

        
        powerSupply OBJECT-TYPE
            SYNTAX FloatingPoint
            UNITS "volt"
            MAX-ACCESS read-only
            STATUS current
            DESCRIPTION
                "Monitoring value of the output voltages of the NCU power supply."
            ::= { txControlUnit 19 }

        
        additionalPowerSupply OBJECT-TYPE
            SYNTAX TruthValue
            MAX-ACCESS read-only
            STATUS current
            DESCRIPTION
                "Shows whether the NCU has an additional (external) power supply."
            ::= { txControlUnit 20 }

        
        internalPowerSupply OBJECT-TYPE
            SYNTAX FloatingPoint
            UNITS "volt"
            MAX-ACCESS read-only
            STATUS current
            DESCRIPTION
                "Monitoring value of the output voltages of the NCU internal power supply."
            ::= { txControlUnit 21 }

        
        externalPowerSupply OBJECT-TYPE
            SYNTAX FloatingPoint
            UNITS "volt"
            MAX-ACCESS read-only
            STATUS current
            DESCRIPTION
                "Monitoring value of the output voltages of the NCU external power supply."
            ::= { txControlUnit 22 }

        
        ncuProductInfoTable OBJECT-TYPE
            SYNTAX SEQUENCE OF NcuProductInfoEntry
            MAX-ACCESS not-accessible
            STATUS current
            DESCRIPTION
                "The table for product typeplates."
            ::= { txControlUnit 100 }

        
        ncuProductInfoEntry OBJECT-TYPE
            SYNTAX NcuProductInfoEntry
            MAX-ACCESS not-accessible
            STATUS current
            DESCRIPTION
                "A row (an entry) for one typeplate."
            INDEX { ncuProdInfoModuleIdx, ncuProdInfoTxIdx }
            ::= { ncuProductInfoTable 1 }

        
        NcuProductInfoEntry ::=
            SEQUENCE { 
                ncuProdInfoModuleIdx
                    ProdInfoModuleNameNsu,
                ncuProdInfoTxIdx
                    IndexTransmitter,
                ncuProdInfoModuleName
                    ProdInfoModuleNameNsu,
                ncuProdInfoSerialNumber
                    ReadableString,
                ncuProdInfoIdentNumberSW
                    ReadableString,
                ncuProdInfoVersionNumberSW
                    ReadableString,
                ncuProdInfoIdentNumberHW
                    ReadableString,
                ncuProdInfoVersionNumberHW
                    ReadableString,
                ncuProductInfoProductDateHW
                    DateAndTime
             }

        ncuProdInfoModuleIdx OBJECT-TYPE
            SYNTAX ProdInfoModuleNameNsu
            MAX-ACCESS not-accessible
            STATUS current
            DESCRIPTION
                "The module index."
            ::= { ncuProductInfoEntry 1 }

        
        ncuProdInfoTxIdx OBJECT-TYPE
            SYNTAX IndexTransmitter
            MAX-ACCESS not-accessible
            STATUS current
            DESCRIPTION
                "The transmitter index."
            ::= { ncuProductInfoEntry 2 }

        
        ncuProdInfoModuleName OBJECT-TYPE
            SYNTAX ProdInfoModuleNameNsu
            MAX-ACCESS read-only
            STATUS current
            DESCRIPTION
                "The name of the module as a text."
            ::= { ncuProductInfoEntry 6 }

        
        ncuProdInfoSerialNumber OBJECT-TYPE
            SYNTAX ReadableString
            MAX-ACCESS read-only
            STATUS current
            DESCRIPTION
                "The serial number of the subdevice."
            ::= { ncuProductInfoEntry 7 }

        
        ncuProdInfoIdentNumberSW OBJECT-TYPE
            SYNTAX ReadableString
            MAX-ACCESS read-only
            STATUS current
            DESCRIPTION
                "The Rohde&Schwarz identification number of the software, for example 2094.2090.02."
            ::= { ncuProductInfoEntry 8 }

        
        ncuProdInfoVersionNumberSW OBJECT-TYPE
            SYNTAX ReadableString
            MAX-ACCESS read-only
            STATUS current
            DESCRIPTION
                "The Rohde&Schwarz revision number of the software, for example 1.2.1."
            ::= { ncuProductInfoEntry 9 }

        
        ncuProdInfoIdentNumberHW OBJECT-TYPE
            SYNTAX ReadableString
            MAX-ACCESS read-only
            STATUS current
            DESCRIPTION
                "The Rohde&Schwarz identification number of the hardware, for example 2095.8007.02 (NetCCU)."
            ::= { ncuProductInfoEntry 10 }

        
        ncuProdInfoVersionNumberHW OBJECT-TYPE
            SYNTAX ReadableString
            MAX-ACCESS read-only
            STATUS current
            DESCRIPTION
                "The Rohde&Schwarz revision number (product index) of the hardware, for example 03.03."
            ::= { ncuProductInfoEntry 11 }

        
        ncuProductInfoProductDateHW OBJECT-TYPE
            SYNTAX DateAndTime
            MAX-ACCESS read-only
            STATUS current
            DESCRIPTION
                "The Rohde&Schwarz production date of the hardware,"
            ::= { ncuProductInfoEntry 12 }

        
-- *****************************************************************************
-- **          transmitter (physical) view
-- *****************************************************************************
        transmitter OBJECT IDENTIFIER ::= { rsXx8000DvbNTxObjs 3 }

        
        commandsTxTable OBJECT-TYPE
            SYNTAX SEQUENCE OF CommandsTxEntry
            MAX-ACCESS not-accessible
            STATUS current
            DESCRIPTION
                "This table contents important commands for the transmitters."
            ::= { transmitter 1 }

        
        commandsTxEntry OBJECT-TYPE
            SYNTAX CommandsTxEntry
            MAX-ACCESS not-accessible
            STATUS current
            DESCRIPTION
                "An entry for a designated transmitter and device."
            INDEX { cmdTxIdx, cmdDeviceIdx }
            ::= { commandsTxTable 1 }

        
        CommandsTxEntry ::=
            SEQUENCE { 
                cmdTxIdx
                    IndexTransmitter,
                cmdTxName
                    IndexTransmitter,
                cmdTxResetSumFault
                    Trigger,
                cmdTxParametersetLoad
                    Integer32,
                cmdTxParametersetSave
                    Integer32,
                cmdTxParametersetReSave
                    Trigger,
                cmdTxOpModeProgram
                    SwitchOnOff,
                cmdTxOperationModeReserve
                    SwitchOnOff,
                cmdTxOpModeExcAutomatic
                    SwitchOnOff,
                cmdTxOpModeOstAutomatic
                    SwitchOnOff,
                cmdTxPreselectExciter
                    IndexAB,
                cmdTxPreselectOutputstage
                    INTEGER,
                cmdTxDelayTimeExcAutomatic
                    Integer32,
                cmdTxDelayTimeOstAutomatic
                    Integer32,
                cmdDeviceIdx
                    IndexAB,
                cmdExcOpModeInputAutomatic
                    SwitchOnOff,
                cmdExcPreselectInput
                    INTEGER,
                cmdExcMode
                    INTEGER,
                cmdExcNetworkMode
                    INTEGER,
                cmdExcTPSSource
                    INTEGER,
                cmdExcEnableCellID
                    SwitchOnOff,
                cmdExcTxAddress
                    Integer32,
                cmdExcTxAutomatic
                    SwitchOnOff,
                cmdExcInputAutoSwitch
                    SwitchOnOff,
                cmdExcInputSeamless
                    SwitchOnOff,
                cmdExcInputPriority
                    INTEGER,
                cmdExcInputCheckTimeForward
                    Integer32,
                cmdExcInputCheckTimeSwitchback
                    Integer32,
                cmdExcInputMuteOnFail
                    INTEGER,
                cmdExcInputManualPreseletionHP1
                    INTEGER,
                cmdExcInputManualPreseletionHP2
                    INTEGER,
                cmdExcInputManualPreseletionLP1
                    INTEGER,
                cmdExcInputManualPreseletionLP2
                    INTEGER,
                cmdExcTPSManualBandwidth
                    INTEGER,
                cmdExcTPSManualFFTLength
                    INTEGER,
                cmdExcTPSManualGuardInterval
                    INTEGER,
                cmdExcTPSManualConstellation
                    INTEGER,
                cmdExcTPSManualAlpha
                    INTEGER,
                cmdExcTPSManualCellID
                    Integer32,
                cmdExcTPSManualInterleaver
                    INTEGER,
                cmdExcTPSManualCoderateHP
                    INTEGER,
                cmdExcTPSManualCoderateLP
                    INTEGER,
                cmdExcTPSManualTimeSlicingHP
                    SwitchOnOff,
                cmdExcTPSManualTimeSlicingLP
                    SwitchOnOff,
                cmdExcTPSManualFECHP
                    SwitchOnOff,
                cmdExcTPSManualFECLP
                    SwitchOnOff,
                cmdExcSFNStaticDelay
                    FloatingPoint,
                cmdExcSFNDeviationTime
                    Integer32,
                cmdExcFrequency
                    Integer32,
                cmdExcReferenceSource
                    INTEGER,
                cmdExcMuteOnPPSFail
                    INTEGER,
                cmdExcMuteOnReferenceFail
                    INTEGER,
                cmdExcRefFailDelayTime
                    Integer32,
                cmdExcTypeLossOfInput
                    INTEGER,
                cmdExcRfOutput
                    SwitchOnOff,
                cmdExcRfOutputRegulation
                    SwitchOnOff,
                cmdExcRfOutputManualRfLevel
                    FloatingPoint,
                cmdExcRfOutputAttenuation
                    Integer32,
                cmdExcRfOutputRfSlope
                    FloatingPoint,
                cmdExcRfOutputModulationSlope
                    FloatingPoint,
                cmdExcRfIqAdjustStart
                    INTEGER,
                cmdExcRfIqAdjustTestsignal
                    SwitchOnOff,
                cmdExcRfIqAdjustBiasCoarseI
                    Integer32,
                cmdExcRfIqAdjustBiasCoarseQ
                    Integer32,
                cmdExcRfIqAdjustBiasFineI
                    Integer32,
                cmdExcRfIqAdjustBiasFineQ
                    Integer32,
                cmdExcRfIqAdjustGainI
                    Integer32,
                cmdExcRfIqAdjustGainQ
                    Integer32,
                cmdExcRfIqAdjustPhase
                    FloatingPoint,
                cmdExcInput1Source
                    InputSource,
                cmdExcInput2Source
                    InputSource,
                cmdExcInpAutoReadyAfterChangeOv
                    SwitchOnOff,
                cmdExcInputFailDelayTime
                    Integer32,
                cmdExcMuteCondition
                    INTEGER,
                cmdExcMonitoringOutput
                    INTEGER,
                cmdExcOcxoAdjust
                    Integer32,
                cmdExcExpectInputReserve
                    SwitchOnOff,
                cmdExcEnablePcrReset
                    SwitchOnOff,
                cmdExcTimeForDailyPcrReset
                    TimeOfDay,
                cmdExcFailDelayMode
                    FailDelayMode,
                cmdExcTransparentTs
                    SwitchOnOff,
                cmdOstRefVoltageVision
                    FloatingPoint,
                cmdOstMaxOutletTempThreshold
                    Integer32
             }

        cmdTxIdx OBJECT-TYPE
            SYNTAX IndexTransmitter
            MAX-ACCESS not-accessible
            STATUS current
            DESCRIPTION
                "The transmitter index. There are max. 8 transmitters, if you have an 8+1 system."
            ::= { commandsTxEntry 1 }

        
        cmdTxName OBJECT-TYPE
            SYNTAX IndexTransmitter
            MAX-ACCESS read-only
            STATUS current
            DESCRIPTION
                "This is the logical name for the transmitters."
            ::= { commandsTxEntry 2 }

        
        cmdTxResetSumFault OBJECT-TYPE
            SYNTAX Trigger
            MAX-ACCESS read-write
            STATUS current
            DESCRIPTION
                "Reset all faults (in all modules) of the transmitter.
                
                You reset a designated transmitter (NetCCU, Exciters, Outputstages).
                An equivalent would be pressing RESET at this transmitters frontpanel.
                
                A GET will always return idle(1). A SET idle(1) will return NO_ERROR without doing anything."
            ::= { commandsTxEntry 3 }

        
        cmdTxParametersetLoad OBJECT-TYPE
            SYNTAX Integer32 (1..8)
            MAX-ACCESS read-write
            STATUS current
            DESCRIPTION
                "This loads the desired parameter set."
            ::= { commandsTxEntry 4 }

        
        cmdTxParametersetSave OBJECT-TYPE
            SYNTAX Integer32 (1..8)
            MAX-ACCESS read-write
            STATUS current
            DESCRIPTION
                "This saves the current settings to a designated parameter set."
            ::= { commandsTxEntry 5 }

        
        cmdTxParametersetReSave OBJECT-TYPE
            SYNTAX Trigger
            MAX-ACCESS read-write
            STATUS obsolete
            DESCRIPTION
                "This saves the changes to the current parameter set."
            ::= { commandsTxEntry 6 }

        
        cmdTxOpModeProgram OBJECT-TYPE
            SYNTAX SwitchOnOff
            MAX-ACCESS read-write
            STATUS current
            DESCRIPTION
                "This switches the program path of the transmitter on/off."
            ::= { commandsTxEntry 7 }

        
        cmdTxOperationModeReserve OBJECT-TYPE
            SYNTAX SwitchOnOff
            MAX-ACCESS read-write
            STATUS current
            DESCRIPTION
                "This switches the reserve path of the transmitter on/off."
            ::= { commandsTxEntry 8 }

        
        cmdTxOpModeExcAutomatic OBJECT-TYPE
            SYNTAX SwitchOnOff
            MAX-ACCESS read-write
            STATUS current
            DESCRIPTION
                "This switches the exciter automatic on/off."
            ::= { commandsTxEntry 9 }

        
        cmdTxOpModeOstAutomatic OBJECT-TYPE
            SYNTAX SwitchOnOff
            MAX-ACCESS read-write
            STATUS current
            DESCRIPTION
                "This switches the outputstage automatic on/off.
                
                This paramter is only available for systems with an automatic output switch."
            ::= { commandsTxEntry 10 }

        
        cmdTxPreselectExciter OBJECT-TYPE
            SYNTAX IndexAB
            MAX-ACCESS read-write
            STATUS current
            DESCRIPTION
                "This sets exciterA or exciterB to program path (antenna) of the transmitter."
            ::= { commandsTxEntry 11 }

        
        cmdTxPreselectOutputstage OBJECT-TYPE
            SYNTAX INTEGER
                {
                outputstageA(1),
                outputstageB(2),
                bothToAntenna(3),
                bothToDummyLoad(4)
                }
            MAX-ACCESS read-write
            STATUS current
            DESCRIPTION
                "This sets 
                - outputstageA or 
                - outputstageB or
                - both
                to program path (antenna) of the transmitter,
                or it sets both to dummyload.
                
                The settings bothToAntenna(3) and bothToDummyLoad(4) are only settable 
                for ActiveReserve systems.
                
                This parameter is only available for systems with an automatic output switch."
            ::= { commandsTxEntry 12 }

        
        cmdTxDelayTimeExcAutomatic OBJECT-TYPE
            SYNTAX Integer32 (1..60)
            UNITS "seconds"
            MAX-ACCESS read-write
            STATUS current
            DESCRIPTION
                "This sets the exciter automatic delay time."
            ::= { commandsTxEntry 13 }

        
        cmdTxDelayTimeOstAutomatic OBJECT-TYPE
            SYNTAX Integer32 (1..60)
            UNITS "seconds"
            MAX-ACCESS read-write
            STATUS current
            DESCRIPTION
                "This sets the outputstage automatic delay time.
                
                This paramter is only available for systems with an automatic output switch."
            ::= { commandsTxEntry 14 }

        
        cmdDeviceIdx OBJECT-TYPE
            SYNTAX IndexAB
            MAX-ACCESS not-accessible
            STATUS current
            DESCRIPTION
                "This column is used to show parameters for both exiters, if you have 
                dualdrive transmitters."
            ::= { commandsTxEntry 99 }

        
        cmdExcOpModeInputAutomatic OBJECT-TYPE
            SYNTAX SwitchOnOff
            MAX-ACCESS read-write
            STATUS current
            DESCRIPTION
                "Activates/deactivates the input automatic.
                If input automatic is active 
                and a loss of input signal is detected on the current input
                the reserve input will be used instead."
            ::= { commandsTxEntry 100 }

        
        cmdExcPreselectInput OBJECT-TYPE
            SYNTAX INTEGER
                {
                input1(1),
                input2(2)
                }
            MAX-ACCESS read-write
            STATUS current
            DESCRIPTION
                "This sets the preselection of a transmitters input."
            ::= { commandsTxEntry 101 }

        
        cmdExcMode OBJECT-TYPE
            SYNTAX INTEGER
                {
                dvbT(1),
                dvbH(2)
                }
            MAX-ACCESS read-write
            STATUS current
            DESCRIPTION
                "Switch between DVB-T and DVB-H."
            ::= { commandsTxEntry 102 }

        
        cmdExcNetworkMode OBJECT-TYPE
            SYNTAX INTEGER
                {
                mfn(1),
                sfn(2)
                }
            MAX-ACCESS read-write
            STATUS current
            DESCRIPTION
                "Switch between Single Frequency Networks (SFN) and 
                Multiple Frequency Networks (MFN)."
            ::= { commandsTxEntry 103 }

        
        cmdExcTPSSource OBJECT-TYPE
            SYNTAX INTEGER
                {
                manualPresets(1),
                mip(2)
                }
            MAX-ACCESS read-write
            STATUS current
            DESCRIPTION
                "Transmitted TPS parameters can be adjusted manually inside 
                the transmitter or automatically via MIP from the SFN adaptor."
            ::= { commandsTxEntry 104 }

        
        cmdExcEnableCellID OBJECT-TYPE
            SYNTAX SwitchOnOff
            MAX-ACCESS read-write
            STATUS current
            DESCRIPTION
                "This enables the Cell ID insertion. 
                The length indicator will be adjusted."
            ::= { commandsTxEntry 105 }

        
        cmdExcTxAddress OBJECT-TYPE
            SYNTAX Integer32 (0..65535)
            MAX-ACCESS read-write
            STATUS current
            DESCRIPTION
                "This is the unique address of the transmitter 
                to reference specific settings in the MIP."
            ::= { commandsTxEntry 106 }

        
        cmdExcTxAutomatic OBJECT-TYPE
            SYNTAX SwitchOnOff
            MAX-ACCESS read-write
            STATUS current
            DESCRIPTION
                "This enables Tx specific parameters from the 
                MIP data caroussel (e.g. time offset, frequency offset)."
            ::= { commandsTxEntry 107 }

        
        cmdExcInputAutoSwitch OBJECT-TYPE
            SYNTAX SwitchOnOff
            MAX-ACCESS read-write
            STATUS deprecated
            DESCRIPTION
                "Activates/deactivates the input automatic.
                If input automatic is active 
                and a loss of input signal is detected on the current input
                the reserve input will be used instead.
                
                This object is deprecated. It's recommended to use cmdExcOpModeInputAutomatic instead."
            ::= { commandsTxEntry 108 }

        
        cmdExcInputSeamless OBJECT-TYPE
            SYNTAX SwitchOnOff
            MAX-ACCESS read-write
            STATUS current
            DESCRIPTION
                "If the datastreams on both inputs are syncronised a seamless switch is possible. 
                With this parameter the seamless switch can be suppressed to enable a check of the input automatic."
            ::= { commandsTxEntry 109 }

        
        cmdExcInputPriority OBJECT-TYPE
            SYNTAX INTEGER
                {
                equal(1),
                prior(2)
                }
            MAX-ACCESS read-write
            STATUS current
            DESCRIPTION
                "Equal: There are no differences between both inputs. 
                If a failure on the current input is detected it will be switched to the reserve input. 
                It stays there until the reserve shows a failure. 
                Prior: Whenever possible a certain input shall be used. 
                If a failure is detected the reserve will be used as short as possible."
            ::= { commandsTxEntry 110 }

        
        cmdExcInputCheckTimeForward OBJECT-TYPE
            SYNTAX Integer32 (0..600)
            UNITS "seconds"
            MAX-ACCESS read-write
            STATUS current
            DESCRIPTION
                "This time has to elapse before the current input switches 
                to the reserve input."
            ::= { commandsTxEntry 111 }

        
        cmdExcInputCheckTimeSwitchback OBJECT-TYPE
            SYNTAX Integer32 (0..600)
            UNITS "seconds"
            MAX-ACCESS read-write
            STATUS current
            DESCRIPTION
                "This time has to elapse before the automatic switches back 
                from the reserve to a preselected input. 
                This value has no effect if the priority is set to equal."
            ::= { commandsTxEntry 112 }

        
        cmdExcInputMuteOnFail OBJECT-TYPE
            SYNTAX INTEGER
                {
                mute(1),
                noMute(2)
                }
            MAX-ACCESS read-write
            STATUS current
            DESCRIPTION
                "If a loss of input signal is detected, the exciter mutes."
            ::= { commandsTxEntry 113 }

        
        cmdExcInputManualPreseletionHP1 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 114 }

        
        cmdExcInputManualPreseletionHP2 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 115 }

        
        cmdExcInputManualPreseletionLP1 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 116 }

        
        cmdExcInputManualPreseletionLP2 OBJECT-TYPE
            SYNTAX INTEGER
                {
                auto(1),
                asi(2),
                smpte(3)
                }
            MAX-ACCESS read-write
            STATUS current
            DESCRIPTION
                "The data format of the input can be detected 
                automatically or can be set manually to ASI or SMPTE."
            ::= { commandsTxEntry 117 }

        
        cmdExcTPSManualBandwidth OBJECT-TYPE
            SYNTAX INTEGER
                {
                mhz5(1),
                mhz6(2),
                mhz7(3),
                mhz8(4)
                }
            MAX-ACCESS read-write
            STATUS current
            DESCRIPTION
                "The bandwidth used by the RF channel."
            ::= { commandsTxEntry 118 }

        
        cmdExcTPSManualFFTLength OBJECT-TYPE
            SYNTAX INTEGER
                {
                k2(1),
                k8(2),
                k4(3)
                }
            MAX-ACCESS read-write
            STATUS current
            DESCRIPTION
                "The used FFT length (depends on the DVB network)."
            ::= { commandsTxEntry 119 }

        
        cmdExcTPSManualGuardInterval OBJECT-TYPE
            SYNTAX INTEGER
                {
                oneOf32(1),
                oneOf16(2),
                oneOf8(3),
                oneOf4(4)
                }
            MAX-ACCESS read-write
            STATUS current
            DESCRIPTION
                "The Guard interval affects the error correction in multipath receiving situations.
                A long Guard Interval reduces the amount of payload data."
            ::= { commandsTxEntry 120 }

        
        cmdExcTPSManualConstellation OBJECT-TYPE
            SYNTAX INTEGER
                {
                qpsk(1),
                qam16(2),
                qam64(3)
                }
            MAX-ACCESS read-write
            STATUS current
            DESCRIPTION
                "This parameter sets the modulation mode."
            ::= { commandsTxEntry 121 }

        
        cmdExcTPSManualAlpha OBJECT-TYPE
            SYNTAX INTEGER
                {
                noHierarchy(1),
                one(2),
                two(3),
                four(4)
                }
            MAX-ACCESS read-write
            STATUS obsolete
            DESCRIPTION
                "An alpha greater than noHierarchy(1) enables the hierarchical coding mode.
                obsoleted - always returns noHierarchy(1)"
            ::= { commandsTxEntry 122 }

        
        cmdExcTPSManualCellID OBJECT-TYPE
            SYNTAX Integer32 (0..65535)
            MAX-ACCESS read-write
            STATUS current
            DESCRIPTION
                "Via Cell ID the receiver knows the current network."
            ::= { commandsTxEntry 123 }

        
        cmdExcTPSManualInterleaver OBJECT-TYPE
            SYNTAX INTEGER
                {
                indepth(1),
                nat(2)
                }
            MAX-ACCESS read-write
            STATUS current
            DESCRIPTION
                "Enables the bit interleaver for hierarchical coding"
            ::= { commandsTxEntry 124 }

        
        cmdExcTPSManualCoderateHP OBJECT-TYPE
            SYNTAX INTEGER
                {
                oneOf2(1),
                twoOf3(2),
                threeOf4(3),
                fiveOf6(4),
                sevenOf8(5)
                }
            MAX-ACCESS read-write
            STATUS current
            DESCRIPTION
                "The Code Rate sets the ratio between payload and error correction information."
            ::= { commandsTxEntry 125 }

        
        cmdExcTPSManualCoderateLP OBJECT-TYPE
            SYNTAX INTEGER
                {
                oneOf2(1),
                twoOf3(2),
                threeOf4(3),
                fiveOf6(4),
                sevenOf8(5)
                }
            MAX-ACCESS read-write
            STATUS current
            DESCRIPTION
                "The Code Rate sets the ratio between payload and error correction information."
            ::= { commandsTxEntry 126 }

        
        cmdExcTPSManualTimeSlicingHP OBJECT-TYPE
            SYNTAX SwitchOnOff
            MAX-ACCESS read-write
            STATUS current
            DESCRIPTION
                "Enables the time slicing for hierarchical coding."
            ::= { commandsTxEntry 127 }

        
        cmdExcTPSManualTimeSlicingLP OBJECT-TYPE
            SYNTAX SwitchOnOff
            MAX-ACCESS read-write
            STATUS current
            DESCRIPTION
                "Enables the time slicing for hierarchical coding."
            ::= { commandsTxEntry 128 }

        
        cmdExcTPSManualFECHP OBJECT-TYPE
            SYNTAX SwitchOnOff
            MAX-ACCESS read-write
            STATUS current
            DESCRIPTION
                "Enables the forward error correction (FEC) for hierarchical coding."
            ::= { commandsTxEntry 129 }

        
        cmdExcTPSManualFECLP OBJECT-TYPE
            SYNTAX SwitchOnOff
            MAX-ACCESS read-write
            STATUS current
            DESCRIPTION
                "Enables the forward error correction (FEC) for hierarchical coding."
            ::= { commandsTxEntry 130 }

        
        cmdExcSFNStaticDelay OBJECT-TYPE
            SYNTAX FloatingPoint
            UNITS "Microseconds"
            MAX-ACCESS read-write
            STATUS current
            DESCRIPTION
                "A constant adjustable delay for tuning a SFN (-999999.9 ... 999999.9)."
            ::= { commandsTxEntry 131 }

        
        cmdExcSFNDeviationTime OBJECT-TYPE
            SYNTAX Integer32 (1..100)
            UNITS "Microseconds"
            MAX-ACCESS read-write
            STATUS current
            DESCRIPTION
                "Leap In Time.
                This parameter sets the deviation in time when a readjustment 
                of the dynamic delay is necessary."
            ::= { commandsTxEntry 132 }

        
        cmdExcFrequency OBJECT-TYPE
            SYNTAX Integer32 (47000000..1500000000)
            UNITS "Hertz"
            MAX-ACCESS read-write
            STATUS current
            DESCRIPTION
                "This is the RF frequency."
            ::= { commandsTxEntry 133 }

        
        cmdExcReferenceSource OBJECT-TYPE
            SYNTAX INTEGER
                {
                intern(1),
                extern5Mhz(2),
                extern10Mhz(3),
                extern1PPS(4)
                }
            MAX-ACCESS read-write
            STATUS current
            DESCRIPTION
                "The Source of the reference signal."
            ::= { commandsTxEntry 134 }

        
        cmdExcMuteOnPPSFail OBJECT-TYPE
            SYNTAX INTEGER
                {
                off(1),
                onlyAtStartup(2),
                afterFailDelayTime(3)
                }
            MAX-ACCESS read-write
            STATUS current
            DESCRIPTION
                "Select the behaviour if the external second pulse is not available."
            ::= { commandsTxEntry 135 }

        
        cmdExcMuteOnReferenceFail OBJECT-TYPE
            SYNTAX INTEGER
                {
                off(1),
                onlyAtStartup(2),
                afterFailDelayTime(3)
                }
            MAX-ACCESS read-write
            STATUS current
            DESCRIPTION
                "Select the behaviour if the external reference is not available."
            ::= { commandsTxEntry 136 }

        
        cmdExcRefFailDelayTime OBJECT-TYPE
            SYNTAX Integer32 (0..24)
            UNITS "Hours"
            MAX-ACCESS read-write
            STATUS current
            DESCRIPTION
                "Adjusts the time after the RF will be muted in case of a reference problem.
                Zero hours means react immediately."
            ::= { commandsTxEntry 137 }

        
        cmdExcTypeLossOfInput OBJECT-TYPE
            SYNTAX INTEGER
                {
                warning(1),
                fault(2)
                }
            MAX-ACCESS read-write
            STATUS current
            DESCRIPTION
                "If the input signal is lost, either a warning or a fault can be generated.
                If you select fault here, a switchover to the reserve exciter will be executed 
                when input signal is lost."
            ::= { commandsTxEntry 138 }

        
        cmdExcRfOutput OBJECT-TYPE
            SYNTAX SwitchOnOff
            MAX-ACCESS read-write
            STATUS current
            DESCRIPTION
                "Turns on/switches off the output signal. This switch takes the same effect as the switch on the frontpanel of the exciter."
            ::= { commandsTxEntry 139 }

        
        cmdExcRfOutputRegulation OBJECT-TYPE
            SYNTAX SwitchOnOff
            MAX-ACCESS read-write
            STATUS current
            DESCRIPTION
                "Turns on/switches off the automatic output level regulation."
            ::= { commandsTxEntry 140 }

        
        cmdExcRfOutputManualRfLevel OBJECT-TYPE
            SYNTAX FloatingPoint
            UNITS "Percent"
            MAX-ACCESS read-write
            STATUS current
            DESCRIPTION
                "Adjusts the RF level (0.0 ... 100.0). The value relates to an attenuation of 0 dB."
            ::= { commandsTxEntry 141 }

        
        cmdExcRfOutputAttenuation OBJECT-TYPE
            SYNTAX Integer32 (0..9)
            UNITS "dB"
            MAX-ACCESS read-write
            STATUS current
            DESCRIPTION
                "Activates internal attenuators to reduce the output level of the exciter.
                Adjustable in steps of 3 dB only."
            ::= { commandsTxEntry 142 }

        
        cmdExcRfOutputRfSlope OBJECT-TYPE
            SYNTAX FloatingPoint
            UNITS "Percent"
            MAX-ACCESS read-write
            STATUS current
            DESCRIPTION
                "Adjusts a slope in the RF signal (-50.0 ... 50.0)."
            ::= { commandsTxEntry 143 }

        
        cmdExcRfOutputModulationSlope OBJECT-TYPE
            SYNTAX FloatingPoint
            UNITS "Percent"
            MAX-ACCESS read-write
            STATUS current
            DESCRIPTION
                "Modulation slope (-50.0 ... 50.0)."
            ::= { commandsTxEntry 144 }

        
        cmdExcRfIqAdjustStart OBJECT-TYPE
            SYNTAX INTEGER
                {
                break(1),
                start(2)
                }
            MAX-ACCESS read-write
            STATUS current
            DESCRIPTION
                "Starts the automatic IQ adjustment. It works for the current used local 1 frequency and lasts up to 5 minutes. In this time the output will be muted. During the adjustment no transmitter parameter shall be changed. Break will stop the automatic immediately. The IQ modulator looses its adjustment!
                Read values mean idle(1) and started(2)."
            ::= { commandsTxEntry 146 }

        
        cmdExcRfIqAdjustTestsignal OBJECT-TYPE
            SYNTAX SwitchOnOff
            MAX-ACCESS read-write
            STATUS current
            DESCRIPTION
                "Generates a test signal to adjust the IQ modulation. It is necessary to disconnect the rf-cable to the output stages."
            ::= { commandsTxEntry 147 }

        
        cmdExcRfIqAdjustBiasCoarseI OBJECT-TYPE
            SYNTAX Integer32 (-1023..1023)
            MAX-ACCESS read-write
            STATUS current
            DESCRIPTION
                "Adjusts the offset for I in huge steps."
            ::= { commandsTxEntry 148 }

        
        cmdExcRfIqAdjustBiasCoarseQ OBJECT-TYPE
            SYNTAX Integer32 (-1023..1023)
            MAX-ACCESS read-write
            STATUS current
            DESCRIPTION
                "Adjusts the offset for Q in huge steps."
            ::= { commandsTxEntry 149 }

        
        cmdExcRfIqAdjustBiasFineI OBJECT-TYPE
            SYNTAX Integer32 (-32767..32767)
            MAX-ACCESS read-write
            STATUS current
            DESCRIPTION
                "Adjusts the offset for I in small steps."
            ::= { commandsTxEntry 150 }

        
        cmdExcRfIqAdjustBiasFineQ OBJECT-TYPE
            SYNTAX Integer32 (-32767..32767)
            MAX-ACCESS read-write
            STATUS current
            DESCRIPTION
                "Adjusts the offset for Q in small steps."
            ::= { commandsTxEntry 151 }

        
        cmdExcRfIqAdjustGainI OBJECT-TYPE
            SYNTAX Integer32 (0..255)
            MAX-ACCESS read-write
            STATUS current
            DESCRIPTION
                "Adjusts the gain for I in small steps."
            ::= { commandsTxEntry 152 }

        
        cmdExcRfIqAdjustGainQ OBJECT-TYPE
            SYNTAX Integer32 (0..255)
            MAX-ACCESS read-write
            STATUS current
            DESCRIPTION
                "Adjusts the gain for Q in small steps."
            ::= { commandsTxEntry 153 }

        
        cmdExcRfIqAdjustPhase OBJECT-TYPE
            SYNTAX FloatingPoint
            MAX-ACCESS read-write
            STATUS current
            DESCRIPTION
                "Adjusts the phase between I and Q (-14.000 ... 14.000)."
            ::= { commandsTxEntry 154 }

        
        cmdExcInput1Source OBJECT-TYPE
            SYNTAX InputSource
            MAX-ACCESS read-write
            STATUS current
            DESCRIPTION
                "Source for input 1.
                
                For Slx only."
            ::= { commandsTxEntry 155 }

        
        cmdExcInput2Source OBJECT-TYPE
            SYNTAX InputSource
            MAX-ACCESS read-write
            STATUS current
            DESCRIPTION
                "Source for input 2.
                
                For Slx only."
            ::= { commandsTxEntry 156 }

        
        cmdExcInpAutoReadyAfterChangeOv OBJECT-TYPE
            SYNTAX SwitchOnOff
            MAX-ACCESS read-write
            STATUS current
            DESCRIPTION
                "Input automatic ready after change over."
            ::= { commandsTxEntry 157 }

        
        cmdExcInputFailDelayTime OBJECT-TYPE
            SYNTAX Integer32 (0..600)
            UNITS "Seconds"
            MAX-ACCESS read-write
            STATUS current
            DESCRIPTION
                "The time between detecting a loss of input signal and displaying a failure."
            ::= { commandsTxEntry 158 }

        
        cmdExcMuteCondition OBJECT-TYPE
            SYNTAX INTEGER
                {
                onAllFaults(1),
                notBeforeSyncLoss(2)
                }
            MAX-ACCESS read-write
            STATUS current
            DESCRIPTION
                "When notBeforeSyncLoss(2) is selected,
                it relativizes the cmdExcInputMuteOnFail setting mute(1):
                If a DVB receiver is the last valid input, an existing transport stream,
                even if it is faulty shall not be muted.
                
                Only for SLx/Sx801"
            ::= { commandsTxEntry 161 }

        
        cmdExcMonitoringOutput OBJECT-TYPE
            SYNTAX INTEGER
                {
                off(1),
                reference10MHz(2),
                generated1PPS(3),
                kHz1(4),
                pulse1PPS(5)
                }
            MAX-ACCESS read-write
            STATUS current
            DESCRIPTION
                "Selects which signal appears at the monitoring output."
            ::= { commandsTxEntry 179 }

        
        cmdExcOcxoAdjust OBJECT-TYPE
            SYNTAX Integer32 (0..65535)
            MAX-ACCESS read-write
            STATUS current
            DESCRIPTION
                "Adjusts the frequency of the internal 10 MHz reference.
                This value only takes effect if the reference source 'internal' is selected."
            ::= { commandsTxEntry 180 }

        
        cmdExcExpectInputReserve OBJECT-TYPE
            SYNTAX SwitchOnOff
            MAX-ACCESS read-write
            STATUS current
            DESCRIPTION
                "If on(1) the warning txExcInputReseveMissing will be generated
                in case second input is missing."
            ::= { commandsTxEntry 181 }

        
        cmdExcEnablePcrReset OBJECT-TYPE
            SYNTAX SwitchOnOff
            MAX-ACCESS read-write
            STATUS obsolete
            DESCRIPTION
                "Enables/disables daily PCR resets.
                This option is valid only in MFN operation.
                The reset time is given in cmdExcTimeForDailyPcrReset."
            ::= { commandsTxEntry 182 }

        
        cmdExcTimeForDailyPcrReset OBJECT-TYPE
            SYNTAX TimeOfDay
            MAX-ACCESS read-write
            STATUS obsolete
            DESCRIPTION
                "Sets the time of day for daily PCR reset."
            ::= { commandsTxEntry 183 }

        
        cmdExcFailDelayMode OBJECT-TYPE
            SYNTAX FailDelayMode
            MAX-ACCESS read-write
            STATUS current
            DESCRIPTION
                "Condition when the fail delay time is used."
            ::= { commandsTxEntry 184 }

        
        cmdExcTransparentTs OBJECT-TYPE
            SYNTAX SwitchOnOff
            MAX-ACCESS read-write
            STATUS current
            DESCRIPTION
                "If enabled in MFN, then stuffing and PCR restamping is off;
                output datarate is controlled by input datarate.
                In SFN this option is always enabled."
            ::= { commandsTxEntry 185 }

        
        cmdOstRefVoltageVision OBJECT-TYPE
            SYNTAX FloatingPoint
            UNITS "Percent"
            MAX-ACCESS read-write
            STATUS current
            DESCRIPTION
                "This adjusts the output power of the amplifier.
                This value is settable witch maximal 1 position after point (example 11.2)."
            ::= { commandsTxEntry 200 }

        
        cmdOstMaxOutletTempThreshold OBJECT-TYPE
            SYNTAX Integer32 (45..65)
            UNITS "Degree Celsius"
            MAX-ACCESS read-write
            STATUS current
            DESCRIPTION
                "This sets the threshold for the outlet temperature."
            ::= { commandsTxEntry 201 }

        
        summaryInfoTxTable OBJECT-TYPE
            SYNTAX SEQUENCE OF SummaryInfoTxEntry
            MAX-ACCESS not-accessible
            STATUS current
            DESCRIPTION
                "This table shows overall information for all transmitters.
                An equivalent would be System Overview at the NCU."
            ::= { transmitter 2 }

        
        summaryInfoTxEntry OBJECT-TYPE
            SYNTAX SummaryInfoTxEntry
            MAX-ACCESS not-accessible
            STATUS current
            DESCRIPTION
                "An entry for a designated transmitter."
            INDEX { statusTxIdx }
            ::= { summaryInfoTxTable 1 }

        
        SummaryInfoTxEntry ::=
            SEQUENCE { 
                statusTxIdx
                    IndexTransmitter,
                statusTxName
                    IndexTransmitter,
                statusTxNoConnection
                    TruthValue,
                statusTxSummaryFault
                    TruthValue,
                statusTxSummaryWarning
                    TruthValue,
                statusTxLocalMode
                    TruthValue,
                statusTxRfOn
                    TruthValue,
                statusTxForwardPower
                    FloatingPoint,
                statusTxReflectedPower
                    FloatingPoint,
                statusTxSummaryFaultExcA
                    TruthValue,
                statusTxSummaryFaultOstA
                    TruthValue,
                statusTxSummaryFaultExcB
                    TruthValue,
                statusTxSummaryFaultOstB
                    TruthValue,
                statusTxExciterAutomaticReady
                    TruthValue,
                statusTxExciterAutomaticChanged
                    TruthValue,
                statusTxExciterAutomaticFault
                    TruthValue,
                statusTxOstAutomaticReady
                    TruthValue,
                statusTxOstAutomaticChanged
                    TruthValue,
                statusTxOstAutomaticFault
                    TruthValue,
                statusTxNoConnectionExcA
                    TruthValue,
                statusTxNoConnectionOstA
                    TruthValue,
                statusTxNoConnectionExcB
                    TruthValue,
                statusTxNoConnectionOstB
                    TruthValue,
                statusTxActiveExcA
                    TruthValue,
                statusTxActiveOstA
                    TruthValue,
                statusTxActiveExcB
                    TruthValue,
                statusTxActiveOstB
                    TruthValue,
                statusTxExcSwitch
                    INTEGER,
                statusTxOstSwitch
                    INTEGER,
                statusTxNoConnectionApaIf
                    TruthValue,
                statusTxAbsorberFault
                    TruthValue,
                statusTxPowerSupply
                    FloatingPoint,
                statusTxAdditionalPowerSupply
                    TruthValue,
                statusTxInternalPowerSupply
                    FloatingPoint,
                statusTxExternalPowerSupply
                    FloatingPoint
             }

        statusTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { summaryInfoTxEntry 1 }

        
        statusTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { summaryInfoTxEntry 2 }

        
        statusTxNoConnection OBJECT-TYPE
            SYNTAX TruthValue
            MAX-ACCESS read-only
            STATUS current
            DESCRIPTION
                "No connection between NCU and transmitter."
            ::= { summaryInfoTxEntry 3 }

        
        statusTxSummaryFault OBJECT-TYPE
            SYNTAX TruthValue
            MAX-ACCESS read-only
            STATUS current
            DESCRIPTION
                "This indicates a summary fault of the transmitter.
                true(1)  --> summary fault
                false(2) --> no summary fault
                
                There is a fault of at least one module (e.g. Exciter) which causes this summary fault.
                
                An equivalent would be the LED Fault at the transmitters frontpanel."
            ::= { summaryInfoTxEntry 4 }

        
        statusTxSummaryWarning OBJECT-TYPE
            SYNTAX TruthValue
            MAX-ACCESS read-only
            STATUS current
            DESCRIPTION
                "This indicates a summary warning of the transmitter.
                true(1)  --> summary warning
                false(2) --> no summary warning
                
                There is a fault of at least one module (e.g. Exciter) which causes this summary warning.
                
                An equivalent would be the LED Warning at the transmitters frontpanel."
            ::= { summaryInfoTxEntry 5 }

        
        statusTxLocalMode OBJECT-TYPE
            SYNTAX TruthValue
            MAX-ACCESS read-only
            STATUS current
            DESCRIPTION
                "This indicates the local/remote-mode of the transmitter.
                true(1)  --> local
                false(2) --> remote
                
                The transmitter is eigther in local-mode or in remote-mode. 
                For security reasons it is not possible to set this value!
                
                An equivalent would the LED Local at the transmitters frontpanel."
            ::= { summaryInfoTxEntry 6 }

        
        statusTxRfOn OBJECT-TYPE
            SYNTAX TruthValue
            MAX-ACCESS read-only
            STATUS current
            DESCRIPTION
                "The RF is present for the corresponding transmitter."
            ::= { summaryInfoTxEntry 7 }

        
        statusTxForwardPower OBJECT-TYPE
            SYNTAX FloatingPoint
            UNITS "Watt"
            MAX-ACCESS read-only
            STATUS current
            DESCRIPTION
                "The measured forwarded power [W]."
            ::= { summaryInfoTxEntry 13 }

        
        statusTxReflectedPower OBJECT-TYPE
            SYNTAX FloatingPoint
            UNITS "Watt"
            MAX-ACCESS read-only
            STATUS current
            DESCRIPTION
                "The measured reflected power [W] (not available for lowpower)."
            ::= { summaryInfoTxEntry 14 }

        
        statusTxSummaryFaultExcA OBJECT-TYPE
            SYNTAX TruthValue
            MAX-ACCESS read-only
            STATUS current
            DESCRIPTION
                "This indicates a summary fault of exciter."
            ::= { summaryInfoTxEntry 15 }

        
        statusTxSummaryFaultOstA OBJECT-TYPE
            SYNTAX TruthValue
            MAX-ACCESS read-only
            STATUS current
            DESCRIPTION
                "This indicates a summary fault of outputstage."
            ::= { summaryInfoTxEntry 16 }

        
        statusTxSummaryFaultExcB OBJECT-TYPE
            SYNTAX TruthValue
            MAX-ACCESS read-only
            STATUS current
            DESCRIPTION
                "This indicates a summary fault of exciter."
            ::= { summaryInfoTxEntry 17 }

        
        statusTxSummaryFaultOstB OBJECT-TYPE
            SYNTAX TruthValue
            MAX-ACCESS read-only
            STATUS current
            DESCRIPTION
                "This indicates a summary fault of outputstage."
            ::= { summaryInfoTxEntry 18 }

        
        statusTxExciterAutomaticReady OBJECT-TYPE
            SYNTAX TruthValue
            MAX-ACCESS read-only
            STATUS current
            DESCRIPTION
                "The Exciter Automatic is Ready. 
                In case of any fault on one exciter, there will be a switchover to the other exciter."
            ::= { summaryInfoTxEntry 19 }

        
        statusTxExciterAutomaticChanged OBJECT-TYPE
            SYNTAX TruthValue
            MAX-ACCESS read-only
            STATUS current
            DESCRIPTION
                "The Exciter Automatic has changed. 
                There was a fault on one exciter which lead to this changeover."
            ::= { summaryInfoTxEntry 20 }

        
        statusTxExciterAutomaticFault OBJECT-TYPE
            SYNTAX TruthValue
            MAX-ACCESS read-only
            STATUS current
            DESCRIPTION
                "The Exciter Automatic is faulty. 
                In case of any fault on one exciter, there will be no switchover to the other exciter,
                because of this fault."
            ::= { summaryInfoTxEntry 21 }

        
        statusTxOstAutomaticReady OBJECT-TYPE
            SYNTAX TruthValue
            MAX-ACCESS read-only
            STATUS current
            DESCRIPTION
                "The Outputstage Automatic is Ready. 
                In case of any fault on one outputstage, there will be a switchover to the other outputstage.
                
                This paramter is only available for systems with an automatic output switch."
            ::= { summaryInfoTxEntry 22 }

        
        statusTxOstAutomaticChanged OBJECT-TYPE
            SYNTAX TruthValue
            MAX-ACCESS read-only
            STATUS current
            DESCRIPTION
                "The Outputstage Automatic has changed. 
                There was a fault on one outputstage which lead to this changeover.
                
                This paramter is only available for systems with an automatic output switch."
            ::= { summaryInfoTxEntry 23 }

        
        statusTxOstAutomaticFault OBJECT-TYPE
            SYNTAX TruthValue
            MAX-ACCESS read-only
            STATUS current
            DESCRIPTION
                "The Outputstage Automatic is faulty. 
                In case of any fault on one outputstage, there will be no switchover to the other outputstage,
                because of this fault.
                
                This paramter is only available for systems with an automatic output switch."
            ::= { summaryInfoTxEntry 24 }

        
        statusTxNoConnectionExcA OBJECT-TYPE
            SYNTAX TruthValue
            MAX-ACCESS read-only
            STATUS current
            DESCRIPTION
                "No Connection between NetCCU and Exciter."
            ::= { summaryInfoTxEntry 25 }

        
        statusTxNoConnectionOstA OBJECT-TYPE
            SYNTAX TruthValue
            MAX-ACCESS read-only
            STATUS current
            DESCRIPTION
                "No Connection between NetCCU and Outputstage."
            ::= { summaryInfoTxEntry 26 }

        
        statusTxNoConnectionExcB OBJECT-TYPE
            SYNTAX TruthValue
            MAX-ACCESS read-only
            STATUS current
            DESCRIPTION
                "No Connection between NetCCU and Exciter."
            ::= { summaryInfoTxEntry 27 }

        
        statusTxNoConnectionOstB OBJECT-TYPE
            SYNTAX TruthValue
            MAX-ACCESS read-only
            STATUS current
            DESCRIPTION
                "No Connection between NetCCU and Outputstage."
            ::= { summaryInfoTxEntry 28 }

        
        statusTxActiveExcA OBJECT-TYPE
            SYNTAX TruthValue
            MAX-ACCESS read-only
            STATUS current
            DESCRIPTION
                "ExciterA is currently active."
            ::= { summaryInfoTxEntry 29 }

        
        statusTxActiveOstA OBJECT-TYPE
            SYNTAX TruthValue
            MAX-ACCESS read-only
            STATUS current
            DESCRIPTION
                "OutputstageA is currently active."
            ::= { summaryInfoTxEntry 30 }

        
        statusTxActiveExcB OBJECT-TYPE
            SYNTAX TruthValue
            MAX-ACCESS read-only
            STATUS current
            DESCRIPTION
                "ExciterB is currently active."
            ::= { summaryInfoTxEntry 31 }

        
        statusTxActiveOstB OBJECT-TYPE
            SYNTAX TruthValue
            MAX-ACCESS read-only
            STATUS current
            DESCRIPTION
                "OutputstageB is currently active."
            ::= { summaryInfoTxEntry 32 }

        
        statusTxExcSwitch OBJECT-TYPE
            SYNTAX INTEGER
                {
                fault(1),
                excAToOstA(2),
                excBToOstA(3),
                excAToBothOst(4),
                excBToBothOst(5)
                }
            MAX-ACCESS read-only
            STATUS current
            DESCRIPTION
                "Current state of the exciter RF switch.
                
                In a PassivePa or ActivePa system
                value excAToOstA(2) implies that exciter B is connected to output stage B;
                and
                value excBToOstA(3) implies that exciter A is connected to output stage B.
                
                When the system is not SingleTx there is a corresponding preselection object:
                cmdTxPreselectExciter."
            ::= { summaryInfoTxEntry 33 }

        
        statusTxOstSwitch OBJECT-TYPE
            SYNTAX INTEGER
                {
                fault(1),
                ostAToAntenna(2),
                ostBToAntenna(3),
                bothToAntenna(4),
                bothToDummyLoad(5),
                undefined(6)
                }
            MAX-ACCESS read-only
            STATUS current
            DESCRIPTION
                "Current state of the output stage RF switch.
                
                In a PassivePa or ActivePa system
                value ostAToAntenna(2) implies that output stage B is connected to dummy load;
                and
                value ostBToAntenna(3) implies that output stage A is connected to dummy load.
                
                When the system is PassivePa or ActivePa with an automatic power switch
                there is a corresponding preselection object: cmdTxPreselectExciter."
            ::= { summaryInfoTxEntry 34 }

        
        statusTxNoConnectionApaIf OBJECT-TYPE
            SYNTAX TruthValue
            MAX-ACCESS read-only
            STATUS current
            DESCRIPTION
                "NetCCU can not communicate to the APA-Interface."
            ::= { summaryInfoTxEntry 35 }

        
        statusTxAbsorberFault OBJECT-TYPE
            SYNTAX TruthValue
            MAX-ACCESS read-only
            STATUS current
            DESCRIPTION
                "Absorber fault occurred.
                "
            ::= { summaryInfoTxEntry 36 }

        
        statusTxPowerSupply OBJECT-TYPE
            SYNTAX FloatingPoint
            UNITS "volt"
            MAX-ACCESS read-only
            STATUS current
            DESCRIPTION
                "Monitoring value of the output voltages of the power supply."
            ::= { summaryInfoTxEntry 37 }

        
        statusTxAdditionalPowerSupply OBJECT-TYPE
            SYNTAX TruthValue
            MAX-ACCESS read-only
            STATUS current
            DESCRIPTION
                "Shows whether the NetCCU has an additional (external) power supply."
            ::= { summaryInfoTxEntry 38 }

        
        statusTxInternalPowerSupply OBJECT-TYPE
            SYNTAX FloatingPoint
            UNITS "volt"
            MAX-ACCESS read-only
            STATUS current
            DESCRIPTION
                "Monitoring value of the output voltages of the internal power supply."
            ::= { summaryInfoTxEntry 39 }

        
        statusTxExternalPowerSupply OBJECT-TYPE
            SYNTAX FloatingPoint
            UNITS "volt"
            MAX-ACCESS read-only
            STATUS current
            DESCRIPTION
                "Monitoring value of the output voltages of the external power supply."
            ::= { summaryInfoTxEntry 40 }

        
        txA1 OBJECT IDENTIFIER ::= { transmitter 5 }

        
        logbookTxA1 OBJECT IDENTIFIER ::= { txA1 1 }

        
        txA1NetCCUNumberOfEntries OBJECT-TYPE
            SYNTAX LogbookMaxEntryNumber
            MAX-ACCESS read-only
            STATUS current
            DESCRIPTION
                "The number of entries in logbook."
            ::= { logbookTxA1 1 }

        
        txA1NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 2 }

        
        txA1NetCCULogbookTable OBJECT-TYPE
            SYNTAX SEQUENCE OF TxA1NetCCULogbookEntry
            MAX-ACCESS not-accessible
            STATUS current
            DESCRIPTION
                "NetCCU logbook table."
            ::= { logbookTxA1 3 }

        
        txA1NetCCULogbookEntry OBJECT-TYPE
            SYNTAX TxA1NetCCULogbookEntry
            MAX-ACCESS not-accessible
            STATUS current
            DESCRIPTION
                "This is a entry in the logbook."
            INDEX { txA1NetCCULogbookEntryIdx }
            ::= { txA1NetCCULogbookTable 1 }

        
        TxA1NetCCULogbookEntry ::=
            SEQUENCE { 
                txA1NetCCULogbookEntryIdx
                    LogbookMaxEntryNumber,
                txA1NetCCULogbookEntryNbr
                    LogbookMaxEntryNumber,
                txA1NetCCULogbookType
                    EventClass,
                txA1NetCCULogbookSlope
                    LogbookEntrySlope,
                txA1NetCCULogbookMessage
                    LogbookEntryMessagesNetCCU,
                txA1NetCCULogbookDateTime
                    DateAndTime
             }

        txA1NetCCULogbookEntryIdx OBJECT-TYPE
            SYNTAX LogbookMaxEntryNumber
            MAX-ACCESS not-accessible
            STATUS current
            DESCRIPTION
                "This is an increasing number from 1 to maximum. It is used as an index column for SNMP."
            ::= { txA1NetCCULogbookEntry 1 }

        
        txA1NetCCULogbookEntryNbr OBJECT-TYPE
            SYNTAX LogbookMaxEntryNumber
            MAX-ACCESS read-only
            STATUS current
            DESCRIPTION
                "This is the number of the logbook entry. It is an decreasing number from maximum down to 1."
            ::= { txA1NetCCULogbookEntry 2 }

        
        txA1NetCCULogbookType OBJECT-TYPE
            SYNTAX EventClass
            MAX-ACCESS read-only
            STATUS current
            DESCRIPTION
                "Can either be Fault, Warning or State."
            ::= { txA1NetCCULogbookEntry 3 }

        
        txA1NetCCULogbookSlope OBJECT-TYPE
            SYNTAX LogbookEntrySlope
            MAX-ACCESS read-only
            STATUS current
            DESCRIPTION
                "Either set (event raises) or reset (event disappears)"
            ::= { txA1NetCCULogbookEntry 4 }

        
        txA1NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA1NetCCULogbookEntry 5 }

        
        txA1NetCCULogbookDateTime OBJECT-TYPE
            SYNTAX DateAndTime
            MAX-ACCESS read-only
            STATUS current
            DESCRIPTION
                "The time of the logbook entry."
            ::= { txA1NetCCULogbookEntry 6 }

        
        txA1ExciterANumberOfEntries OBJECT-TYPE
            SYNTAX LogbookMaxEntryNumber
            MAX-ACCESS read-only
            STATUS current
            DESCRIPTION
                "The number of entries in logbook."
            ::= { logbookTxA1 4 }

        
        txA1ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 5 }

        
        txA1ExciterALogbookTable OBJECT-TYPE
            SYNTAX SEQUENCE OF TxA1ExciterALogbookEntry
            MAX-ACCESS not-accessible
            STATUS current
            DESCRIPTION
                "ExciterA logbook table."
            ::= { logbookTxA1 6 }

        
        txA1ExciterALogbookEntry OBJECT-TYPE
            SYNTAX TxA1ExciterALogbookEntry
            MAX-ACCESS not-accessible
            STATUS current
            DESCRIPTION
                "This is a entry in the logbook."
            INDEX { txA1ExcALogbookEntryIdx }
            ::= { txA1ExciterALogbookTable 1 }

        
        TxA1ExciterALogbookEntry ::=
            SEQUENCE { 
                txA1ExcALogbookEntryIdx
                    LogbookMaxEntryNumber,
                txA1ExcALogbookEntryNbr
                    LogbookMaxEntryNumber,
                txA1ExcALogbookType
                    EventClass,
                txA1ExcALogbookSlope
                    LogbookEntrySlope,
                txA1ExcALogbookMessage
                    LogbookEntryMessagesExcTv,
                txA1ExcALogbookDateTime
                    DateAndTime
             }

        txA1ExcALogbookEntryIdx OBJECT-TYPE
            SYNTAX LogbookMaxEntryNumber
            MAX-ACCESS not-accessible
            STATUS current
            DESCRIPTION
                "This is an increasing number from 1 to 128. It is used as an index column for SNMP."
            ::= { txA1ExciterALogbookEntry 1 }

        
        txA1ExcALogbookEntryNbr OBJECT-TYPE
            SYNTAX LogbookMaxEntryNumber
            MAX-ACCESS read-only
            STATUS current
            DESCRIPTION
                "This is the number of the logbook entry. It is an decreasing number from max 128 down to 1."
            ::= { txA1ExciterALogbookEntry 2 }

        
        txA1ExcALogbookType OBJECT-TYPE
            SYNTAX EventClass
            MAX-ACCESS read-only
            STATUS current
            DESCRIPTION
                "Can either be Fault, Warning or State."
            ::= { txA1ExciterALogbookEntry 3 }

        
        txA1ExcALogbookSlope OBJECT-TYPE
            SYNTAX LogbookEntrySlope
            MAX-ACCESS read-only
            STATUS current
            DESCRIPTION
                "Either set (event raises) or reset (event disappears)"
            ::= { txA1ExciterALogbookEntry 4 }

        
        txA1ExcALogbookMessage OBJECT-TYPE
            SYNTAX LogbookEntryMessagesExcTv
            MAX-ACCESS read-only
            STATUS current
            DESCRIPTION
                "See RS-XX8000-COMMON-MIB - TextualConvention for details."
            ::= { txA1ExciterALogbookEntry 5 }

        
        txA1ExcALogbookDateTime OBJECT-TYPE
            SYNTAX DateAndTime
            MAX-ACCESS read-only
            STATUS current
            DESCRIPTION
                "The time of the logbook entry."
            ::= { txA1ExciterALogbookEntry 6 }

        
        txA1OutputstageANumberOfEntries OBJECT-TYPE
            SYNTAX LogbookMaxEntryNumber
            MAX-ACCESS read-only
            STATUS current
            DESCRIPTION
                "The number of entries in logbook."
            ::= { logbookTxA1 7 }

        
        txA1OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 8 }

        
        txA1OutputstageALogbookTable OBJECT-TYPE
            SYNTAX SEQUENCE OF TxA1OutputstageALogbookEntry
            MAX-ACCESS not-accessible
            STATUS current
            DESCRIPTION
                "OutputstageA logbook table."
            ::= { logbookTxA1 9 }

        
        txA1OutputstageALogbookEntry OBJECT-TYPE
            SYNTAX TxA1OutputstageALogbookEntry
            MAX-ACCESS not-accessible
            STATUS current
            DESCRIPTION
                "This is a entry in the logbook."
            INDEX { txA1OstALogbookEntryIdx }
            ::= { txA1OutputstageALogbookTable 1 }

        
        TxA1OutputstageALogbookEntry ::=
            SEQUENCE { 
                txA1OstALogbookEntryIdx
                    LogbookMaxEntryNumber,
                txA1OstALogbookEntryNbr
                    LogbookMaxEntryNumber,
                txA1OstALogbookType
                    EventClass,
                txA1OstALogbookSlope
                    LogbookEntrySlope,
                txA1OstALogbookMessage
                    LogbookEntryMessagesOST,
                txA1OstALogbookDateTime
                    DateAndTime
             }

        txA1OstALogbookEntryIdx OBJECT-TYPE
            SYNTAX LogbookMaxEntryNumber
            MAX-ACCESS not-accessible
            STATUS current
            DESCRIPTION
                "This is an increasing number from 1 to maximum. It is used as an index column for SNMP."
            ::= { txA1OutputstageALogbookEntry 1 }

        
        txA1OstALogbookEntryNbr OBJECT-TYPE
            SYNTAX LogbookMaxEntryNumber
            MAX-ACCESS read-only
            STATUS current
            DESCRIPTION
                "This is the number of the logbook entry. It is an decreasing number from maximum down to 1."
            ::= { txA1OutputstageALogbookEntry 2 }

        
        txA1OstALogbookType OBJECT-TYPE
            SYNTAX EventClass
            MAX-ACCESS read-only
            STATUS current
            DESCRIPTION
                "Can either be Fault, Warning or State."
            ::= { txA1OutputstageALogbookEntry 3 }

        
        txA1OstALogbookSlope OBJECT-TYPE
            SYNTAX LogbookEntrySlope
            MAX-ACCESS read-only
            STATUS current
            DESCRIPTION
                "Either set (event raises) or reset (event disappears)"
            ::= { txA1OutputstageALogbookEntry 4 }

        
        txA1OstALogbookMessage OBJECT-TYPE
            SYNTAX LogbookEntryMessagesOST
            MAX-ACCESS read-only
            STATUS current
            DESCRIPTION
                "See RS-XX8000-COMMON-MIB - TextualConvention for details."
            ::= { txA1OutputstageALogbookEntry 5 }

        
        txA1OstALogbookDateTime OBJECT-TYPE
            SYNTAX DateAndTime
            MAX-ACCESS read-only
            STATUS current
            DESCRIPTION
                "The time of the logbook entry."
            ::= { txA1OutputstageALogbookEntry 6 }

        
        txA1ExciterBNumberOfEntries OBJECT-TYPE
            SYNTAX LogbookMaxEntryNumber
            MAX-ACCESS read-only
            STATUS current
            DESCRIPTION
                "The number of entries in logbook."
            ::= { logbookTxA1 13 }

        
        txA1ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 14 }

        
        txA1ExciterBLogbookTable OBJECT-TYPE
            SYNTAX SEQUENCE OF TxA1ExciterBLogbookEntry
            MAX-ACCESS not-accessible
            STATUS current
            DESCRIPTION
                "ExciterB logbook table."
            ::= { logbookTxA1 15 }

        
        txA1ExciterBLogbookEntry OBJECT-TYPE
            SYNTAX TxA1ExciterBLogbookEntry
            MAX-ACCESS not-accessible
            STATUS current
            DESCRIPTION
                "This is a entry in the logbook."
            INDEX { txA1ExcBLogbookEntryIdx }
            ::= { txA1ExciterBLogbookTable 1 }

        
        TxA1ExciterBLogbookEntry ::=
            SEQUENCE { 
                txA1ExcBLogbookEntryIdx
                    LogbookMaxEntryNumber,
                txA1ExcBLogbookEntryNbr
                    LogbookMaxEntryNumber,
                txA1ExcBLogbookType
                    EventClass,
                txA1ExcBLogbookSlope
                    LogbookEntrySlope,
                txA1ExcBLogbookMessage
                    LogbookEntryMessagesExcTv,
                txA1ExcBLogbookDateTime
                    DateAndTime
             }

        txA1ExcBLogbookEntryIdx OBJECT-TYPE
            SYNTAX LogbookMaxEntryNumber
            MAX-ACCESS not-accessible
            STATUS current
            DESCRIPTION
                "This is an increasing number from 1 to maximum. It is used as an index column for SNMP."
            ::= { txA1ExciterBLogbookEntry 1 }

        
        txA1ExcBLogbookEntryNbr OBJECT-TYPE
            SYNTAX LogbookMaxEntryNumber
            MAX-ACCESS read-only
            STATUS current
            DESCRIPTION
                "This is the number of the logbook entry. It is an decreasing number from maximum down to 1."
            ::= { txA1ExciterBLogbookEntry 2 }

        
        txA1ExcBLogbookType OBJECT-TYPE
            SYNTAX EventClass
            MAX-ACCESS read-only
            STATUS current
            DESCRIPTION
                "Can either be Fault, Warning or State."
            ::= { txA1ExciterBLogbookEntry 3 }

        
        txA1ExcBLogbookSlope OBJECT-TYPE
            SYNTAX LogbookEntrySlope
            MAX-ACCESS read-only
            STATUS current
            DESCRIPTION
                "Either set (event raises) or reset (event disappears)"
            ::= { txA1ExciterBLogbookEntry 4 }

        
        txA1ExcBLogbookMessage OBJECT-TYPE
            SYNTAX LogbookEntryMessagesExcTv
            MAX-ACCESS read-only
            STATUS current
            DESCRIPTION
                "See RS-XX8000-COMMON-MIB - TextualConvention for details."
            ::= { txA1ExciterBLogbookEntry 5 }

        
        txA1ExcBLogbookDateTime OBJECT-TYPE
            SYNTAX DateAndTime
            MAX-ACCESS read-only
            STATUS current
            DESCRIPTION
                "The time of the logbook entry."
            ::= { txA1ExciterBLogbookEntry 6 }

        
        txA1OutputstageBNumberOfEntries OBJECT-TYPE
            SYNTAX LogbookMaxEntryNumber
            MAX-ACCESS read-only
            STATUS current
            DESCRIPTION
                "The number of entries in the logbook of output stage B."
            ::= { logbookTxA1 16 }

        
        txA1OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 17 }

        
        txA1OutputstageBLogbookTable OBJECT-TYPE
            SYNTAX SEQUENCE OF TxA1OutputstageBLogbookEntry
            MAX-ACCESS not-accessible
            STATUS current
            DESCRIPTION
                "Output stage B logbook table."
            ::= { logbookTxA1 18 }

        
        txA1OutputstageBLogbookEntry OBJECT-TYPE
            SYNTAX TxA1OutputstageBLogbookEntry
            MAX-ACCESS not-accessible
            STATUS current
            DESCRIPTION
                "This is a entry in the logbook."
            INDEX { txA1OstBLogbookEntryIdx }
            ::= { txA1OutputstageBLogbookTable 1 }

        
        TxA1OutputstageBLogbookEntry ::=
            SEQUENCE { 
                txA1OstBLogbookEntryIdx
                    LogbookMaxEntryNumber,
                txA1OstBLogbookEntryNbr
                    LogbookMaxEntryNumber,
                txA1OstBLogbookType
                    EventClass,
                txA1OstBLogbookSlope
                    LogbookEntrySlope,
                txA1OstBLogbookMessage
                    LogbookEntryMessagesOST,
                txA1OstBLogbookDateTime
                    DateAndTime
             }

        txA1OstBLogbookEntryIdx OBJECT-TYPE
            SYNTAX LogbookMaxEntryNumber
            MAX-ACCESS not-accessible
            STATUS current
            DESCRIPTION
                "This is an increasing number from 1 to maximum.
                It is used as an index column for SNMP."
            ::= { txA1OutputstageBLogbookEntry 1 }

        
        txA1OstBLogbookEntryNbr OBJECT-TYPE
            SYNTAX LogbookMaxEntryNumber
            MAX-ACCESS read-only
            STATUS current
            DESCRIPTION
                "This is the number of the logbook entry.
                It is an decreasing number from maximum down to 1."
            ::= { txA1OutputstageBLogbookEntry 2 }

        
        txA1OstBLogbookType OBJECT-TYPE
            SYNTAX EventClass
            MAX-ACCESS read-only
            STATUS current
            DESCRIPTION
                "Can either be Fault, Warning or State."
            ::= { txA1OutputstageBLogbookEntry 3 }

        
        txA1OstBLogbookSlope OBJECT-TYPE
            SYNTAX LogbookEntrySlope
            MAX-ACCESS read-only
            STATUS current
            DESCRIPTION
                "Either set (event raises) or reset (event disappears)"
            ::= { txA1OutputstageBLogbookEntry 4 }

        
        txA1OstBLogbookMessage OBJECT-TYPE
            SYNTAX LogbookEntryMessagesOST
            MAX-ACCESS read-only
            STATUS current
            DESCRIPTION
                "See RS-XX8000-COMMON-MIB - TextualConvention for details."
            ::= { txA1OutputstageBLogbookEntry 5 }

        
        txA1OstBLogbookDateTime OBJECT-TYPE
            SYNTAX DateAndTime
            MAX-ACCESS read-only
            STATUS current
            DESCRIPTION
                "The time of the logbook entry."
            ::= { txA1OutputstageBLogbookEntry 6 }

        
        outputstageATxA1 OBJECT IDENTIFIER ::= { txA1 2 }

        
        txA1OstARackTable OBJECT-TYPE
            SYNTAX SEQUENCE OF TxA1OstARackEntry
            MAX-ACCESS not-accessible
            STATUS current
            DESCRIPTION
                "The table of racks."
            ::= { outputstageATxA1 1 }

        
        txA1OstARackEntry OBJECT-TYPE
            SYNTAX TxA1OstARackEntry
            MAX-ACCESS not-accessible
            STATUS current
            DESCRIPTION
                "A row (an entry) for one rack."
            INDEX { txA1OstARackIdx }
            ::= { txA1OstARackTable 1 }

        
        TxA1OstARackEntry ::=
            SEQUENCE { 
                txA1OstARackIdx
                    IndexRack,
                txA1OstARackInletTemperature
                    FloatingPoint,
                txA1OstARackOutletTemperature
                    FloatingPoint,
                txA1OstARackAuxPowerSupply
                    FloatingPoint
             }

        txA1OstARackIdx OBJECT-TYPE
            SYNTAX IndexRack
            MAX-ACCESS not-accessible
            STATUS current
            DESCRIPTION
                "The rack number (1..10)."
            ::= { txA1OstARackEntry 1 }

        
        txA1OstARackInletTemperature OBJECT-TYPE
            SYNTAX FloatingPoint
            UNITS "Degree Celsius"
            MAX-ACCESS read-only
            STATUS current
            DESCRIPTION
                "The inlet temperature."
            ::= { txA1OstARackEntry 2 }

        
        txA1OstARackOutletTemperature OBJECT-TYPE
            SYNTAX FloatingPoint
            UNITS "Degree Celsius"
            MAX-ACCESS read-only
            STATUS current
            DESCRIPTION
                "The outlet temperature."
            ::= { txA1OstARackEntry 3 }

        
        txA1OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA1OstARackEntry 4 }

        
        exciterTxA1 OBJECT IDENTIFIER ::= { txA1 3 }

        
        txA1ExcInputTable OBJECT-TYPE
            SYNTAX SEQUENCE OF TxA1ExcInputEntry
            MAX-ACCESS not-accessible
            STATUS current
            DESCRIPTION
                "A table for more detailed information about the exciter.
                These values are all read-only. For settings, refer to commandsTxTable."
            ::= { exciterTxA1 1 }

        
        txA1ExcInputEntry OBJECT-TYPE
            SYNTAX TxA1ExcInputEntry
            MAX-ACCESS not-accessible
            STATUS current
            DESCRIPTION
                "An entry for a designated input channel."
            INDEX { txA1ExcInputExcIdx, txA1ExcInputChannelIdx }
            ::= { txA1ExcInputTable 1 }

        
        TxA1ExcInputEntry ::=
            SEQUENCE { 
                txA1ExcInputExcIdx
                    INTEGER,
                txA1ExcInputChannelIdx
                    Integer32,
                txA1ExcInputChannelName
                    INTEGER,
                txA1ExcInputConnected
                    TruthValue,
                txA1ExcInputSeamless
                    TruthValue,
                txA1ExcInputPreselected
                    TruthValue,
                txA1ExcInputActive
                    TruthValue,
                txA1ExcInputMipFail
                    TruthValue,
                txA1ExcInputBandwidth
                    INTEGER,
                txA1ExcInputFFTLength
                    INTEGER,
                txA1ExcInputGuardInterval
                    INTEGER,
                txA1ExcInputConstellation
                    INTEGER,
                txA1ExcInputAlpha
                    INTEGER,
                txA1ExcInputCellID
                    Integer32,
                txA1ExcInputInterleaver
                    INTEGER,
                txA1ExcInputCodeRate
                    INTEGER,
                txA1ExcInputPacketLength
                    Integer32,
                txA1ExcInputMeasuredDatarate
                    Integer32,
                txA1ExcInputRequiredDatarate
                    Integer32,
                txA1ExcInputMaximumDelay
                    Integer32
             }

        txA1ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA1ExcInputEntry 1 }

        
        txA1ExcInputChannelIdx OBJECT-TYPE
            SYNTAX Integer32 (1..6)
            MAX-ACCESS not-accessible
            STATUS current
            DESCRIPTION
                "The index for the different input channels."
            ::= { txA1ExcInputEntry 2 }

        
        txA1ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA1ExcInputEntry 3 }

        
        txA1ExcInputConnected OBJECT-TYPE
            SYNTAX TruthValue
            MAX-ACCESS read-only
            STATUS current
            DESCRIPTION
                "The input channel is connected."
            ::= { txA1ExcInputEntry 4 }

        
        txA1ExcInputSeamless OBJECT-TYPE
            SYNTAX TruthValue
            MAX-ACCESS read-only
            STATUS current
            DESCRIPTION
                "The input channel is in seamless mode."
            ::= { txA1ExcInputEntry 5 }

        
        txA1ExcInputPreselected OBJECT-TYPE
            SYNTAX TruthValue
            MAX-ACCESS read-only
            STATUS current
            DESCRIPTION
                "The input channel is the preselected."
            ::= { txA1ExcInputEntry 6 }

        
        txA1ExcInputActive OBJECT-TYPE
            SYNTAX TruthValue
            MAX-ACCESS read-only
            STATUS current
            DESCRIPTION
                "The input channel is active."
            ::= { txA1ExcInputEntry 7 }

        
        txA1ExcInputMipFail OBJECT-TYPE
            SYNTAX TruthValue
            MAX-ACCESS read-only
            STATUS current
            DESCRIPTION
                "Input channel MIP fail."
            ::= { txA1ExcInputEntry 8 }

        
        txA1ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA1ExcInputEntry 9 }

        
        txA1ExcInputFFTLength OBJECT-TYPE
            SYNTAX INTEGER
                {
                k2(1),
                k8(2),
                k4(3)
                }
            MAX-ACCESS read-only
            STATUS current
            DESCRIPTION
                "The used FFT length (depends on the DVB network)."
            ::= { txA1ExcInputEntry 10 }

        
        txA1ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA1ExcInputEntry 11 }

        
        txA1ExcInputConstellation OBJECT-TYPE
            SYNTAX INTEGER
                {
                qpsk(1),
                qam16(2),
                qam64(3)
                }
            MAX-ACCESS read-only
            STATUS current
            DESCRIPTION
                "This parameter sets the modulation mode."
            ::= { txA1ExcInputEntry 12 }

        
        txA1ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA1ExcInputEntry 13 }

        
        txA1ExcInputCellID OBJECT-TYPE
            SYNTAX Integer32 (0..65535)
            MAX-ACCESS read-only
            STATUS current
            DESCRIPTION
                "Via Cell ID the receiver knows the current network."
            ::= { txA1ExcInputEntry 14 }

        
        txA1ExcInputInterleaver OBJECT-TYPE
            SYNTAX INTEGER
                {
                indepth(1),
                nat(2)
                }
            MAX-ACCESS read-only
            STATUS current
            DESCRIPTION
                "Enables the bit interleaver for hierarchical coding"
            ::= { txA1ExcInputEntry 15 }

        
        txA1ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA1ExcInputEntry 16 }

        
        txA1ExcInputPacketLength OBJECT-TYPE
            SYNTAX Integer32 (188..208)
            MAX-ACCESS read-only
            STATUS current
            DESCRIPTION
                "The Packet length for the channel."
            ::= { txA1ExcInputEntry 17 }

        
        txA1ExcInputMeasuredDatarate OBJECT-TYPE
            SYNTAX Integer32
            MAX-ACCESS read-only
            STATUS current
            DESCRIPTION
                "The measured datarate of the input."
            ::= { txA1ExcInputEntry 18 }

        
        txA1ExcInputRequiredDatarate OBJECT-TYPE
            SYNTAX Integer32
            MAX-ACCESS read-only
            STATUS current
            DESCRIPTION
                "The required datarate of the input."
            ::= { txA1ExcInputEntry 19 }

        
        txA1ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA1ExcInputEntry 20 }

        
        outputstageBTxA1 OBJECT IDENTIFIER ::= { txA1 4 }

        
        txA1OstBRackTable OBJECT-TYPE
            SYNTAX SEQUENCE OF TxA1OstBRackEntry
            MAX-ACCESS not-accessible
            STATUS current
            DESCRIPTION
                "The table of racks for output stage B."
            ::= { outputstageBTxA1 1 }

        
        txA1OstBRackEntry OBJECT-TYPE
            SYNTAX TxA1OstBRackEntry
            MAX-ACCESS not-accessible
            STATUS current
            DESCRIPTION
                "A row (an entry) for one rack."
            INDEX { txA1OstBRackIdx }
            ::= { txA1OstBRackTable 1 }

        
        TxA1OstBRackEntry ::=
            SEQUENCE { 
                txA1OstBRackIdx
                    IndexRack,
                txA1OstBRackInletTemperature
                    FloatingPoint,
                txA1OstBRackOutletTemperature
                    FloatingPoint,
                txA1OstBRackAuxPowerSupply
                    FloatingPoint
             }

        txA1OstBRackIdx OBJECT-TYPE
            SYNTAX IndexRack
            MAX-ACCESS not-accessible
            STATUS current
            DESCRIPTION
                "The rack number (1..10)."
            ::= { txA1OstBRackEntry 1 }

        
        txA1OstBRackInletTemperature OBJECT-TYPE
            SYNTAX FloatingPoint
            UNITS "Degree Celsius"
            MAX-ACCESS read-only
            STATUS current
            DESCRIPTION
                "The inlet temperature."
            ::= { txA1OstBRackEntry 2 }

        
        txA1OstBRackOutletTemperature OBJECT-TYPE
            SYNTAX FloatingPoint
            UNITS "Degree Celsius"
            MAX-ACCESS read-only
            STATUS current
            DESCRIPTION
                "The outlet temperature."
            ::= { txA1OstBRackEntry 3 }

        
        txA1OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA1OstBRackEntry 4 }

        
        txA2 OBJECT IDENTIFIER ::= { transmitter 6 }

        
        logbookTxA2 OBJECT IDENTIFIER ::= { txA2 1 }

        
        txA2NetCCUNumberOfEntries OBJECT-TYPE
            SYNTAX LogbookMaxEntryNumber
            MAX-ACCESS read-only
            STATUS current
            DESCRIPTION
                "The number of entries in logbook."
            ::= { logbookTxA2 1 }

        
        txA2NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 2 }

        
        txA2NetCCULogbookTable OBJECT-TYPE
            SYNTAX SEQUENCE OF TxA2NetCCULogbookEntry
            MAX-ACCESS not-accessible
            STATUS current
            DESCRIPTION
                "NetCCU logbook table."
            ::= { logbookTxA2 3 }

        
        txA2NetCCULogbookEntry OBJECT-TYPE
            SYNTAX TxA2NetCCULogbookEntry
            MAX-ACCESS not-accessible
            STATUS current
            DESCRIPTION
                "This is a entry in the logbook."
            INDEX { txA2NetCCULogbookEntryIdx }
            ::= { txA2NetCCULogbookTable 1 }

        
        TxA2NetCCULogbookEntry ::=
            SEQUENCE { 
                txA2NetCCULogbookEntryIdx
                    LogbookMaxEntryNumber,
                txA2NetCCULogbookEntryNbr
                    LogbookMaxEntryNumber,
                txA2NetCCULogbookType
                    EventClass,
                txA2NetCCULogbookSlope
                    LogbookEntrySlope,
                txA2NetCCULogbookMessage
                    LogbookEntryMessagesNetCCU,
                txA2NetCCULogbookDateTime
                    DateAndTime
             }

        txA2NetCCULogbookEntryIdx OBJECT-TYPE
            SYNTAX LogbookMaxEntryNumber
            MAX-ACCESS not-accessible
            STATUS current
            DESCRIPTION
                "This is an increasing number from 1 to maximum. It is used as an index column for SNMP."
            ::= { txA2NetCCULogbookEntry 1 }

        
        txA2NetCCULogbookEntryNbr OBJECT-TYPE
            SYNTAX LogbookMaxEntryNumber
            MAX-ACCESS read-only
            STATUS current
            DESCRIPTION
                "This is the number of the logbook entry. It is an decreasing number from maximum down to 1."
            ::= { txA2NetCCULogbookEntry 2 }

        
        txA2NetCCULogbookType OBJECT-TYPE
            SYNTAX EventClass
            MAX-ACCESS read-only
            STATUS current
            DESCRIPTION
                "Can either be Fault, Warning or State."
            ::= { txA2NetCCULogbookEntry 3 }

        
        txA2NetCCULogbookSlope OBJECT-TYPE
            SYNTAX LogbookEntrySlope
            MAX-ACCESS read-only
            STATUS current
            DESCRIPTION
                "Either set (event raises) or reset (event disappears)"
            ::= { txA2NetCCULogbookEntry 4 }

        
        txA2NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA2NetCCULogbookEntry 5 }

        
        txA2NetCCULogbookDateTime OBJECT-TYPE
            SYNTAX DateAndTime
            MAX-ACCESS read-only
            STATUS current
            DESCRIPTION
                "The time of the logbook entry."
            ::= { txA2NetCCULogbookEntry 6 }

        
        txA2ExciterANumberOfEntries OBJECT-TYPE
            SYNTAX LogbookMaxEntryNumber
            MAX-ACCESS read-only
            STATUS current
            DESCRIPTION
                "The number of entries in logbook."
            ::= { logbookTxA2 4 }

        
        txA2ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 5 }

        
        txA2ExciterALogbookTable OBJECT-TYPE
            SYNTAX SEQUENCE OF TxA2ExciterALogbookEntry
            MAX-ACCESS not-accessible
            STATUS current
            DESCRIPTION
                "ExciterA logbook table."
            ::= { logbookTxA2 6 }

        
        txA2ExciterALogbookEntry OBJECT-TYPE
            SYNTAX TxA2ExciterALogbookEntry
            MAX-ACCESS not-accessible
            STATUS current
            DESCRIPTION
                "This is a entry in the logbook."
            INDEX { txA2ExcALogbookEntryIdx }
            ::= { txA2ExciterALogbookTable 1 }

        
        TxA2ExciterALogbookEntry ::=
            SEQUENCE { 
                txA2ExcALogbookEntryIdx
                    LogbookMaxEntryNumber,
                txA2ExcALogbookEntryNbr
                    LogbookMaxEntryNumber,
                txA2ExcALogbookType
                    EventClass,
                txA2ExcALogbookSlope
                    LogbookEntrySlope,
                txA2ExcALogbookMessage
                    LogbookEntryMessagesExcTv,
                txA2ExcALogbookDateTime
                    DateAndTime
             }

        txA2ExcALogbookEntryIdx OBJECT-TYPE
            SYNTAX LogbookMaxEntryNumber
            MAX-ACCESS not-accessible
            STATUS current
            DESCRIPTION
                "This is an increasing number from 1 to 128. It is used as an index column for SNMP."
            ::= { txA2ExciterALogbookEntry 1 }

        
        txA2ExcALogbookEntryNbr OBJECT-TYPE
            SYNTAX LogbookMaxEntryNumber
            MAX-ACCESS read-only
            STATUS current
            DESCRIPTION
                "This is the number of the logbook entry. It is an decreasing number from max 128 down to 1."
            ::= { txA2ExciterALogbookEntry 2 }

        
        txA2ExcALogbookType OBJECT-TYPE
            SYNTAX EventClass
            MAX-ACCESS read-only
            STATUS current
            DESCRIPTION
                "Can either be Fault, Warning or State."
            ::= { txA2ExciterALogbookEntry 3 }

        
        txA2ExcALogbookSlope OBJECT-TYPE
            SYNTAX LogbookEntrySlope
            MAX-ACCESS read-only
            STATUS current
            DESCRIPTION
                "Either set (event raises) or reset (event disappears)"
            ::= { txA2ExciterALogbookEntry 4 }

        
        txA2ExcALogbookMessage OBJECT-TYPE
            SYNTAX LogbookEntryMessagesExcTv
            MAX-ACCESS read-only
            STATUS current
            DESCRIPTION
                "See RS-XX8000-COMMON-MIB - TextualConvention for details."
            ::= { txA2ExciterALogbookEntry 5 }

        
        txA2ExcALogbookDateTime OBJECT-TYPE
            SYNTAX DateAndTime
            MAX-ACCESS read-only
            STATUS current
            DESCRIPTION
                "The time of the logbook entry."
            ::= { txA2ExciterALogbookEntry 6 }

        
        txA2OutputstageANumberOfEntries OBJECT-TYPE
            SYNTAX LogbookMaxEntryNumber
            MAX-ACCESS read-only
            STATUS current
            DESCRIPTION
                "The number of entries in logbook."
            ::= { logbookTxA2 7 }

        
        txA2OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 8 }

        
        txA2OutputstageALogbookTable OBJECT-TYPE
            SYNTAX SEQUENCE OF TxA2OutputstageALogbookEntry
            MAX-ACCESS not-accessible
            STATUS current
            DESCRIPTION
                "OutputstageA logbook table."
            ::= { logbookTxA2 9 }

        
        txA2OutputstageALogbookEntry OBJECT-TYPE
            SYNTAX TxA2OutputstageALogbookEntry
            MAX-ACCESS not-accessible
            STATUS current
            DESCRIPTION
                "This is a entry in the logbook."
            INDEX { txA2OstALogbookEntryIdx }
            ::= { txA2OutputstageALogbookTable 1 }

        
        TxA2OutputstageALogbookEntry ::=
            SEQUENCE { 
                txA2OstALogbookEntryIdx
                    LogbookMaxEntryNumber,
                txA2OstALogbookEntryNbr
                    LogbookMaxEntryNumber,
                txA2OstALogbookType
                    EventClass,
                txA2OstALogbookSlope
                    LogbookEntrySlope,
                txA2OstALogbookMessage
                    LogbookEntryMessagesOST,
                txA2OstALogbookDateTime
                    DateAndTime
             }

        txA2OstALogbookEntryIdx OBJECT-TYPE
            SYNTAX LogbookMaxEntryNumber
            MAX-ACCESS not-accessible
            STATUS current
            DESCRIPTION
                "This is an increasing number from 1 to maximum. It is used as an index column for SNMP."
            ::= { txA2OutputstageALogbookEntry 1 }

        
        txA2OstALogbookEntryNbr OBJECT-TYPE
            SYNTAX LogbookMaxEntryNumber
            MAX-ACCESS read-only
            STATUS current
            DESCRIPTION
                "This is the number of the logbook entry. It is an decreasing number from maximum down to 1."
            ::= { txA2OutputstageALogbookEntry 2 }

        
        txA2OstALogbookType OBJECT-TYPE
            SYNTAX EventClass
            MAX-ACCESS read-only
            STATUS current
            DESCRIPTION
                "Can either be Fault, Warning or State."
            ::= { txA2OutputstageALogbookEntry 3 }

        
        txA2OstALogbookSlope OBJECT-TYPE
            SYNTAX LogbookEntrySlope
            MAX-ACCESS read-only
            STATUS current
            DESCRIPTION
                "Either set (event raises) or reset (event disappears)"
            ::= { txA2OutputstageALogbookEntry 4 }

        
        txA2OstALogbookMessage OBJECT-TYPE
            SYNTAX LogbookEntryMessagesOST
            MAX-ACCESS read-only
            STATUS current
            DESCRIPTION
                "See RS-XX8000-COMMON-MIB - TextualConvention for details."
            ::= { txA2OutputstageALogbookEntry 5 }

        
        txA2OstALogbookDateTime OBJECT-TYPE
            SYNTAX DateAndTime
            MAX-ACCESS read-only
            STATUS current
            DESCRIPTION
                "The time of the logbook entry."
            ::= { txA2OutputstageALogbookEntry 6 }

        
        txA2ExciterBNumberOfEntries OBJECT-TYPE
            SYNTAX LogbookMaxEntryNumber
            MAX-ACCESS read-only
            STATUS current
            DESCRIPTION
                "The number of entries in logbook."
            ::= { logbookTxA2 13 }

        
        txA2ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 14 }

        
        txA2ExciterBLogbookTable OBJECT-TYPE
            SYNTAX SEQUENCE OF TxA2ExciterBLogbookEntry
            MAX-ACCESS not-accessible
            STATUS current
            DESCRIPTION
                "ExciterB logbook table."
            ::= { logbookTxA2 15 }

        
        txA2ExciterBLogbookEntry OBJECT-TYPE
            SYNTAX TxA2ExciterBLogbookEntry
            MAX-ACCESS not-accessible
            STATUS current
            DESCRIPTION
                "This is a entry in the logbook."
            INDEX { txA2ExcBLogbookEntryIdx }
            ::= { txA2ExciterBLogbookTable 1 }

        
        TxA2ExciterBLogbookEntry ::=
            SEQUENCE { 
                txA2ExcBLogbookEntryIdx
                    LogbookMaxEntryNumber,
                txA2ExcBLogbookEntryNbr
                    LogbookMaxEntryNumber,
                txA2ExcBLogbookType
                    EventClass,
                txA2ExcBLogbookSlope
                    LogbookEntrySlope,
                txA2ExcBLogbookMessage
                    LogbookEntryMessagesExcTv,
                txA2ExcBLogbookDateTime
                    DateAndTime
             }

        txA2ExcBLogbookEntryIdx OBJECT-TYPE
            SYNTAX LogbookMaxEntryNumber
            MAX-ACCESS not-accessible
            STATUS current
            DESCRIPTION
                "This is an increasing number from 1 to maximum. It is used as an index column for SNMP."
            ::= { txA2ExciterBLogbookEntry 1 }

        
        txA2ExcBLogbookEntryNbr OBJECT-TYPE
            SYNTAX LogbookMaxEntryNumber
            MAX-ACCESS read-only
            STATUS current
            DESCRIPTION
                "This is the number of the logbook entry. It is an decreasing number from maximum down to 1."
            ::= { txA2ExciterBLogbookEntry 2 }

        
        txA2ExcBLogbookType OBJECT-TYPE
            SYNTAX EventClass
            MAX-ACCESS read-only
            STATUS current
            DESCRIPTION
                "Can either be Fault, Warning or State."
            ::= { txA2ExciterBLogbookEntry 3 }

        
        txA2ExcBLogbookSlope OBJECT-TYPE
            SYNTAX LogbookEntrySlope
            MAX-ACCESS read-only
            STATUS current
            DESCRIPTION
                "Either set (event raises) or reset (event disappears)"
            ::= { txA2ExciterBLogbookEntry 4 }

        
        txA2ExcBLogbookMessage OBJECT-TYPE
            SYNTAX LogbookEntryMessagesExcTv
            MAX-ACCESS read-only
            STATUS current
            DESCRIPTION
                "See RS-XX8000-COMMON-MIB - TextualConvention for details."
            ::= { txA2ExciterBLogbookEntry 5 }

        
        txA2ExcBLogbookDateTime OBJECT-TYPE
            SYNTAX DateAndTime
            MAX-ACCESS read-only
            STATUS current
            DESCRIPTION
                "The time of the logbook entry."
            ::= { txA2ExciterBLogbookEntry 6 }

        
        txA2OutputstageBNumberOfEntries OBJECT-TYPE
            SYNTAX LogbookMaxEntryNumber
            MAX-ACCESS read-only
            STATUS current
            DESCRIPTION
                "The number of entries in the logbook of output stage B."
            ::= { logbookTxA2 16 }

        
        txA2OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 17 }

        
        txA2OutputstageBLogbookTable OBJECT-TYPE
            SYNTAX SEQUENCE OF TxA2OutputstageBLogbookEntry
            MAX-ACCESS not-accessible
            STATUS current
            DESCRIPTION
                "Output stage B logbook table."
            ::= { logbookTxA2 18 }

        
        txA2OutputstageBLogbookEntry OBJECT-TYPE
            SYNTAX TxA2OutputstageBLogbookEntry
            MAX-ACCESS not-accessible
            STATUS current
            DESCRIPTION
                "This is a entry in the logbook."
            INDEX { txA2OstBLogbookEntryIdx }
            ::= { txA2OutputstageBLogbookTable 1 }

        
        TxA2OutputstageBLogbookEntry ::=
            SEQUENCE { 
                txA2OstBLogbookEntryIdx
                    LogbookMaxEntryNumber,
                txA2OstBLogbookEntryNbr
                    LogbookMaxEntryNumber,
                txA2OstBLogbookType
                    EventClass,
                txA2OstBLogbookSlope
                    LogbookEntrySlope,
                txA2OstBLogbookMessage
                    LogbookEntryMessagesOST,
                txA2OstBLogbookDateTime
                    DateAndTime
             }

        txA2OstBLogbookEntryIdx OBJECT-TYPE
            SYNTAX LogbookMaxEntryNumber
            MAX-ACCESS not-accessible
            STATUS current
            DESCRIPTION
                "This is an increasing number from 1 to maximum. It is used as an index column for SNMP."
            ::= { txA2OutputstageBLogbookEntry 1 }

        
        txA2OstBLogbookEntryNbr OBJECT-TYPE
            SYNTAX LogbookMaxEntryNumber
            MAX-ACCESS read-only
            STATUS current
            DESCRIPTION
                "This is the number of the logbook entry. It is an decreasing number from maximum down to 1."
            ::= { txA2OutputstageBLogbookEntry 2 }

        
        txA2OstBLogbookType OBJECT-TYPE
            SYNTAX EventClass
            MAX-ACCESS read-only
            STATUS current
            DESCRIPTION
                "Can either be Fault, Warning or State."
            ::= { txA2OutputstageBLogbookEntry 3 }

        
        txA2OstBLogbookSlope OBJECT-TYPE
            SYNTAX LogbookEntrySlope
            MAX-ACCESS read-only
            STATUS current
            DESCRIPTION
                "Either set (event raises) or reset (event disappears)"
            ::= { txA2OutputstageBLogbookEntry 4 }

        
        txA2OstBLogbookMessage OBJECT-TYPE
            SYNTAX LogbookEntryMessagesOST
            MAX-ACCESS read-only
            STATUS current
            DESCRIPTION
                "See RS-XX8000-COMMON-MIB - TextualConvention for details."
            ::= { txA2OutputstageBLogbookEntry 5 }

        
        txA2OstBLogbookDateTime OBJECT-TYPE
            SYNTAX DateAndTime
            MAX-ACCESS read-only
            STATUS current
            DESCRIPTION
                "The time of the logbook entry."
            ::= { txA2OutputstageBLogbookEntry 6 }

        
        outputstageATxA2 OBJECT IDENTIFIER ::= { txA2 2 }

        
        txA2OstARackTable OBJECT-TYPE
            SYNTAX SEQUENCE OF TxA2OstARackEntry
            MAX-ACCESS not-accessible
            STATUS current
            DESCRIPTION
                "The table of racks."
            ::= { outputstageATxA2 1 }

        
        txA2OstARackEntry OBJECT-TYPE
            SYNTAX TxA2OstARackEntry
            MAX-ACCESS not-accessible
            STATUS current
            DESCRIPTION
                "A row (an entry) for one rack."
            INDEX { txA2OstARackIdx }
            ::= { txA2OstARackTable 1 }

        
        TxA2OstARackEntry ::=
            SEQUENCE { 
                txA2OstARackIdx
                    IndexRack,
                txA2OstARackInletTemperature
                    FloatingPoint,
                txA2OstARackOutletTemperature
                    FloatingPoint,
                txA2OstARackAuxPowerSupply
                    FloatingPoint
             }

        txA2OstARackIdx OBJECT-TYPE
            SYNTAX IndexRack
            MAX-ACCESS not-accessible
            STATUS current
            DESCRIPTION
                "The rack number (1..10)."
            ::= { txA2OstARackEntry 1 }

        
        txA2OstARackInletTemperature OBJECT-TYPE
            SYNTAX FloatingPoint
            UNITS "Degree Celsius"
            MAX-ACCESS read-only
            STATUS current
            DESCRIPTION
                "The inlet temperature."
            ::= { txA2OstARackEntry 2 }

        
        txA2OstARackOutletTemperature OBJECT-TYPE
            SYNTAX FloatingPoint
            UNITS "Degree Celsius"
            MAX-ACCESS read-only
            STATUS current
            DESCRIPTION
                "The outlet temperature."
            ::= { txA2OstARackEntry 3 }

        
        txA2OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA2OstARackEntry 4 }

        
        exciterTxA2 OBJECT IDENTIFIER ::= { txA2 3 }

        
        txA2ExcInputTable OBJECT-TYPE
            SYNTAX SEQUENCE OF TxA2ExcInputEntry
            MAX-ACCESS not-accessible
            STATUS current
            DESCRIPTION
                "A table for more detailed information about the exciter.
                These values are all read-only. For settings, refer to commandsTxTable."
            ::= { exciterTxA2 1 }

        
        txA2ExcInputEntry OBJECT-TYPE
            SYNTAX TxA2ExcInputEntry
            MAX-ACCESS not-accessible
            STATUS current
            DESCRIPTION
                "An entry for a designated input channel."
            INDEX { txA2ExcInputExcIdx, txA2ExcInputChannelIdx }
            ::= { txA2ExcInputTable 1 }

        
        TxA2ExcInputEntry ::=
            SEQUENCE { 
                txA2ExcInputExcIdx
                    INTEGER,
                txA2ExcInputChannelIdx
                    Integer32,
                txA2ExcInputChannelName
                    INTEGER,
                txA2ExcInputConnected
                    TruthValue,
                txA2ExcInputSeamless
                    TruthValue,
                txA2ExcInputPreselected
                    TruthValue,
                txA2ExcInputActive
                    TruthValue,
                txA2ExcInputMipFail
                    TruthValue,
                txA2ExcInputBandwidth
                    INTEGER,
                txA2ExcInputFFTLength
                    INTEGER,
                txA2ExcInputGuardInterval
                    INTEGER,
                txA2ExcInputConstellation
                    INTEGER,
                txA2ExcInputAlpha
                    INTEGER,
                txA2ExcInputCellID
                    Integer32,
                txA2ExcInputInterleaver
                    INTEGER,
                txA2ExcInputCodeRate
                    INTEGER,
                txA2ExcInputPacketLength
                    Integer32,
                txA2ExcInputMeasuredDatarate
                    Integer32,
                txA2ExcInputRequiredDatarate
                    Integer32,
                txA2ExcInputMaximumDelay
                    Integer32
             }

        txA2ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA2ExcInputEntry 1 }

        
        txA2ExcInputChannelIdx OBJECT-TYPE
            SYNTAX Integer32 (1..6)
            MAX-ACCESS not-accessible
            STATUS current
            DESCRIPTION
                "The index for the different input channels."
            ::= { txA2ExcInputEntry 2 }

        
        txA2ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA2ExcInputEntry 3 }

        
        txA2ExcInputConnected OBJECT-TYPE
            SYNTAX TruthValue
            MAX-ACCESS read-only
            STATUS current
            DESCRIPTION
                "The input channel is connected."
            ::= { txA2ExcInputEntry 4 }

        
        txA2ExcInputSeamless OBJECT-TYPE
            SYNTAX TruthValue
            MAX-ACCESS read-only
            STATUS current
            DESCRIPTION
                "The input channel is in seamless mode."
            ::= { txA2ExcInputEntry 5 }

        
        txA2ExcInputPreselected OBJECT-TYPE
            SYNTAX TruthValue
            MAX-ACCESS read-only
            STATUS current
            DESCRIPTION
                "The input channel is the preselected."
            ::= { txA2ExcInputEntry 6 }

        
        txA2ExcInputActive OBJECT-TYPE
            SYNTAX TruthValue
            MAX-ACCESS read-only
            STATUS current
            DESCRIPTION
                "The input channel is active."
            ::= { txA2ExcInputEntry 7 }

        
        txA2ExcInputMipFail OBJECT-TYPE
            SYNTAX TruthValue
            MAX-ACCESS read-only
            STATUS current
            DESCRIPTION
                "Input channel MIP fail."
            ::= { txA2ExcInputEntry 8 }

        
        txA2ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA2ExcInputEntry 9 }

        
        txA2ExcInputFFTLength OBJECT-TYPE
            SYNTAX INTEGER
                {
                k2(1),
                k8(2),
                k4(3)
                }
            MAX-ACCESS read-only
            STATUS current
            DESCRIPTION
                "The used FFT length (depends on the DVB network)."
            ::= { txA2ExcInputEntry 10 }

        
        txA2ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA2ExcInputEntry 11 }

        
        txA2ExcInputConstellation OBJECT-TYPE
            SYNTAX INTEGER
                {
                qpsk(1),
                qam16(2),
                qam64(3)
                }
            MAX-ACCESS read-only
            STATUS current
            DESCRIPTION
                "This parameter sets the modulation mode."
            ::= { txA2ExcInputEntry 12 }

        
        txA2ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA2ExcInputEntry 13 }

        
        txA2ExcInputCellID OBJECT-TYPE
            SYNTAX Integer32 (0..65535)
            MAX-ACCESS read-only
            STATUS current
            DESCRIPTION
                "Via Cell ID the receiver knows the current network."
            ::= { txA2ExcInputEntry 14 }

        
        txA2ExcInputInterleaver OBJECT-TYPE
            SYNTAX INTEGER
                {
                indepth(1),
                nat(2)
                }
            MAX-ACCESS read-only
            STATUS current
            DESCRIPTION
                "Enables the bit interleaver for hierarchical coding"
            ::= { txA2ExcInputEntry 15 }

        
        txA2ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA2ExcInputEntry 16 }

        
        txA2ExcInputPacketLength OBJECT-TYPE
            SYNTAX Integer32 (188..208)
            MAX-ACCESS read-only
            STATUS current
            DESCRIPTION
                "The Packet length for the channel."
            ::= { txA2ExcInputEntry 17 }

        
        txA2ExcInputMeasuredDatarate OBJECT-TYPE
            SYNTAX Integer32
            MAX-ACCESS read-only
            STATUS current
            DESCRIPTION
                "The measured datarate of the input."
            ::= { txA2ExcInputEntry 18 }

        
        txA2ExcInputRequiredDatarate OBJECT-TYPE
            SYNTAX Integer32
            MAX-ACCESS read-only
            STATUS current
            DESCRIPTION
                "The required datarate of the input."
            ::= { txA2ExcInputEntry 19 }

        
        txA2ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA2ExcInputEntry 20 }

        
        outputstageBTxA2 OBJECT IDENTIFIER ::= { txA2 4 }

        
        txA2OstBRackTable OBJECT-TYPE
            SYNTAX SEQUENCE OF TxA2OstBRackEntry
            MAX-ACCESS not-accessible
            STATUS current
            DESCRIPTION
                "The table of racks for output stage B."
            ::= { outputstageBTxA2 1 }

        
        txA2OstBRackEntry OBJECT-TYPE
            SYNTAX TxA2OstBRackEntry
            MAX-ACCESS not-accessible
            STATUS current
            DESCRIPTION
                "A row (an entry) for one rack."
            INDEX { txA2OstBRackIdx }
            ::= { txA2OstBRackTable 1 }

        
        TxA2OstBRackEntry ::=
            SEQUENCE { 
                txA2OstBRackIdx
                    IndexRack,
                txA2OstBRackInletTemperature
                    FloatingPoint,
                txA2OstBRackOutletTemperature
                    FloatingPoint,
                txA2OstBRackAuxPowerSupply
                    FloatingPoint
             }

        txA2OstBRackIdx OBJECT-TYPE
            SYNTAX IndexRack
            MAX-ACCESS not-accessible
            STATUS current
            DESCRIPTION
                "The rack number (1..10)."
            ::= { txA2OstBRackEntry 1 }

        
        txA2OstBRackInletTemperature OBJECT-TYPE
            SYNTAX FloatingPoint
            UNITS "Degree Celsius"
            MAX-ACCESS read-only
            STATUS current
            DESCRIPTION
                "The inlet temperature."
            ::= { txA2OstBRackEntry 2 }

        
        txA2OstBRackOutletTemperature OBJECT-TYPE
            SYNTAX FloatingPoint
            UNITS "Degree Celsius"
            MAX-ACCESS read-only
            STATUS current
            DESCRIPTION
                "The outlet temperature."
            ::= { txA2OstBRackEntry 3 }

        
        txA2OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA2OstBRackEntry 4 }

        
        txA3 OBJECT IDENTIFIER ::= { transmitter 7 }

        
        logbookTxA3 OBJECT IDENTIFIER ::= { txA3 1 }

        
        txA3NetCCUNumberOfEntries OBJECT-TYPE
            SYNTAX LogbookMaxEntryNumber
            MAX-ACCESS read-only
            STATUS current
            DESCRIPTION
                "The number of entries in logbook."
            ::= { logbookTxA3 1 }

        
        txA3NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 2 }

        
        txA3NetCCULogbookTable OBJECT-TYPE
            SYNTAX SEQUENCE OF TxA3NetCCULogbookEntry
            MAX-ACCESS not-accessible
            STATUS current
            DESCRIPTION
                "NetCCU logbook table."
            ::= { logbookTxA3 3 }

        
        txA3NetCCULogbookEntry OBJECT-TYPE
            SYNTAX TxA3NetCCULogbookEntry
            MAX-ACCESS not-accessible
            STATUS current
            DESCRIPTION
                "This is a entry in the logbook."
            INDEX { txA3NetCCULogbookEntryIdx }
            ::= { txA3NetCCULogbookTable 1 }

        
        TxA3NetCCULogbookEntry ::=
            SEQUENCE { 
                txA3NetCCULogbookEntryIdx
                    LogbookMaxEntryNumber,
                txA3NetCCULogbookEntryNbr
                    LogbookMaxEntryNumber,
                txA3NetCCULogbookType
                    EventClass,
                txA3NetCCULogbookSlope
                    LogbookEntrySlope,
                txA3NetCCULogbookMessage
                    LogbookEntryMessagesNetCCU,
                txA3NetCCULogbookDateTime
                    DateAndTime
             }

        txA3NetCCULogbookEntryIdx OBJECT-TYPE
            SYNTAX LogbookMaxEntryNumber
            MAX-ACCESS not-accessible
            STATUS current
            DESCRIPTION
                "This is an increasing number from 1 to maximum. It is used as an index column for SNMP."
            ::= { txA3NetCCULogbookEntry 1 }

        
        txA3NetCCULogbookEntryNbr OBJECT-TYPE
            SYNTAX LogbookMaxEntryNumber
            MAX-ACCESS read-only
            STATUS current
            DESCRIPTION
                "This is the number of the logbook entry. It is an decreasing number from maximum down to 1."
            ::= { txA3NetCCULogbookEntry 2 }

        
        txA3NetCCULogbookType OBJECT-TYPE
            SYNTAX EventClass
            MAX-ACCESS read-only
            STATUS current
            DESCRIPTION
                "Can either be Fault, Warning or State."
            ::= { txA3NetCCULogbookEntry 3 }

        
        txA3NetCCULogbookSlope OBJECT-TYPE
            SYNTAX LogbookEntrySlope
            MAX-ACCESS read-only
            STATUS current
            DESCRIPTION
                "Either set (event raises) or reset (event disappears)"
            ::= { txA3NetCCULogbookEntry 4 }

        
        txA3NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA3NetCCULogbookEntry 5 }

        
        txA3NetCCULogbookDateTime OBJECT-TYPE
            SYNTAX DateAndTime
            MAX-ACCESS read-only
            STATUS current
            DESCRIPTION
                "The time of the logbook entry."
            ::= { txA3NetCCULogbookEntry 6 }

        
        txA3ExciterANumberOfEntries OBJECT-TYPE
            SYNTAX LogbookMaxEntryNumber
            MAX-ACCESS read-only
            STATUS current
            DESCRIPTION
                "The number of entries in logbook."
            ::= { logbookTxA3 4 }

        
        txA3ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 5 }

        
        txA3ExciterALogbookTable OBJECT-TYPE
            SYNTAX SEQUENCE OF TxA3ExciterALogbookEntry
            MAX-ACCESS not-accessible
            STATUS current
            DESCRIPTION
                "ExciterA logbook table."
            ::= { logbookTxA3 6 }

        
        txA3ExciterALogbookEntry OBJECT-TYPE
            SYNTAX TxA3ExciterALogbookEntry
            MAX-ACCESS not-accessible
            STATUS current
            DESCRIPTION
                "This is a entry in the logbook."
            INDEX { txA3ExcALogbookEntryIdx }
            ::= { txA3ExciterALogbookTable 1 }

        
        TxA3ExciterALogbookEntry ::=
            SEQUENCE { 
                txA3ExcALogbookEntryIdx
                    LogbookMaxEntryNumber,
                txA3ExcALogbookEntryNbr
                    LogbookMaxEntryNumber,
                txA3ExcALogbookType
                    EventClass,
                txA3ExcALogbookSlope
                    LogbookEntrySlope,
                txA3ExcALogbookMessage
                    LogbookEntryMessagesExcTv,
                txA3ExcALogbookDateTime
                    DateAndTime
             }

        txA3ExcALogbookEntryIdx OBJECT-TYPE
            SYNTAX LogbookMaxEntryNumber
            MAX-ACCESS not-accessible
            STATUS current
            DESCRIPTION
                "This is an increasing number from 1 to 128. It is used as an index column for SNMP."
            ::= { txA3ExciterALogbookEntry 1 }

        
        txA3ExcALogbookEntryNbr OBJECT-TYPE
            SYNTAX LogbookMaxEntryNumber
            MAX-ACCESS read-only
            STATUS current
            DESCRIPTION
                "This is the number of the logbook entry. It is an decreasing number from max 128 down to 1."
            ::= { txA3ExciterALogbookEntry 2 }

        
        txA3ExcALogbookType OBJECT-TYPE
            SYNTAX EventClass
            MAX-ACCESS read-only
            STATUS current
            DESCRIPTION
                "Can either be Fault, Warning or State."
            ::= { txA3ExciterALogbookEntry 3 }

        
        txA3ExcALogbookSlope OBJECT-TYPE
            SYNTAX LogbookEntrySlope
            MAX-ACCESS read-only
            STATUS current
            DESCRIPTION
                "Either set (event raises) or reset (event disappears)"
            ::= { txA3ExciterALogbookEntry 4 }

        
        txA3ExcALogbookMessage OBJECT-TYPE
            SYNTAX LogbookEntryMessagesExcTv
            MAX-ACCESS read-only
            STATUS current
            DESCRIPTION
                "See RS-XX8000-COMMON-MIB - TextualConvention for details."
            ::= { txA3ExciterALogbookEntry 5 }

        
        txA3ExcALogbookDateTime OBJECT-TYPE
            SYNTAX DateAndTime
            MAX-ACCESS read-only
            STATUS current
            DESCRIPTION
                "The time of the logbook entry."
            ::= { txA3ExciterALogbookEntry 6 }

        
        txA3OutputstageANumberOfEntries OBJECT-TYPE
            SYNTAX LogbookMaxEntryNumber
            MAX-ACCESS read-only
            STATUS current
            DESCRIPTION
                "The number of entries in logbook."
            ::= { logbookTxA3 7 }

        
        txA3OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 8 }

        
        txA3OutputstageALogbookTable OBJECT-TYPE
            SYNTAX SEQUENCE OF TxA3OutputstageALogbookEntry
            MAX-ACCESS not-accessible
            STATUS current
            DESCRIPTION
                "OutputstageA logbook table."
            ::= { logbookTxA3 9 }

        
        txA3OutputstageALogbookEntry OBJECT-TYPE
            SYNTAX TxA3OutputstageALogbookEntry
            MAX-ACCESS not-accessible
            STATUS current
            DESCRIPTION
                "This is a entry in the logbook."
            INDEX { txA3OstALogbookEntryIdx }
            ::= { txA3OutputstageALogbookTable 1 }

        
        TxA3OutputstageALogbookEntry ::=
            SEQUENCE { 
                txA3OstALogbookEntryIdx
                    LogbookMaxEntryNumber,
                txA3OstALogbookEntryNbr
                    LogbookMaxEntryNumber,
                txA3OstALogbookType
                    EventClass,
                txA3OstALogbookSlope
                    LogbookEntrySlope,
                txA3OstALogbookMessage
                    LogbookEntryMessagesOST,
                txA3OstALogbookDateTime
                    DateAndTime
             }

        txA3OstALogbookEntryIdx OBJECT-TYPE
            SYNTAX LogbookMaxEntryNumber
            MAX-ACCESS not-accessible
            STATUS current
            DESCRIPTION
                "This is an increasing number from 1 to maximum. It is used as an index column for SNMP."
            ::= { txA3OutputstageALogbookEntry 1 }

        
        txA3OstALogbookEntryNbr OBJECT-TYPE
            SYNTAX LogbookMaxEntryNumber
            MAX-ACCESS read-only
            STATUS current
            DESCRIPTION
                "This is the number of the logbook entry. It is an decreasing number from maximum down to 1."
            ::= { txA3OutputstageALogbookEntry 2 }

        
        txA3OstALogbookType OBJECT-TYPE
            SYNTAX EventClass
            MAX-ACCESS read-only
            STATUS current
            DESCRIPTION
                "Can either be Fault, Warning or State."
            ::= { txA3OutputstageALogbookEntry 3 }

        
        txA3OstALogbookSlope OBJECT-TYPE
            SYNTAX LogbookEntrySlope
            MAX-ACCESS read-only
            STATUS current
            DESCRIPTION
                "Either set (event raises) or reset (event disappears)"
            ::= { txA3OutputstageALogbookEntry 4 }

        
        txA3OstALogbookMessage OBJECT-TYPE
            SYNTAX LogbookEntryMessagesOST
            MAX-ACCESS read-only
            STATUS current
            DESCRIPTION
                "See RS-XX8000-COMMON-MIB - TextualConvention for details."
            ::= { txA3OutputstageALogbookEntry 5 }

        
        txA3OstALogbookDateTime OBJECT-TYPE
            SYNTAX DateAndTime
            MAX-ACCESS read-only
            STATUS current
            DESCRIPTION
                "The time of the logbook entry."
            ::= { txA3OutputstageALogbookEntry 6 }

        
        txA3ExciterBNumberOfEntries OBJECT-TYPE
            SYNTAX LogbookMaxEntryNumber
            MAX-ACCESS read-only
            STATUS current
            DESCRIPTION
                "The number of entries in logbook."
            ::= { logbookTxA3 13 }

        
        txA3ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 14 }

        
        txA3ExciterBLogbookTable OBJECT-TYPE
            SYNTAX SEQUENCE OF TxA3ExciterBLogbookEntry
            MAX-ACCESS not-accessible
            STATUS current
            DESCRIPTION
                "ExciterB logbook table."
            ::= { logbookTxA3 15 }

        
        txA3ExciterBLogbookEntry OBJECT-TYPE
            SYNTAX TxA3ExciterBLogbookEntry
            MAX-ACCESS not-accessible
            STATUS current
            DESCRIPTION
                "This is a entry in the logbook."
            INDEX { txA3ExcBLogbookEntryIdx }
            ::= { txA3ExciterBLogbookTable 1 }

        
        TxA3ExciterBLogbookEntry ::=
            SEQUENCE { 
                txA3ExcBLogbookEntryIdx
                    LogbookMaxEntryNumber,
                txA3ExcBLogbookEntryNbr
                    LogbookMaxEntryNumber,
                txA3ExcBLogbookType
                    EventClass,
                txA3ExcBLogbookSlope
                    LogbookEntrySlope,
                txA3ExcBLogbookMessage
                    LogbookEntryMessagesExcTv,
                txA3ExcBLogbookDateTime
                    DateAndTime
             }

        txA3ExcBLogbookEntryIdx OBJECT-TYPE
            SYNTAX LogbookMaxEntryNumber
            MAX-ACCESS not-accessible
            STATUS current
            DESCRIPTION
                "This is an increasing number from 1 to maximum. It is used as an index column for SNMP."
            ::= { txA3ExciterBLogbookEntry 1 }

        
        txA3ExcBLogbookEntryNbr OBJECT-TYPE
            SYNTAX LogbookMaxEntryNumber
            MAX-ACCESS read-only
            STATUS current
            DESCRIPTION
                "This is the number of the logbook entry. It is an decreasing number from maximum down to 1."
            ::= { txA3ExciterBLogbookEntry 2 }

        
        txA3ExcBLogbookType OBJECT-TYPE
            SYNTAX EventClass
            MAX-ACCESS read-only
            STATUS current
            DESCRIPTION
                "Can either be Fault, Warning or State."
            ::= { txA3ExciterBLogbookEntry 3 }

        
        txA3ExcBLogbookSlope OBJECT-TYPE
            SYNTAX LogbookEntrySlope
            MAX-ACCESS read-only
            STATUS current
            DESCRIPTION
                "Either set (event raises) or reset (event disappears)"
            ::= { txA3ExciterBLogbookEntry 4 }

        
        txA3ExcBLogbookMessage OBJECT-TYPE
            SYNTAX LogbookEntryMessagesExcTv
            MAX-ACCESS read-only
            STATUS current
            DESCRIPTION
                "See RS-XX8000-COMMON-MIB - TextualConvention for details."
            ::= { txA3ExciterBLogbookEntry 5 }

        
        txA3ExcBLogbookDateTime OBJECT-TYPE
            SYNTAX DateAndTime
            MAX-ACCESS read-only
            STATUS current
            DESCRIPTION
                "The time of the logbook entry."
            ::= { txA3ExciterBLogbookEntry 6 }

        
        txA3OutputstageBNumberOfEntries OBJECT-TYPE
            SYNTAX LogbookMaxEntryNumber
            MAX-ACCESS read-only
            STATUS current
            DESCRIPTION
                "The number of entries in logbook of output stage B."
            ::= { logbookTxA3 16 }

        
        txA3OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 17 }

        
        txA3OutputstageBLogbookTable OBJECT-TYPE
            SYNTAX SEQUENCE OF TxA3OutputstageBLogbookEntry
            MAX-ACCESS not-accessible
            STATUS current
            DESCRIPTION
                "Output stage B logbook table."
            ::= { logbookTxA3 18 }

        
        txA3OutputstageBLogbookEntry OBJECT-TYPE
            SYNTAX TxA3OutputstageBLogbookEntry
            MAX-ACCESS not-accessible
            STATUS current
            DESCRIPTION
                "This is a entry in the logbook."
            INDEX { txA3OstBLogbookEntryIdx }
            ::= { txA3OutputstageBLogbookTable 1 }

        
        TxA3OutputstageBLogbookEntry ::=
            SEQUENCE { 
                txA3OstBLogbookEntryIdx
                    LogbookMaxEntryNumber,
                txA3OstBLogbookEntryNbr
                    LogbookMaxEntryNumber,
                txA3OstBLogbookType
                    EventClass,
                txA3OstBLogbookSlope
                    LogbookEntrySlope,
                txA3OstBLogbookMessage
                    LogbookEntryMessagesOST,
                txA3OstBLogbookDateTime
                    DateAndTime
             }

        txA3OstBLogbookEntryIdx OBJECT-TYPE
            SYNTAX LogbookMaxEntryNumber
            MAX-ACCESS not-accessible
            STATUS current
            DESCRIPTION
                "This is an increasing number from 1 to maximum. It is used as an index column for SNMP."
            ::= { txA3OutputstageBLogbookEntry 1 }

        
        txA3OstBLogbookEntryNbr OBJECT-TYPE
            SYNTAX LogbookMaxEntryNumber
            MAX-ACCESS read-only
            STATUS current
            DESCRIPTION
                "This is the number of the logbook entry. It is an decreasing number from maximum down to 1."
            ::= { txA3OutputstageBLogbookEntry 2 }

        
        txA3OstBLogbookType OBJECT-TYPE
            SYNTAX EventClass
            MAX-ACCESS read-only
            STATUS current
            DESCRIPTION
                "Can either be Fault, Warning or State."
            ::= { txA3OutputstageBLogbookEntry 3 }

        
        txA3OstBLogbookSlope OBJECT-TYPE
            SYNTAX LogbookEntrySlope
            MAX-ACCESS read-only
            STATUS current
            DESCRIPTION
                "Either set (event raises) or reset (event disappears)"
            ::= { txA3OutputstageBLogbookEntry 4 }

        
        txA3OstBLogbookMessage OBJECT-TYPE
            SYNTAX LogbookEntryMessagesOST
            MAX-ACCESS read-only
            STATUS current
            DESCRIPTION
                "See RS-XX8000-COMMON-MIB - TextualConvention for details."
            ::= { txA3OutputstageBLogbookEntry 5 }

        
        txA3OstBLogbookDateTime OBJECT-TYPE
            SYNTAX DateAndTime
            MAX-ACCESS read-only
            STATUS current
            DESCRIPTION
                "The time of the logbook entry."
            ::= { txA3OutputstageBLogbookEntry 6 }

        
        outputstageATxA3 OBJECT IDENTIFIER ::= { txA3 2 }

        
        txA3OstARackTable OBJECT-TYPE
            SYNTAX SEQUENCE OF TxA3OstARackEntry
            MAX-ACCESS not-accessible
            STATUS current
            DESCRIPTION
                "The table of racks."
            ::= { outputstageATxA3 1 }

        
        txA3OstARackEntry OBJECT-TYPE
            SYNTAX TxA3OstARackEntry
            MAX-ACCESS not-accessible
            STATUS current
            DESCRIPTION
                "A row (an entry) for one rack."
            INDEX { txA3OstARackIdx }
            ::= { txA3OstARackTable 1 }

        
        TxA3OstARackEntry ::=
            SEQUENCE { 
                txA3OstARackIdx
                    IndexRack,
                txA3OstARackInletTemperature
                    FloatingPoint,
                txA3OstARackOutletTemperature
                    FloatingPoint,
                txA3OstARackAuxPowerSupply
                    FloatingPoint
             }

        txA3OstARackIdx OBJECT-TYPE
            SYNTAX IndexRack
            MAX-ACCESS not-accessible
            STATUS current
            DESCRIPTION
                "The rack number (1..10)."
            ::= { txA3OstARackEntry 1 }

        
        txA3OstARackInletTemperature OBJECT-TYPE
            SYNTAX FloatingPoint
            UNITS "Degree Celsius"
            MAX-ACCESS read-only
            STATUS current
            DESCRIPTION
                "The inlet temperature."
            ::= { txA3OstARackEntry 2 }

        
        txA3OstARackOutletTemperature OBJECT-TYPE
            SYNTAX FloatingPoint
            UNITS "Degree Celsius"
            MAX-ACCESS read-only
            STATUS current
            DESCRIPTION
                "The outlet temperature."
            ::= { txA3OstARackEntry 3 }

        
        txA3OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA3OstARackEntry 4 }

        
        exciterTxA3 OBJECT IDENTIFIER ::= { txA3 3 }

        
        txA3ExcInputTable OBJECT-TYPE
            SYNTAX SEQUENCE OF TxA3ExcInputEntry
            MAX-ACCESS not-accessible
            STATUS current
            DESCRIPTION
                "A table for more detailed information about the exciter.
                These values are all read-only. For settings, refer to commandsTxTable."
            ::= { exciterTxA3 1 }

        
        txA3ExcInputEntry OBJECT-TYPE
            SYNTAX TxA3ExcInputEntry
            MAX-ACCESS not-accessible
            STATUS current
            DESCRIPTION
                "An entry for a designated input channel."
            INDEX { txA3ExcInputExcIdx, txA3ExcInputChannelIdx }
            ::= { txA3ExcInputTable 1 }

        
        TxA3ExcInputEntry ::=
            SEQUENCE { 
                txA3ExcInputExcIdx
                    INTEGER,
                txA3ExcInputChannelIdx
                    Integer32,
                txA3ExcInputChannelName
                    INTEGER,
                txA3ExcInputConnected
                    TruthValue,
                txA3ExcInputSeamless
                    TruthValue,
                txA3ExcInputPreselected
                    TruthValue,
                txA3ExcInputActive
                    TruthValue,
                txA3ExcInputMipFail
                    TruthValue,
                txA3ExcInputBandwidth
                    INTEGER,
                txA3ExcInputFFTLength
                    INTEGER,
                txA3ExcInputGuardInterval
                    INTEGER,
                txA3ExcInputConstellation
                    INTEGER,
                txA3ExcInputAlpha
                    INTEGER,
                txA3ExcInputCellID
                    Integer32,
                txA3ExcInputInterleaver
                    INTEGER,
                txA3ExcInputCodeRate
                    INTEGER,
                txA3ExcInputPacketLength
                    Integer32,
                txA3ExcInputMeasuredDatarate
                    Integer32,
                txA3ExcInputRequiredDatarate
                    Integer32,
                txA3ExcInputMaximumDelay
                    Integer32
             }

        txA3ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA3ExcInputEntry 1 }

        
        txA3ExcInputChannelIdx OBJECT-TYPE
            SYNTAX Integer32 (1..6)
            MAX-ACCESS not-accessible
            STATUS current
            DESCRIPTION
                "The index for the different input channels."
            ::= { txA3ExcInputEntry 2 }

        
        txA3ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA3ExcInputEntry 3 }

        
        txA3ExcInputConnected OBJECT-TYPE
            SYNTAX TruthValue
            MAX-ACCESS read-only
            STATUS current
            DESCRIPTION
                "The input channel is connected."
            ::= { txA3ExcInputEntry 4 }

        
        txA3ExcInputSeamless OBJECT-TYPE
            SYNTAX TruthValue
            MAX-ACCESS read-only
            STATUS current
            DESCRIPTION
                "The input channel is in seamless mode."
            ::= { txA3ExcInputEntry 5 }

        
        txA3ExcInputPreselected OBJECT-TYPE
            SYNTAX TruthValue
            MAX-ACCESS read-only
            STATUS current
            DESCRIPTION
                "The input channel is the preselected."
            ::= { txA3ExcInputEntry 6 }

        
        txA3ExcInputActive OBJECT-TYPE
            SYNTAX TruthValue
            MAX-ACCESS read-only
            STATUS current
            DESCRIPTION
                "The input channel is active."
            ::= { txA3ExcInputEntry 7 }

        
        txA3ExcInputMipFail OBJECT-TYPE
            SYNTAX TruthValue
            MAX-ACCESS read-only
            STATUS current
            DESCRIPTION
                "Input channel MIP fail."
            ::= { txA3ExcInputEntry 8 }

        
        txA3ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA3ExcInputEntry 9 }

        
        txA3ExcInputFFTLength OBJECT-TYPE
            SYNTAX INTEGER
                {
                k2(1),
                k8(2),
                k4(3)
                }
            MAX-ACCESS read-only
            STATUS current
            DESCRIPTION
                "The used FFT length (depends on the DVB network)."
            ::= { txA3ExcInputEntry 10 }

        
        txA3ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA3ExcInputEntry 11 }

        
        txA3ExcInputConstellation OBJECT-TYPE
            SYNTAX INTEGER
                {
                qpsk(1),
                qam16(2),
                qam64(3)
                }
            MAX-ACCESS read-only
            STATUS current
            DESCRIPTION
                "This parameter sets the modulation mode."
            ::= { txA3ExcInputEntry 12 }

        
        txA3ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA3ExcInputEntry 13 }

        
        txA3ExcInputCellID OBJECT-TYPE
            SYNTAX Integer32 (0..65535)
            MAX-ACCESS read-only
            STATUS current
            DESCRIPTION
                "Via Cell ID the receiver knows the current network."
            ::= { txA3ExcInputEntry 14 }

        
        txA3ExcInputInterleaver OBJECT-TYPE
            SYNTAX INTEGER
                {
                indepth(1),
                nat(2)
                }
            MAX-ACCESS read-only
            STATUS current
            DESCRIPTION
                "Enables the bit interleaver for hierarchical coding"
            ::= { txA3ExcInputEntry 15 }

        
        txA3ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA3ExcInputEntry 16 }

        
        txA3ExcInputPacketLength OBJECT-TYPE
            SYNTAX Integer32 (188..208)
            MAX-ACCESS read-only
            STATUS current
            DESCRIPTION
                "The Packet length for the channel."
            ::= { txA3ExcInputEntry 17 }

        
        txA3ExcInputMeasuredDatarate OBJECT-TYPE
            SYNTAX Integer32
            MAX-ACCESS read-only
            STATUS current
            DESCRIPTION
                "The measured datarate of the input."
            ::= { txA3ExcInputEntry 18 }

        
        txA3ExcInputRequiredDatarate OBJECT-TYPE
            SYNTAX Integer32
            MAX-ACCESS read-only
            STATUS current
            DESCRIPTION
                "The required datarate of the input."
            ::= { txA3ExcInputEntry 19 }

        
        txA3ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA3ExcInputEntry 20 }

        
        outputstageBTxA3 OBJECT IDENTIFIER ::= { txA3 4 }

        
        txA3OstBRackTable OBJECT-TYPE
            SYNTAX SEQUENCE OF TxA3OstBRackEntry
            MAX-ACCESS not-accessible
            STATUS current
            DESCRIPTION
                "The table of racks for output stage B."
            ::= { outputstageBTxA3 1 }

        
        txA3OstBRackEntry OBJECT-TYPE
            SYNTAX TxA3OstBRackEntry
            MAX-ACCESS not-accessible
            STATUS current
            DESCRIPTION
                "A row (an entry) for one rack."
            INDEX { txA3OstBRackIdx }
            ::= { txA3OstBRackTable 1 }

        
        TxA3OstBRackEntry ::=
            SEQUENCE { 
                txA3OstBRackIdx
                    IndexRack,
                txA3OstBRackInletTemperature
                    FloatingPoint,
                txA3OstBRackOutletTemperature
                    FloatingPoint,
                txA3OstBRackAuxPowerSupply
                    FloatingPoint
             }

        txA3OstBRackIdx OBJECT-TYPE
            SYNTAX IndexRack
            MAX-ACCESS not-accessible
            STATUS current
            DESCRIPTION
                "The rack number (1..10)."
            ::= { txA3OstBRackEntry 1 }

        
        txA3OstBRackInletTemperature OBJECT-TYPE
            SYNTAX FloatingPoint
            UNITS "Degree Celsius"
            MAX-ACCESS read-only
            STATUS current
            DESCRIPTION
                "The inlet temperature."
            ::= { txA3OstBRackEntry 2 }

        
        txA3OstBRackOutletTemperature OBJECT-TYPE
            SYNTAX FloatingPoint
            UNITS "Degree Celsius"
            MAX-ACCESS read-only
            STATUS current
            DESCRIPTION
                "The outlet temperature."
            ::= { txA3OstBRackEntry 3 }

        
        txA3OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA3OstBRackEntry 4 }

        
        txA4 OBJECT IDENTIFIER ::= { transmitter 8 }

        
        logbookTxA4 OBJECT IDENTIFIER ::= { txA4 1 }

        
        txA4NetCCUNumberOfEntries OBJECT-TYPE
            SYNTAX LogbookMaxEntryNumber
            MAX-ACCESS read-only
            STATUS current
            DESCRIPTION
                "The number of entries in logbook."
            ::= { logbookTxA4 1 }

        
        txA4NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 2 }

        
        txA4NetCCULogbookTable OBJECT-TYPE
            SYNTAX SEQUENCE OF TxA4NetCCULogbookEntry
            MAX-ACCESS not-accessible
            STATUS current
            DESCRIPTION
                "NetCCU logbook table."
            ::= { logbookTxA4 3 }

        
        txA4NetCCULogbookEntry OBJECT-TYPE
            SYNTAX TxA4NetCCULogbookEntry
            MAX-ACCESS not-accessible
            STATUS current
            DESCRIPTION
                "This is a entry in the logbook."
            INDEX { txA4NetCCULogbookEntryIdx }
            ::= { txA4NetCCULogbookTable 1 }

        
        TxA4NetCCULogbookEntry ::=
            SEQUENCE { 
                txA4NetCCULogbookEntryIdx
                    LogbookMaxEntryNumber,
                txA4NetCCULogbookEntryNbr
                    LogbookMaxEntryNumber,
                txA4NetCCULogbookType
                    EventClass,
                txA4NetCCULogbookSlope
                    LogbookEntrySlope,
                txA4NetCCULogbookMessage
                    LogbookEntryMessagesNetCCU,
                txA4NetCCULogbookDateTime
                    DateAndTime
             }

        txA4NetCCULogbookEntryIdx OBJECT-TYPE
            SYNTAX LogbookMaxEntryNumber
            MAX-ACCESS not-accessible
            STATUS current
            DESCRIPTION
                "This is an increasing number from 1 to maximum. It is used as an index column for SNMP."
            ::= { txA4NetCCULogbookEntry 1 }

        
        txA4NetCCULogbookEntryNbr OBJECT-TYPE
            SYNTAX LogbookMaxEntryNumber
            MAX-ACCESS read-only
            STATUS current
            DESCRIPTION
                "This is the number of the logbook entry. It is an decreasing number from maximum down to 1."
            ::= { txA4NetCCULogbookEntry 2 }

        
        txA4NetCCULogbookType OBJECT-TYPE
            SYNTAX EventClass
            MAX-ACCESS read-only
            STATUS current
            DESCRIPTION
                "Can either be Fault, Warning or State."
            ::= { txA4NetCCULogbookEntry 3 }

        
        txA4NetCCULogbookSlope OBJECT-TYPE
            SYNTAX LogbookEntrySlope
            MAX-ACCESS read-only
            STATUS current
            DESCRIPTION
                "Either set (event raises) or reset (event disappears)"
            ::= { txA4NetCCULogbookEntry 4 }

        
        txA4NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA4NetCCULogbookEntry 5 }

        
        txA4NetCCULogbookDateTime OBJECT-TYPE
            SYNTAX DateAndTime
            MAX-ACCESS read-only
            STATUS current
            DESCRIPTION
                "The time of the logbook entry."
            ::= { txA4NetCCULogbookEntry 6 }

        
        txA4ExciterANumberOfEntries OBJECT-TYPE
            SYNTAX LogbookMaxEntryNumber
            MAX-ACCESS read-only
            STATUS current
            DESCRIPTION
                "The number of entries in logbook."
            ::= { logbookTxA4 4 }

        
        txA4ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 5 }

        
        txA4ExciterALogbookTable OBJECT-TYPE
            SYNTAX SEQUENCE OF TxA4ExciterALogbookEntry
            MAX-ACCESS not-accessible
            STATUS current
            DESCRIPTION
                "ExciterA logbook table."
            ::= { logbookTxA4 6 }

        
        txA4ExciterALogbookEntry OBJECT-TYPE
            SYNTAX TxA4ExciterALogbookEntry
            MAX-ACCESS not-accessible
            STATUS current
            DESCRIPTION
                "This is a entry in the logbook."
            INDEX { txA4ExcALogbookEntryIdx }
            ::= { txA4ExciterALogbookTable 1 }

        
        TxA4ExciterALogbookEntry ::=
            SEQUENCE { 
                txA4ExcALogbookEntryIdx
                    LogbookMaxEntryNumber,
                txA4ExcALogbookEntryNbr
                    LogbookMaxEntryNumber,
                txA4ExcALogbookType
                    EventClass,
                txA4ExcALogbookSlope
                    LogbookEntrySlope,
                txA4ExcALogbookMessage
                    LogbookEntryMessagesExcTv,
                txA4ExcALogbookDateTime
                    DateAndTime
             }

        txA4ExcALogbookEntryIdx OBJECT-TYPE
            SYNTAX LogbookMaxEntryNumber
            MAX-ACCESS not-accessible
            STATUS current
            DESCRIPTION
                "This is an increasing number from 1 to 128. It is used as an index column for SNMP."
            ::= { txA4ExciterALogbookEntry 1 }

        
        txA4ExcALogbookEntryNbr OBJECT-TYPE
            SYNTAX LogbookMaxEntryNumber
            MAX-ACCESS read-only
            STATUS current
            DESCRIPTION
                "This is the number of the logbook entry. It is an decreasing number from max 128 down to 1."
            ::= { txA4ExciterALogbookEntry 2 }

        
        txA4ExcALogbookType OBJECT-TYPE
            SYNTAX EventClass
            MAX-ACCESS read-only
            STATUS current
            DESCRIPTION
                "Can either be Fault, Warning or State."
            ::= { txA4ExciterALogbookEntry 3 }

        
        txA4ExcALogbookSlope OBJECT-TYPE
            SYNTAX LogbookEntrySlope
            MAX-ACCESS read-only
            STATUS current
            DESCRIPTION
                "Either set (event raises) or reset (event disappears)"
            ::= { txA4ExciterALogbookEntry 4 }

        
        txA4ExcALogbookMessage OBJECT-TYPE
            SYNTAX LogbookEntryMessagesExcTv
            MAX-ACCESS read-only
            STATUS current
            DESCRIPTION
                "See RS-XX8000-COMMON-MIB - TextualConvention for details."
            ::= { txA4ExciterALogbookEntry 5 }

        
        txA4ExcALogbookDateTime OBJECT-TYPE
            SYNTAX DateAndTime
            MAX-ACCESS read-only
            STATUS current
            DESCRIPTION
                "The time of the logbook entry."
            ::= { txA4ExciterALogbookEntry 6 }

        
        txA4OutputstageANumberOfEntries OBJECT-TYPE
            SYNTAX LogbookMaxEntryNumber
            MAX-ACCESS read-only
            STATUS current
            DESCRIPTION
                "The number of entries in logbook."
            ::= { logbookTxA4 7 }

        
        txA4OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 8 }

        
        txA4OutputstageALogbookTable OBJECT-TYPE
            SYNTAX SEQUENCE OF TxA4OutputstageALogbookEntry
            MAX-ACCESS not-accessible
            STATUS current
            DESCRIPTION
                "OutputstageA logbook table."
            ::= { logbookTxA4 9 }

        
        txA4OutputstageALogbookEntry OBJECT-TYPE
            SYNTAX TxA4OutputstageALogbookEntry
            MAX-ACCESS not-accessible
            STATUS current
            DESCRIPTION
                "This is a entry in the logbook."
            INDEX { txA4OstALogbookEntryIdx }
            ::= { txA4OutputstageALogbookTable 1 }

        
        TxA4OutputstageALogbookEntry ::=
            SEQUENCE { 
                txA4OstALogbookEntryIdx
                    LogbookMaxEntryNumber,
                txA4OstALogbookEntryNbr
                    LogbookMaxEntryNumber,
                txA4OstALogbookType
                    EventClass,
                txA4OstALogbookSlope
                    LogbookEntrySlope,
                txA4OstALogbookMessage
                    LogbookEntryMessagesOST,
                txA4OstALogbookDateTime
                    DateAndTime
             }

        txA4OstALogbookEntryIdx OBJECT-TYPE
            SYNTAX LogbookMaxEntryNumber
            MAX-ACCESS not-accessible
            STATUS current
            DESCRIPTION
                "This is an increasing number from 1 to maximum. It is used as an index column for SNMP."
            ::= { txA4OutputstageALogbookEntry 1 }

        
        txA4OstALogbookEntryNbr OBJECT-TYPE
            SYNTAX LogbookMaxEntryNumber
            MAX-ACCESS read-only
            STATUS current
            DESCRIPTION
                "This is the number of the logbook entry. It is an decreasing number from maximum down to 1."
            ::= { txA4OutputstageALogbookEntry 2 }

        
        txA4OstALogbookType OBJECT-TYPE
            SYNTAX EventClass
            MAX-ACCESS read-only
            STATUS current
            DESCRIPTION
                "Can either be Fault, Warning or State."
            ::= { txA4OutputstageALogbookEntry 3 }

        
        txA4OstALogbookSlope OBJECT-TYPE
            SYNTAX LogbookEntrySlope
            MAX-ACCESS read-only
            STATUS current
            DESCRIPTION
                "Either set (event raises) or reset (event disappears)"
            ::= { txA4OutputstageALogbookEntry 4 }

        
        txA4OstALogbookMessage OBJECT-TYPE
            SYNTAX LogbookEntryMessagesOST
            MAX-ACCESS read-only
            STATUS current
            DESCRIPTION
                "See RS-XX8000-COMMON-MIB - TextualConvention for details."
            ::= { txA4OutputstageALogbookEntry 5 }

        
        txA4OstALogbookDateTime OBJECT-TYPE
            SYNTAX DateAndTime
            MAX-ACCESS read-only
            STATUS current
            DESCRIPTION
                "The time of the logbook entry."
            ::= { txA4OutputstageALogbookEntry 6 }

        
        txA4ExciterBNumberOfEntries OBJECT-TYPE
            SYNTAX LogbookMaxEntryNumber
            MAX-ACCESS read-only
            STATUS current
            DESCRIPTION
                "The number of entries in logbook."
            ::= { logbookTxA4 13 }

        
        txA4ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 14 }

        
        txA4ExciterBLogbookTable OBJECT-TYPE
            SYNTAX SEQUENCE OF TxA4ExciterBLogbookEntry
            MAX-ACCESS not-accessible
            STATUS current
            DESCRIPTION
                "ExciterB logbook table."
            ::= { logbookTxA4 15 }

        
        txA4ExciterBLogbookEntry OBJECT-TYPE
            SYNTAX TxA4ExciterBLogbookEntry
            MAX-ACCESS not-accessible
            STATUS current
            DESCRIPTION
                "This is a entry in the logbook."
            INDEX { txA4ExcBLogbookEntryIdx }
            ::= { txA4ExciterBLogbookTable 1 }

        
        TxA4ExciterBLogbookEntry ::=
            SEQUENCE { 
                txA4ExcBLogbookEntryIdx
                    LogbookMaxEntryNumber,
                txA4ExcBLogbookEntryNbr
                    LogbookMaxEntryNumber,
                txA4ExcBLogbookType
                    EventClass,
                txA4ExcBLogbookSlope
                    LogbookEntrySlope,
                txA4ExcBLogbookMessage
                    LogbookEntryMessagesExcTv,
                txA4ExcBLogbookDateTime
                    DateAndTime
             }

        txA4ExcBLogbookEntryIdx OBJECT-TYPE
            SYNTAX LogbookMaxEntryNumber
            MAX-ACCESS not-accessible
            STATUS current
            DESCRIPTION
                "This is an increasing number from 1 to maximum. It is used as an index column for SNMP."
            ::= { txA4ExciterBLogbookEntry 1 }

        
        txA4ExcBLogbookEntryNbr OBJECT-TYPE
            SYNTAX LogbookMaxEntryNumber
            MAX-ACCESS read-only
            STATUS current
            DESCRIPTION
                "This is the number of the logbook entry. It is an decreasing number from maximum down to 1."
            ::= { txA4ExciterBLogbookEntry 2 }

        
        txA4ExcBLogbookType OBJECT-TYPE
            SYNTAX EventClass
            MAX-ACCESS read-only
            STATUS current
            DESCRIPTION
                "Can either be Fault, Warning or State."
            ::= { txA4ExciterBLogbookEntry 3 }

        
        txA4ExcBLogbookSlope OBJECT-TYPE
            SYNTAX LogbookEntrySlope
            MAX-ACCESS read-only
            STATUS current
            DESCRIPTION
                "Either set (event raises) or reset (event disappears)"
            ::= { txA4ExciterBLogbookEntry 4 }

        
        txA4ExcBLogbookMessage OBJECT-TYPE
            SYNTAX LogbookEntryMessagesExcTv
            MAX-ACCESS read-only
            STATUS current
            DESCRIPTION
                "See RS-XX8000-COMMON-MIB - TextualConvention for details."
            ::= { txA4ExciterBLogbookEntry 5 }

        
        txA4ExcBLogbookDateTime OBJECT-TYPE
            SYNTAX DateAndTime
            MAX-ACCESS read-only
            STATUS current
            DESCRIPTION
                "The time of the logbook entry."
            ::= { txA4ExciterBLogbookEntry 6 }

        
        txA4OutputstageBNumberOfEntries OBJECT-TYPE
            SYNTAX LogbookMaxEntryNumber
            MAX-ACCESS read-only
            STATUS current
            DESCRIPTION
                "The number of entries in logbook of output stage B."
            ::= { logbookTxA4 16 }

        
        txA4OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 17 }

        
        txA4OutputstageBLogbookTable OBJECT-TYPE
            SYNTAX SEQUENCE OF TxA4OutputstageBLogbookEntry
            MAX-ACCESS not-accessible
            STATUS current
            DESCRIPTION
                "Output stage B logbook table."
            ::= { logbookTxA4 18 }

        
        txA4OutputstageBLogbookEntry OBJECT-TYPE
            SYNTAX TxA4OutputstageBLogbookEntry
            MAX-ACCESS not-accessible
            STATUS current
            DESCRIPTION
                "This is a entry in the logbook."
            INDEX { txA4OstBLogbookEntryIdx }
            ::= { txA4OutputstageBLogbookTable 1 }

        
        TxA4OutputstageBLogbookEntry ::=
            SEQUENCE { 
                txA4OstBLogbookEntryIdx
                    LogbookMaxEntryNumber,
                txA4OstBLogbookEntryNbr
                    LogbookMaxEntryNumber,
                txA4OstBLogbookType
                    EventClass,
                txA4OstBLogbookSlope
                    LogbookEntrySlope,
                txA4OstBLogbookMessage
                    LogbookEntryMessagesOST,
                txA4OstBLogbookDateTime
                    DateAndTime
             }

        txA4OstBLogbookEntryIdx OBJECT-TYPE
            SYNTAX LogbookMaxEntryNumber
            MAX-ACCESS not-accessible
            STATUS current
            DESCRIPTION
                "This is an increasing number from 1 to maximum. It is used as an index column for SNMP."
            ::= { txA4OutputstageBLogbookEntry 1 }

        
        txA4OstBLogbookEntryNbr OBJECT-TYPE
            SYNTAX LogbookMaxEntryNumber
            MAX-ACCESS read-only
            STATUS current
            DESCRIPTION
                "This is the number of the logbook entry. It is an decreasing number from maximum down to 1."
            ::= { txA4OutputstageBLogbookEntry 2 }

        
        txA4OstBLogbookType OBJECT-TYPE
            SYNTAX EventClass
            MAX-ACCESS read-only
            STATUS current
            DESCRIPTION
                "Can either be Fault, Warning or State."
            ::= { txA4OutputstageBLogbookEntry 3 }

        
        txA4OstBLogbookSlope OBJECT-TYPE
            SYNTAX LogbookEntrySlope
            MAX-ACCESS read-only
            STATUS current
            DESCRIPTION
                "Either set (event raises) or reset (event disappears)"
            ::= { txA4OutputstageBLogbookEntry 4 }

        
        txA4OstBLogbookMessage OBJECT-TYPE
            SYNTAX LogbookEntryMessagesOST
            MAX-ACCESS read-only
            STATUS current
            DESCRIPTION
                "See RS-XX8000-COMMON-MIB - TextualConvention for details."
            ::= { txA4OutputstageBLogbookEntry 5 }

        
        txA4OstBLogbookDateTime OBJECT-TYPE
            SYNTAX DateAndTime
            MAX-ACCESS read-only
            STATUS current
            DESCRIPTION
                "The time of the logbook entry."
            ::= { txA4OutputstageBLogbookEntry 6 }

        
        outputstageATxA4 OBJECT IDENTIFIER ::= { txA4 2 }

        
        txA4OstARackTable OBJECT-TYPE
            SYNTAX SEQUENCE OF TxA4OstARackEntry
            MAX-ACCESS not-accessible
            STATUS current
            DESCRIPTION
                "The table of racks."
            ::= { outputstageATxA4 1 }

        
        txA4OstARackEntry OBJECT-TYPE
            SYNTAX TxA4OstARackEntry
            MAX-ACCESS not-accessible
            STATUS current
            DESCRIPTION
                "A row (an entry) for one rack."
            INDEX { txA4OstARackIdx }
            ::= { txA4OstARackTable 1 }

        
        TxA4OstARackEntry ::=
            SEQUENCE { 
                txA4OstARackIdx
                    IndexRack,
                txA4OstARackInletTemperature
                    FloatingPoint,
                txA4OstARackOutletTemperature
                    FloatingPoint,
                txA4OstARackAuxPowerSupply
                    FloatingPoint
             }

        txA4OstARackIdx OBJECT-TYPE
            SYNTAX IndexRack
            MAX-ACCESS not-accessible
            STATUS current
            DESCRIPTION
                "The rack number (1..10)."
            ::= { txA4OstARackEntry 1 }

        
        txA4OstARackInletTemperature OBJECT-TYPE
            SYNTAX FloatingPoint
            UNITS "Degree Celsius"
            MAX-ACCESS read-only
            STATUS current
            DESCRIPTION
                "The inlet temperature."
            ::= { txA4OstARackEntry 2 }

        
        txA4OstARackOutletTemperature OBJECT-TYPE
            SYNTAX FloatingPoint
            UNITS "Degree Celsius"
            MAX-ACCESS read-only
            STATUS current
            DESCRIPTION
                "The outlet temperature."
            ::= { txA4OstARackEntry 3 }

        
        txA4OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA4OstARackEntry 4 }

        
        exciterTxA4 OBJECT IDENTIFIER ::= { txA4 3 }

        
        txA4ExcInputTable OBJECT-TYPE
            SYNTAX SEQUENCE OF TxA4ExcInputEntry
            MAX-ACCESS not-accessible
            STATUS current
            DESCRIPTION
                "A table for more detailed information about the exciter.
                These values are all read-only. For settings, refer to commandsTxTable."
            ::= { exciterTxA4 1 }

        
        txA4ExcInputEntry OBJECT-TYPE
            SYNTAX TxA4ExcInputEntry
            MAX-ACCESS not-accessible
            STATUS current
            DESCRIPTION
                "An entry for a designated input channel."
            INDEX { txA4ExcInputExcIdx, txA4ExcInputChannelIdx }
            ::= { txA4ExcInputTable 1 }

        
        TxA4ExcInputEntry ::=
            SEQUENCE { 
                txA4ExcInputExcIdx
                    INTEGER,
                txA4ExcInputChannelIdx
                    Integer32,
                txA4ExcInputChannelName
                    INTEGER,
                txA4ExcInputConnected
                    TruthValue,
                txA4ExcInputSeamless
                    TruthValue,
                txA4ExcInputPreselected
                    TruthValue,
                txA4ExcInputActive
                    TruthValue,
                txA4ExcInputMipFail
                    TruthValue,
                txA4ExcInputBandwidth
                    INTEGER,
                txA4ExcInputFFTLength
                    INTEGER,
                txA4ExcInputGuardInterval
                    INTEGER,
                txA4ExcInputConstellation
                    INTEGER,
                txA4ExcInputAlpha
                    INTEGER,
                txA4ExcInputCellID
                    Integer32,
                txA4ExcInputInterleaver
                    INTEGER,
                txA4ExcInputCodeRate
                    INTEGER,
                txA4ExcInputPacketLength
                    Integer32,
                txA4ExcInputMeasuredDatarate
                    Integer32,
                txA4ExcInputRequiredDatarate
                    Integer32,
                txA4ExcInputMaximumDelay
                    Integer32
             }

        txA4ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA4ExcInputEntry 1 }

        
        txA4ExcInputChannelIdx OBJECT-TYPE
            SYNTAX Integer32 (1..6)
            MAX-ACCESS not-accessible
            STATUS current
            DESCRIPTION
                "The index for the different input channels."
            ::= { txA4ExcInputEntry 2 }

        
        txA4ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA4ExcInputEntry 3 }

        
        txA4ExcInputConnected OBJECT-TYPE
            SYNTAX TruthValue
            MAX-ACCESS read-only
            STATUS current
            DESCRIPTION
                "The input channel is connected."
            ::= { txA4ExcInputEntry 4 }

        
        txA4ExcInputSeamless OBJECT-TYPE
            SYNTAX TruthValue
            MAX-ACCESS read-only
            STATUS current
            DESCRIPTION
                "The input channel is in seamless mode."
            ::= { txA4ExcInputEntry 5 }

        
        txA4ExcInputPreselected OBJECT-TYPE
            SYNTAX TruthValue
            MAX-ACCESS read-only
            STATUS current
            DESCRIPTION
                "The input channel is the preselected."
            ::= { txA4ExcInputEntry 6 }

        
        txA4ExcInputActive OBJECT-TYPE
            SYNTAX TruthValue
            MAX-ACCESS read-only
            STATUS current
            DESCRIPTION
                "The input channel is active."
            ::= { txA4ExcInputEntry 7 }

        
        txA4ExcInputMipFail OBJECT-TYPE
            SYNTAX TruthValue
            MAX-ACCESS read-only
            STATUS current
            DESCRIPTION
                "Input channel MIP fail."
            ::= { txA4ExcInputEntry 8 }

        
        txA4ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA4ExcInputEntry 9 }

        
        txA4ExcInputFFTLength OBJECT-TYPE
            SYNTAX INTEGER
                {
                k2(1),
                k8(2),
                k4(3)
                }
            MAX-ACCESS read-only
            STATUS current
            DESCRIPTION
                "The used FFT length (depends on the DVB network)."
            ::= { txA4ExcInputEntry 10 }

        
        txA4ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA4ExcInputEntry 11 }

        
        txA4ExcInputConstellation OBJECT-TYPE
            SYNTAX INTEGER
                {
                qpsk(1),
                qam16(2),
                qam64(3)
                }
            MAX-ACCESS read-only
            STATUS current
            DESCRIPTION
                "This parameter sets the modulation mode."
            ::= { txA4ExcInputEntry 12 }

        
        txA4ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA4ExcInputEntry 13 }

        
        txA4ExcInputCellID OBJECT-TYPE
            SYNTAX Integer32 (0..65535)
            MAX-ACCESS read-only
            STATUS current
            DESCRIPTION
                "Via Cell ID the receiver knows the current network."
            ::= { txA4ExcInputEntry 14 }

        
        txA4ExcInputInterleaver OBJECT-TYPE
            SYNTAX INTEGER
                {
                indepth(1),
                nat(2)
                }
            MAX-ACCESS read-only
            STATUS current
            DESCRIPTION
                "Enables the bit interleaver for hierarchical coding"
            ::= { txA4ExcInputEntry 15 }

        
        txA4ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA4ExcInputEntry 16 }

        
        txA4ExcInputPacketLength OBJECT-TYPE
            SYNTAX Integer32 (188..208)
            MAX-ACCESS read-only
            STATUS current
            DESCRIPTION
                "The Packet length for the channel."
            ::= { txA4ExcInputEntry 17 }

        
        txA4ExcInputMeasuredDatarate OBJECT-TYPE
            SYNTAX Integer32
            MAX-ACCESS read-only
            STATUS current
            DESCRIPTION
                "The measured datarate of the input."
            ::= { txA4ExcInputEntry 18 }

        
        txA4ExcInputRequiredDatarate OBJECT-TYPE
            SYNTAX Integer32
            MAX-ACCESS read-only
            STATUS current
            DESCRIPTION
                "The required datarate of the input."
            ::= { txA4ExcInputEntry 19 }

        
        txA4ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA4ExcInputEntry 20 }

        
        outputstageBTxA4 OBJECT IDENTIFIER ::= { txA4 4 }

        
        txA4OstBRackTable OBJECT-TYPE
            SYNTAX SEQUENCE OF TxA4OstBRackEntry
            MAX-ACCESS not-accessible
            STATUS current
            DESCRIPTION
                "The table of racks for output stage B."
            ::= { outputstageBTxA4 1 }

        
        txA4OstBRackEntry OBJECT-TYPE
            SYNTAX TxA4OstBRackEntry
            MAX-ACCESS not-accessible
            STATUS current
            DESCRIPTION
                "A row (an entry) for one rack."
            INDEX { txA4OstBRackIdx }
            ::= { txA4OstBRackTable 1 }

        
        TxA4OstBRackEntry ::=
            SEQUENCE { 
                txA4OstBRackIdx
                    IndexRack,
                txA4OstBRackInletTemperature
                    FloatingPoint,
                txA4OstBRackOutletTemperature
                    FloatingPoint,
                txA4OstBRackAuxPowerSupply
                    FloatingPoint
             }

        txA4OstBRackIdx OBJECT-TYPE
            SYNTAX IndexRack
            MAX-ACCESS not-accessible
            STATUS current
            DESCRIPTION
                "The rack number (1..10)."
            ::= { txA4OstBRackEntry 1 }

        
        txA4OstBRackInletTemperature OBJECT-TYPE
            SYNTAX FloatingPoint
            UNITS "Degree Celsius"
            MAX-ACCESS read-only
            STATUS current
            DESCRIPTION
                "The inlet temperature."
            ::= { txA4OstBRackEntry 2 }

        
        txA4OstBRackOutletTemperature OBJECT-TYPE
            SYNTAX FloatingPoint
            UNITS "Degree Celsius"
            MAX-ACCESS read-only
            STATUS current
            DESCRIPTION
                "The outlet temperature."
            ::= { txA4OstBRackEntry 3 }

        
        txA4OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA4OstBRackEntry 4 }

        
        txA5 OBJECT IDENTIFIER ::= { transmitter 9 }

        
        logbookTxA5 OBJECT IDENTIFIER ::= { txA5 1 }

        
        txA5NetCCUNumberOfEntries OBJECT-TYPE
            SYNTAX LogbookMaxEntryNumber
            MAX-ACCESS read-only
            STATUS current
            DESCRIPTION
                "The number of entries in logbook."
            ::= { logbookTxA5 1 }

        
        txA5NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 2 }

        
        txA5NetCCULogbookTable OBJECT-TYPE
            SYNTAX SEQUENCE OF TxA5NetCCULogbookEntry
            MAX-ACCESS not-accessible
            STATUS current
            DESCRIPTION
                "NetCCU logbook table."
            ::= { logbookTxA5 3 }

        
        txA5NetCCULogbookEntry OBJECT-TYPE
            SYNTAX TxA5NetCCULogbookEntry
            MAX-ACCESS not-accessible
            STATUS current
            DESCRIPTION
                "This is a entry in the logbook."
            INDEX { txA5NetCCULogbookEntryIdx }
            ::= { txA5NetCCULogbookTable 1 }

        
        TxA5NetCCULogbookEntry ::=
            SEQUENCE { 
                txA5NetCCULogbookEntryIdx
                    LogbookMaxEntryNumber,
                txA5NetCCULogbookEntryNbr
                    LogbookMaxEntryNumber,
                txA5NetCCULogbookType
                    EventClass,
                txA5NetCCULogbookSlope
                    LogbookEntrySlope,
                txA5NetCCULogbookMessage
                    LogbookEntryMessagesNetCCU,
                txA5NetCCULogbookDateTime
                    DateAndTime
             }

        txA5NetCCULogbookEntryIdx OBJECT-TYPE
            SYNTAX LogbookMaxEntryNumber
            MAX-ACCESS not-accessible
            STATUS current
            DESCRIPTION
                "This is an increasing number from 1 to maximum. It is used as an index column for SNMP."
            ::= { txA5NetCCULogbookEntry 1 }

        
        txA5NetCCULogbookEntryNbr OBJECT-TYPE
            SYNTAX LogbookMaxEntryNumber
            MAX-ACCESS read-only
            STATUS current
            DESCRIPTION
                "This is the number of the logbook entry. It is an decreasing number from maximum down to 1."
            ::= { txA5NetCCULogbookEntry 2 }

        
        txA5NetCCULogbookType OBJECT-TYPE
            SYNTAX EventClass
            MAX-ACCESS read-only
            STATUS current
            DESCRIPTION
                "Can either be Fault, Warning or State."
            ::= { txA5NetCCULogbookEntry 3 }

        
        txA5NetCCULogbookSlope OBJECT-TYPE
            SYNTAX LogbookEntrySlope
            MAX-ACCESS read-only
            STATUS current
            DESCRIPTION
                "Either set (event raises) or reset (event disappears)"
            ::= { txA5NetCCULogbookEntry 4 }

        
        txA5NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA5NetCCULogbookEntry 5 }

        
        txA5NetCCULogbookDateTime OBJECT-TYPE
            SYNTAX DateAndTime
            MAX-ACCESS read-only
            STATUS current
            DESCRIPTION
                "The time of the logbook entry."
            ::= { txA5NetCCULogbookEntry 6 }

        
        txA5ExciterANumberOfEntries OBJECT-TYPE
            SYNTAX LogbookMaxEntryNumber
            MAX-ACCESS read-only
            STATUS current
            DESCRIPTION
                "The number of entries in logbook."
            ::= { logbookTxA5 4 }

        
        txA5ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 5 }

        
        txA5ExciterALogbookTable OBJECT-TYPE
            SYNTAX SEQUENCE OF TxA5ExciterALogbookEntry
            MAX-ACCESS not-accessible
            STATUS current
            DESCRIPTION
                "ExciterA logbook table."
            ::= { logbookTxA5 6 }

        
        txA5ExciterALogbookEntry OBJECT-TYPE
            SYNTAX TxA5ExciterALogbookEntry
            MAX-ACCESS not-accessible
            STATUS current
            DESCRIPTION
                "This is a entry in the logbook."
            INDEX { txA5ExcALogbookEntryIdx }
            ::= { txA5ExciterALogbookTable 1 }

        
        TxA5ExciterALogbookEntry ::=
            SEQUENCE { 
                txA5ExcALogbookEntryIdx
                    LogbookMaxEntryNumber,
                txA5ExcALogbookEntryNbr
                    LogbookMaxEntryNumber,
                txA5ExcALogbookType
                    EventClass,
                txA5ExcALogbookSlope
                    LogbookEntrySlope,
                txA5ExcALogbookMessage
                    LogbookEntryMessagesExcTv,
                txA5ExcALogbookDateTime
                    DateAndTime
             }

        txA5ExcALogbookEntryIdx OBJECT-TYPE
            SYNTAX LogbookMaxEntryNumber
            MAX-ACCESS not-accessible
            STATUS current
            DESCRIPTION
                "This is an increasing number from 1 to 128. It is used as an index column for SNMP."
            ::= { txA5ExciterALogbookEntry 1 }

        
        txA5ExcALogbookEntryNbr OBJECT-TYPE
            SYNTAX LogbookMaxEntryNumber
            MAX-ACCESS read-only
            STATUS current
            DESCRIPTION
                "This is the number of the logbook entry. It is an decreasing number from max 128 down to 1."
            ::= { txA5ExciterALogbookEntry 2 }

        
        txA5ExcALogbookType OBJECT-TYPE
            SYNTAX EventClass
            MAX-ACCESS read-only
            STATUS current
            DESCRIPTION
                "Can either be Fault, Warning or State."
            ::= { txA5ExciterALogbookEntry 3 }

        
        txA5ExcALogbookSlope OBJECT-TYPE
            SYNTAX LogbookEntrySlope
            MAX-ACCESS read-only
            STATUS current
            DESCRIPTION
                "Either set (event raises) or reset (event disappears)"
            ::= { txA5ExciterALogbookEntry 4 }

        
        txA5ExcALogbookMessage OBJECT-TYPE
            SYNTAX LogbookEntryMessagesExcTv
            MAX-ACCESS read-only
            STATUS current
            DESCRIPTION
                "See RS-XX8000-COMMON-MIB - TextualConvention for details."
            ::= { txA5ExciterALogbookEntry 5 }

        
        txA5ExcALogbookDateTime OBJECT-TYPE
            SYNTAX DateAndTime
            MAX-ACCESS read-only
            STATUS current
            DESCRIPTION
                "The time of the logbook entry."
            ::= { txA5ExciterALogbookEntry 6 }

        
        txA5OutputstageANumberOfEntries OBJECT-TYPE
            SYNTAX LogbookMaxEntryNumber
            MAX-ACCESS read-only
            STATUS current
            DESCRIPTION
                "The number of entries in logbook."
            ::= { logbookTxA5 7 }

        
        txA5OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 8 }

        
        txA5OutputstageALogbookTable OBJECT-TYPE
            SYNTAX SEQUENCE OF TxA5OutputstageALogbookEntry
            MAX-ACCESS not-accessible
            STATUS current
            DESCRIPTION
                "OutputstageA logbook table."
            ::= { logbookTxA5 9 }

        
        txA5OutputstageALogbookEntry OBJECT-TYPE
            SYNTAX TxA5OutputstageALogbookEntry
            MAX-ACCESS not-accessible
            STATUS current
            DESCRIPTION
                "This is a entry in the logbook."
            INDEX { txA5OstALogbookEntryIdx }
            ::= { txA5OutputstageALogbookTable 1 }

        
        TxA5OutputstageALogbookEntry ::=
            SEQUENCE { 
                txA5OstALogbookEntryIdx
                    LogbookMaxEntryNumber,
                txA5OstALogbookEntryNbr
                    LogbookMaxEntryNumber,
                txA5OstALogbookType
                    EventClass,
                txA5OstALogbookSlope
                    LogbookEntrySlope,
                txA5OstALogbookMessage
                    LogbookEntryMessagesOST,
                txA5OstALogbookDateTime
                    DateAndTime
             }

        txA5OstALogbookEntryIdx OBJECT-TYPE
            SYNTAX LogbookMaxEntryNumber
            MAX-ACCESS not-accessible
            STATUS current
            DESCRIPTION
                "This is an increasing number from 1 to maximum. It is used as an index column for SNMP."
            ::= { txA5OutputstageALogbookEntry 1 }

        
        txA5OstALogbookEntryNbr OBJECT-TYPE
            SYNTAX LogbookMaxEntryNumber
            MAX-ACCESS read-only
            STATUS current
            DESCRIPTION
                "This is the number of the logbook entry. It is an decreasing number from maximum down to 1."
            ::= { txA5OutputstageALogbookEntry 2 }

        
        txA5OstALogbookType OBJECT-TYPE
            SYNTAX EventClass
            MAX-ACCESS read-only
            STATUS current
            DESCRIPTION
                "Can either be Fault, Warning or State."
            ::= { txA5OutputstageALogbookEntry 3 }

        
        txA5OstALogbookSlope OBJECT-TYPE
            SYNTAX LogbookEntrySlope
            MAX-ACCESS read-only
            STATUS current
            DESCRIPTION
                "Either set (event raises) or reset (event disappears)"
            ::= { txA5OutputstageALogbookEntry 4 }

        
        txA5OstALogbookMessage OBJECT-TYPE
            SYNTAX LogbookEntryMessagesOST
            MAX-ACCESS read-only
            STATUS current
            DESCRIPTION
                "See RS-XX8000-COMMON-MIB - TextualConvention for details."
            ::= { txA5OutputstageALogbookEntry 5 }

        
        txA5OstALogbookDateTime OBJECT-TYPE
            SYNTAX DateAndTime
            MAX-ACCESS read-only
            STATUS current
            DESCRIPTION
                "The time of the logbook entry."
            ::= { txA5OutputstageALogbookEntry 6 }

        
        txA5ExciterBNumberOfEntries OBJECT-TYPE
            SYNTAX LogbookMaxEntryNumber
            MAX-ACCESS read-only
            STATUS current
            DESCRIPTION
                "The number of entries in logbook."
            ::= { logbookTxA5 13 }

        
        txA5ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 14 }

        
        txA5ExciterBLogbookTable OBJECT-TYPE
            SYNTAX SEQUENCE OF TxA5ExciterBLogbookEntry
            MAX-ACCESS not-accessible
            STATUS current
            DESCRIPTION
                "ExciterB logbook table."
            ::= { logbookTxA5 15 }

        
        txA5ExciterBLogbookEntry OBJECT-TYPE
            SYNTAX TxA5ExciterBLogbookEntry
            MAX-ACCESS not-accessible
            STATUS current
            DESCRIPTION
                "This is a entry in the logbook."
            INDEX { txA5ExcBLogbookEntryIdx }
            ::= { txA5ExciterBLogbookTable 1 }

        
        TxA5ExciterBLogbookEntry ::=
            SEQUENCE { 
                txA5ExcBLogbookEntryIdx
                    LogbookMaxEntryNumber,
                txA5ExcBLogbookEntryNbr
                    LogbookMaxEntryNumber,
                txA5ExcBLogbookType
                    EventClass,
                txA5ExcBLogbookSlope
                    LogbookEntrySlope,
                txA5ExcBLogbookMessage
                    LogbookEntryMessagesExcTv,
                txA5ExcBLogbookDateTime
                    DateAndTime
             }

        txA5ExcBLogbookEntryIdx OBJECT-TYPE
            SYNTAX LogbookMaxEntryNumber
            MAX-ACCESS not-accessible
            STATUS current
            DESCRIPTION
                "This is an increasing number from 1 to maximum. It is used as an index column for SNMP."
            ::= { txA5ExciterBLogbookEntry 1 }

        
        txA5ExcBLogbookEntryNbr OBJECT-TYPE
            SYNTAX LogbookMaxEntryNumber
            MAX-ACCESS read-only
            STATUS current
            DESCRIPTION
                "This is the number of the logbook entry. It is an decreasing number from maximum down to 1."
            ::= { txA5ExciterBLogbookEntry 2 }

        
        txA5ExcBLogbookType OBJECT-TYPE
            SYNTAX EventClass
            MAX-ACCESS read-only
            STATUS current
            DESCRIPTION
                "Can either be Fault, Warning or State."
            ::= { txA5ExciterBLogbookEntry 3 }

        
        txA5ExcBLogbookSlope OBJECT-TYPE
            SYNTAX LogbookEntrySlope
            MAX-ACCESS read-only
            STATUS current
            DESCRIPTION
                "Either set (event raises) or reset (event disappears)"
            ::= { txA5ExciterBLogbookEntry 4 }

        
        txA5ExcBLogbookMessage OBJECT-TYPE
            SYNTAX LogbookEntryMessagesExcTv
            MAX-ACCESS read-only
            STATUS current
            DESCRIPTION
                "See RS-XX8000-COMMON-MIB - TextualConvention for details."
            ::= { txA5ExciterBLogbookEntry 5 }

        
        txA5ExcBLogbookDateTime OBJECT-TYPE
            SYNTAX DateAndTime
            MAX-ACCESS read-only
            STATUS current
            DESCRIPTION
                "The time of the logbook entry."
            ::= { txA5ExciterBLogbookEntry 6 }

        
        txA5OutputstageBNumberOfEntries OBJECT-TYPE
            SYNTAX LogbookMaxEntryNumber
            MAX-ACCESS read-only
            STATUS current
            DESCRIPTION
                "The number of entries in logbook of output stage B."
            ::= { logbookTxA5 16 }

        
        txA5OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 17 }

        
        txA5OutputstageBLogbookTable OBJECT-TYPE
            SYNTAX SEQUENCE OF TxA5OutputstageBLogbookEntry
            MAX-ACCESS not-accessible
            STATUS current
            DESCRIPTION
                "Output stage B logbook table."
            ::= { logbookTxA5 18 }

        
        txA5OutputstageBLogbookEntry OBJECT-TYPE
            SYNTAX TxA5OutputstageBLogbookEntry
            MAX-ACCESS not-accessible
            STATUS current
            DESCRIPTION
                "This is a entry in the logbook."
            INDEX { txA5OstBLogbookEntryIdx }
            ::= { txA5OutputstageBLogbookTable 1 }

        
        TxA5OutputstageBLogbookEntry ::=
            SEQUENCE { 
                txA5OstBLogbookEntryIdx
                    LogbookMaxEntryNumber,
                txA5OstBLogbookEntryNbr
                    LogbookMaxEntryNumber,
                txA5OstBLogbookType
                    EventClass,
                txA5OstBLogbookSlope
                    LogbookEntrySlope,
                txA5OstBLogbookMessage
                    LogbookEntryMessagesOST,
                txA5OstBLogbookDateTime
                    DateAndTime
             }

        txA5OstBLogbookEntryIdx OBJECT-TYPE
            SYNTAX LogbookMaxEntryNumber
            MAX-ACCESS not-accessible
            STATUS current
            DESCRIPTION
                "This is an increasing number from 1 to maximum. It is used as an index column for SNMP."
            ::= { txA5OutputstageBLogbookEntry 1 }

        
        txA5OstBLogbookEntryNbr OBJECT-TYPE
            SYNTAX LogbookMaxEntryNumber
            MAX-ACCESS read-only
            STATUS current
            DESCRIPTION
                "This is the number of the logbook entry. It is an decreasing number from maximum down to 1."
            ::= { txA5OutputstageBLogbookEntry 2 }

        
        txA5OstBLogbookType OBJECT-TYPE
            SYNTAX EventClass
            MAX-ACCESS read-only
            STATUS current
            DESCRIPTION
                "Can either be Fault, Warning or State."
            ::= { txA5OutputstageBLogbookEntry 3 }

        
        txA5OstBLogbookSlope OBJECT-TYPE
            SYNTAX LogbookEntrySlope
            MAX-ACCESS read-only
            STATUS current
            DESCRIPTION
                "Either set (event raises) or reset (event disappears)"
            ::= { txA5OutputstageBLogbookEntry 4 }

        
        txA5OstBLogbookMessage OBJECT-TYPE
            SYNTAX LogbookEntryMessagesOST
            MAX-ACCESS read-only
            STATUS current
            DESCRIPTION
                "See RS-XX8000-COMMON-MIB - TextualConvention for details."
            ::= { txA5OutputstageBLogbookEntry 5 }

        
        txA5OstBLogbookDateTime OBJECT-TYPE
            SYNTAX DateAndTime
            MAX-ACCESS read-only
            STATUS current
            DESCRIPTION
                "The time of the logbook entry."
            ::= { txA5OutputstageBLogbookEntry 6 }

        
        outputstageATxA5 OBJECT IDENTIFIER ::= { txA5 2 }

        
        txA5OstARackTable OBJECT-TYPE
            SYNTAX SEQUENCE OF TxA5OstARackEntry
            MAX-ACCESS not-accessible
            STATUS current
            DESCRIPTION
                "The table of racks."
            ::= { outputstageATxA5 1 }

        
        txA5OstARackEntry OBJECT-TYPE
            SYNTAX TxA5OstARackEntry
            MAX-ACCESS not-accessible
            STATUS current
            DESCRIPTION
                "A row (an entry) for one rack."
            INDEX { txA5OstARackIdx }
            ::= { txA5OstARackTable 1 }

        
        TxA5OstARackEntry ::=
            SEQUENCE { 
                txA5OstARackIdx
                    IndexRack,
                txA5OstARackInletTemperature
                    FloatingPoint,
                txA5OstARackOutletTemperature
                    FloatingPoint,
                txA5OstARackAuxPowerSupply
                    FloatingPoint
             }

        txA5OstARackIdx OBJECT-TYPE
            SYNTAX IndexRack
            MAX-ACCESS not-accessible
            STATUS current
            DESCRIPTION
                "The rack number (1..10)."
            ::= { txA5OstARackEntry 1 }

        
        txA5OstARackInletTemperature OBJECT-TYPE
            SYNTAX FloatingPoint
            UNITS "Degree Celsius"
            MAX-ACCESS read-only
            STATUS current
            DESCRIPTION
                "The inlet temperature."
            ::= { txA5OstARackEntry 2 }

        
        txA5OstARackOutletTemperature OBJECT-TYPE
            SYNTAX FloatingPoint
            UNITS "Degree Celsius"
            MAX-ACCESS read-only
            STATUS current
            DESCRIPTION
                "The outlet temperature."
            ::= { txA5OstARackEntry 3 }

        
        txA5OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA5OstARackEntry 4 }

        
        exciterTxA5 OBJECT IDENTIFIER ::= { txA5 3 }

        
        txA5ExcInputTable OBJECT-TYPE
            SYNTAX SEQUENCE OF TxA5ExcInputEntry
            MAX-ACCESS not-accessible
            STATUS current
            DESCRIPTION
                "A table for more detailed information about the exciter.
                These values are all read-only. For settings, refer to commandsTxTable."
            ::= { exciterTxA5 1 }

        
        txA5ExcInputEntry OBJECT-TYPE
            SYNTAX TxA5ExcInputEntry
            MAX-ACCESS not-accessible
            STATUS current
            DESCRIPTION
                "An entry for a designated input channel."
            INDEX { txA5ExcInputExcIdx, txA5ExcInputChannelIdx }
            ::= { txA5ExcInputTable 1 }

        
        TxA5ExcInputEntry ::=
            SEQUENCE { 
                txA5ExcInputExcIdx
                    INTEGER,
                txA5ExcInputChannelIdx
                    Integer32,
                txA5ExcInputChannelName
                    INTEGER,
                txA5ExcInputConnected
                    TruthValue,
                txA5ExcInputSeamless
                    TruthValue,
                txA5ExcInputPreselected
                    TruthValue,
                txA5ExcInputActive
                    TruthValue,
                txA5ExcInputMipFail
                    TruthValue,
                txA5ExcInputBandwidth
                    INTEGER,
                txA5ExcInputFFTLength
                    INTEGER,
                txA5ExcInputGuardInterval
                    INTEGER,
                txA5ExcInputConstellation
                    INTEGER,
                txA5ExcInputAlpha
                    INTEGER,
                txA5ExcInputCellID
                    Integer32,
                txA5ExcInputInterleaver
                    INTEGER,
                txA5ExcInputCodeRate
                    INTEGER,
                txA5ExcInputPacketLength
                    Integer32,
                txA5ExcInputMeasuredDatarate
                    Integer32,
                txA5ExcInputRequiredDatarate
                    Integer32,
                txA5ExcInputMaximumDelay
                    Integer32
             }

        txA5ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA5ExcInputEntry 1 }

        
        txA5ExcInputChannelIdx OBJECT-TYPE
            SYNTAX Integer32 (1..6)
            MAX-ACCESS not-accessible
            STATUS current
            DESCRIPTION
                "The index for the different input channels."
            ::= { txA5ExcInputEntry 2 }

        
        txA5ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA5ExcInputEntry 3 }

        
        txA5ExcInputConnected OBJECT-TYPE
            SYNTAX TruthValue
            MAX-ACCESS read-only
            STATUS current
            DESCRIPTION
                "The input channel is connected."
            ::= { txA5ExcInputEntry 4 }

        
        txA5ExcInputSeamless OBJECT-TYPE
            SYNTAX TruthValue
            MAX-ACCESS read-only
            STATUS current
            DESCRIPTION
                "The input channel is in seamless mode."
            ::= { txA5ExcInputEntry 5 }

        
        txA5ExcInputPreselected OBJECT-TYPE
            SYNTAX TruthValue
            MAX-ACCESS read-only
            STATUS current
            DESCRIPTION
                "The input channel is the preselected."
            ::= { txA5ExcInputEntry 6 }

        
        txA5ExcInputActive OBJECT-TYPE
            SYNTAX TruthValue
            MAX-ACCESS read-only
            STATUS current
            DESCRIPTION
                "The input channel is active."
            ::= { txA5ExcInputEntry 7 }

        
        txA5ExcInputMipFail OBJECT-TYPE
            SYNTAX TruthValue
            MAX-ACCESS read-only
            STATUS current
            DESCRIPTION
                "Input channel MIP fail."
            ::= { txA5ExcInputEntry 8 }

        
        txA5ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA5ExcInputEntry 9 }

        
        txA5ExcInputFFTLength OBJECT-TYPE
            SYNTAX INTEGER
                {
                k2(1),
                k8(2),
                k4(3)
                }
            MAX-ACCESS read-only
            STATUS current
            DESCRIPTION
                "The used FFT length (depends on the DVB network)."
            ::= { txA5ExcInputEntry 10 }

        
        txA5ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA5ExcInputEntry 11 }

        
        txA5ExcInputConstellation OBJECT-TYPE
            SYNTAX INTEGER
                {
                qpsk(1),
                qam16(2),
                qam64(3)
                }
            MAX-ACCESS read-only
            STATUS current
            DESCRIPTION
                "This parameter sets the modulation mode."
            ::= { txA5ExcInputEntry 12 }

        
        txA5ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA5ExcInputEntry 13 }

        
        txA5ExcInputCellID OBJECT-TYPE
            SYNTAX Integer32 (0..65535)
            MAX-ACCESS read-only
            STATUS current
            DESCRIPTION
                "Via Cell ID the receiver knows the current network."
            ::= { txA5ExcInputEntry 14 }

        
        txA5ExcInputInterleaver OBJECT-TYPE
            SYNTAX INTEGER
                {
                indepth(1),
                nat(2)
                }
            MAX-ACCESS read-only
            STATUS current
            DESCRIPTION
                "Enables the bit interleaver for hierarchical coding"
            ::= { txA5ExcInputEntry 15 }

        
        txA5ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA5ExcInputEntry 16 }

        
        txA5ExcInputPacketLength OBJECT-TYPE
            SYNTAX Integer32 (188..208)
            MAX-ACCESS read-only
            STATUS current
            DESCRIPTION
                "The Packet length for the channel."
            ::= { txA5ExcInputEntry 17 }

        
        txA5ExcInputMeasuredDatarate OBJECT-TYPE
            SYNTAX Integer32
            MAX-ACCESS read-only
            STATUS current
            DESCRIPTION
                "The measured datarate of the input."
            ::= { txA5ExcInputEntry 18 }

        
        txA5ExcInputRequiredDatarate OBJECT-TYPE
            SYNTAX Integer32
            MAX-ACCESS read-only
            STATUS current
            DESCRIPTION
                "The required datarate of the input."
            ::= { txA5ExcInputEntry 19 }

        
        txA5ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA5ExcInputEntry 20 }

        
        outputstageBTxA5 OBJECT IDENTIFIER ::= { txA5 4 }

        
        txA5OstBRackTable OBJECT-TYPE
            SYNTAX SEQUENCE OF TxA5OstBRackEntry
            MAX-ACCESS not-accessible
            STATUS current
            DESCRIPTION
                "The table of racks for output stage B."
            ::= { outputstageBTxA5 1 }

        
        txA5OstBRackEntry OBJECT-TYPE
            SYNTAX TxA5OstBRackEntry
            MAX-ACCESS not-accessible
            STATUS current
            DESCRIPTION
                "A row (an entry) for one rack."
            INDEX { txA5OstBRackIdx }
            ::= { txA5OstBRackTable 1 }

        
        TxA5OstBRackEntry ::=
            SEQUENCE { 
                txA5OstBRackIdx
                    IndexRack,
                txA5OstBRackInletTemperature
                    FloatingPoint,
                txA5OstBRackOutletTemperature
                    FloatingPoint,
                txA5OstBRackAuxPowerSupply
                    FloatingPoint
             }

        txA5OstBRackIdx OBJECT-TYPE
            SYNTAX IndexRack
            MAX-ACCESS not-accessible
            STATUS current
            DESCRIPTION
                "The rack number (1..10)."
            ::= { txA5OstBRackEntry 1 }

        
        txA5OstBRackInletTemperature OBJECT-TYPE
            SYNTAX FloatingPoint
            UNITS "Degree Celsius"
            MAX-ACCESS read-only
            STATUS current
            DESCRIPTION
                "The inlet temperature."
            ::= { txA5OstBRackEntry 2 }

        
        txA5OstBRackOutletTemperature OBJECT-TYPE
            SYNTAX FloatingPoint
            UNITS "Degree Celsius"
            MAX-ACCESS read-only
            STATUS current
            DESCRIPTION
                "The outlet temperature."
            ::= { txA5OstBRackEntry 3 }

        
        txA5OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA5OstBRackEntry 4 }

        
        txA6 OBJECT IDENTIFIER ::= { transmitter 10 }

        
        logbookTxA6 OBJECT IDENTIFIER ::= { txA6 1 }

        
        txA6NetCCUNumberOfEntries OBJECT-TYPE
            SYNTAX LogbookMaxEntryNumber
            MAX-ACCESS read-only
            STATUS current
            DESCRIPTION
                "The number of entries in logbook."
            ::= { logbookTxA6 1 }

        
        txA6NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 2 }

        
        txA6NetCCULogbookTable OBJECT-TYPE
            SYNTAX SEQUENCE OF TxA6NetCCULogbookEntry
            MAX-ACCESS not-accessible
            STATUS current
            DESCRIPTION
                "NetCCU logbook table."
            ::= { logbookTxA6 3 }

        
        txA6NetCCULogbookEntry OBJECT-TYPE
            SYNTAX TxA6NetCCULogbookEntry
            MAX-ACCESS not-accessible
            STATUS current
            DESCRIPTION
                "This is a entry in the logbook."
            INDEX { txA6NetCCULogbookEntryIdx }
            ::= { txA6NetCCULogbookTable 1 }

        
        TxA6NetCCULogbookEntry ::=
            SEQUENCE { 
                txA6NetCCULogbookEntryIdx
                    LogbookMaxEntryNumber,
                txA6NetCCULogbookEntryNbr
                    LogbookMaxEntryNumber,
                txA6NetCCULogbookType
                    EventClass,
                txA6NetCCULogbookSlope
                    LogbookEntrySlope,
                txA6NetCCULogbookMessage
                    LogbookEntryMessagesNetCCU,
                txA6NetCCULogbookDateTime
                    DateAndTime
             }

        txA6NetCCULogbookEntryIdx OBJECT-TYPE
            SYNTAX LogbookMaxEntryNumber
            MAX-ACCESS not-accessible
            STATUS current
            DESCRIPTION
                "This is an increasing number from 1 to maximum. It is used as an index column for SNMP."
            ::= { txA6NetCCULogbookEntry 1 }

        
        txA6NetCCULogbookEntryNbr OBJECT-TYPE
            SYNTAX LogbookMaxEntryNumber
            MAX-ACCESS read-only
            STATUS current
            DESCRIPTION
                "This is the number of the logbook entry. It is an decreasing number from maximum down to 1."
            ::= { txA6NetCCULogbookEntry 2 }

        
        txA6NetCCULogbookType OBJECT-TYPE
            SYNTAX EventClass
            MAX-ACCESS read-only
            STATUS current
            DESCRIPTION
                "Can either be Fault, Warning or State."
            ::= { txA6NetCCULogbookEntry 3 }

        
        txA6NetCCULogbookSlope OBJECT-TYPE
            SYNTAX LogbookEntrySlope
            MAX-ACCESS read-only
            STATUS current
            DESCRIPTION
                "Either set (event raises) or reset (event disappears)"
            ::= { txA6NetCCULogbookEntry 4 }

        
        txA6NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA6NetCCULogbookEntry 5 }

        
        txA6NetCCULogbookDateTime OBJECT-TYPE
            SYNTAX DateAndTime
            MAX-ACCESS read-only
            STATUS current
            DESCRIPTION
                "The time of the logbook entry."
            ::= { txA6NetCCULogbookEntry 6 }

        
        txA6ExciterANumberOfEntries OBJECT-TYPE
            SYNTAX LogbookMaxEntryNumber
            MAX-ACCESS read-only
            STATUS current
            DESCRIPTION
                "The number of entries in logbook."
            ::= { logbookTxA6 4 }

        
        txA6ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 5 }

        
        txA6ExciterALogbookTable OBJECT-TYPE
            SYNTAX SEQUENCE OF TxA6ExciterALogbookEntry
            MAX-ACCESS not-accessible
            STATUS current
            DESCRIPTION
                "ExciterA logbook table."
            ::= { logbookTxA6 6 }

        
        txA6ExciterALogbookEntry OBJECT-TYPE
            SYNTAX TxA6ExciterALogbookEntry
            MAX-ACCESS not-accessible
            STATUS current
            DESCRIPTION
                "This is a entry in the logbook."
            INDEX { txA6ExcALogbookEntryIdx }
            ::= { txA6ExciterALogbookTable 1 }

        
        TxA6ExciterALogbookEntry ::=
            SEQUENCE { 
                txA6ExcALogbookEntryIdx
                    LogbookMaxEntryNumber,
                txA6ExcALogbookEntryNbr
                    LogbookMaxEntryNumber,
                txA6ExcALogbookType
                    EventClass,
                txA6ExcALogbookSlope
                    LogbookEntrySlope,
                txA6ExcALogbookMessage
                    LogbookEntryMessagesExcTv,
                txA6ExcALogbookDateTime
                    DateAndTime
             }

        txA6ExcALogbookEntryIdx OBJECT-TYPE
            SYNTAX LogbookMaxEntryNumber
            MAX-ACCESS not-accessible
            STATUS current
            DESCRIPTION
                "This is an increasing number from 1 to 128. It is used as an index column for SNMP."
            ::= { txA6ExciterALogbookEntry 1 }

        
        txA6ExcALogbookEntryNbr OBJECT-TYPE
            SYNTAX LogbookMaxEntryNumber
            MAX-ACCESS read-only
            STATUS current
            DESCRIPTION
                "This is the number of the logbook entry. It is an decreasing number from max 128 down to 1."
            ::= { txA6ExciterALogbookEntry 2 }

        
        txA6ExcALogbookType OBJECT-TYPE
            SYNTAX EventClass
            MAX-ACCESS read-only
            STATUS current
            DESCRIPTION
                "Can either be Fault, Warning or State."
            ::= { txA6ExciterALogbookEntry 3 }

        
        txA6ExcALogbookSlope OBJECT-TYPE
            SYNTAX LogbookEntrySlope
            MAX-ACCESS read-only
            STATUS current
            DESCRIPTION
                "Either set (event raises) or reset (event disappears)"
            ::= { txA6ExciterALogbookEntry 4 }

        
        txA6ExcALogbookMessage OBJECT-TYPE
            SYNTAX LogbookEntryMessagesExcTv
            MAX-ACCESS read-only
            STATUS current
            DESCRIPTION
                "See RS-XX8000-COMMON-MIB - TextualConvention for details."
            ::= { txA6ExciterALogbookEntry 5 }

        
        txA6ExcALogbookDateTime OBJECT-TYPE
            SYNTAX DateAndTime
            MAX-ACCESS read-only
            STATUS current
            DESCRIPTION
                "The time of the logbook entry."
            ::= { txA6ExciterALogbookEntry 6 }

        
        txA6OutputstageANumberOfEntries OBJECT-TYPE
            SYNTAX LogbookMaxEntryNumber
            MAX-ACCESS read-only
            STATUS current
            DESCRIPTION
                "The number of entries in logbook."
            ::= { logbookTxA6 7 }

        
        txA6OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 8 }

        
        txA6OutputstageALogbookTable OBJECT-TYPE
            SYNTAX SEQUENCE OF TxA6OutputstageALogbookEntry
            MAX-ACCESS not-accessible
            STATUS current
            DESCRIPTION
                "OutputstageA logbook table."
            ::= { logbookTxA6 9 }

        
        txA6OutputstageALogbookEntry OBJECT-TYPE
            SYNTAX TxA6OutputstageALogbookEntry
            MAX-ACCESS not-accessible
            STATUS current
            DESCRIPTION
                "This is a entry in the logbook."
            INDEX { txA6OstALogbookEntryIdx }
            ::= { txA6OutputstageALogbookTable 1 }

        
        TxA6OutputstageALogbookEntry ::=
            SEQUENCE { 
                txA6OstALogbookEntryIdx
                    LogbookMaxEntryNumber,
                txA6OstALogbookEntryNbr
                    LogbookMaxEntryNumber,
                txA6OstALogbookType
                    EventClass,
                txA6OstALogbookSlope
                    LogbookEntrySlope,
                txA6OstALogbookMessage
                    LogbookEntryMessagesOST,
                txA6OstALogbookDateTime
                    DateAndTime
             }

        txA6OstALogbookEntryIdx OBJECT-TYPE
            SYNTAX LogbookMaxEntryNumber
            MAX-ACCESS not-accessible
            STATUS current
            DESCRIPTION
                "This is an increasing number from 1 to maximum. It is used as an index column for SNMP."
            ::= { txA6OutputstageALogbookEntry 1 }

        
        txA6OstALogbookEntryNbr OBJECT-TYPE
            SYNTAX LogbookMaxEntryNumber
            MAX-ACCESS read-only
            STATUS current
            DESCRIPTION
                "This is the number of the logbook entry. It is an decreasing number from maximum down to 1."
            ::= { txA6OutputstageALogbookEntry 2 }

        
        txA6OstALogbookType OBJECT-TYPE
            SYNTAX EventClass
            MAX-ACCESS read-only
            STATUS current
            DESCRIPTION
                "Can either be Fault, Warning or State."
            ::= { txA6OutputstageALogbookEntry 3 }

        
        txA6OstALogbookSlope OBJECT-TYPE
            SYNTAX LogbookEntrySlope
            MAX-ACCESS read-only
            STATUS current
            DESCRIPTION
                "Either set (event raises) or reset (event disappears)"
            ::= { txA6OutputstageALogbookEntry 4 }

        
        txA6OstALogbookMessage OBJECT-TYPE
            SYNTAX LogbookEntryMessagesOST
            MAX-ACCESS read-only
            STATUS current
            DESCRIPTION
                "See RS-XX8000-COMMON-MIB - TextualConvention for details."
            ::= { txA6OutputstageALogbookEntry 5 }

        
        txA6OstALogbookDateTime OBJECT-TYPE
            SYNTAX DateAndTime
            MAX-ACCESS read-only
            STATUS current
            DESCRIPTION
                "The time of the logbook entry."
            ::= { txA6OutputstageALogbookEntry 6 }

        
        txA6ExciterBNumberOfEntries OBJECT-TYPE
            SYNTAX LogbookMaxEntryNumber
            MAX-ACCESS read-only
            STATUS current
            DESCRIPTION
                "The number of entries in logbook."
            ::= { logbookTxA6 13 }

        
        txA6ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 14 }

        
        txA6ExciterBLogbookTable OBJECT-TYPE
            SYNTAX SEQUENCE OF TxA6ExciterBLogbookEntry
            MAX-ACCESS not-accessible
            STATUS current
            DESCRIPTION
                "ExciterB logbook table."
            ::= { logbookTxA6 15 }

        
        txA6ExciterBLogbookEntry OBJECT-TYPE
            SYNTAX TxA6ExciterBLogbookEntry
            MAX-ACCESS not-accessible
            STATUS current
            DESCRIPTION
                "This is a entry in the logbook."
            INDEX { txA6ExcBLogbookEntryIdx }
            ::= { txA6ExciterBLogbookTable 1 }

        
        TxA6ExciterBLogbookEntry ::=
            SEQUENCE { 
                txA6ExcBLogbookEntryIdx
                    LogbookMaxEntryNumber,
                txA6ExcBLogbookEntryNbr
                    LogbookMaxEntryNumber,
                txA6ExcBLogbookType
                    EventClass,
                txA6ExcBLogbookSlope
                    LogbookEntrySlope,
                txA6ExcBLogbookMessage
                    LogbookEntryMessagesExcTv,
                txA6ExcBLogbookDateTime
                    DateAndTime
             }

        txA6ExcBLogbookEntryIdx OBJECT-TYPE
            SYNTAX LogbookMaxEntryNumber
            MAX-ACCESS not-accessible
            STATUS current
            DESCRIPTION
                "This is an increasing number from 1 to maximum. It is used as an index column for SNMP."
            ::= { txA6ExciterBLogbookEntry 1 }

        
        txA6ExcBLogbookEntryNbr OBJECT-TYPE
            SYNTAX LogbookMaxEntryNumber
            MAX-ACCESS read-only
            STATUS current
            DESCRIPTION
                "This is the number of the logbook entry. It is an decreasing number from maximum down to 1."
            ::= { txA6ExciterBLogbookEntry 2 }

        
        txA6ExcBLogbookType OBJECT-TYPE
            SYNTAX EventClass
            MAX-ACCESS read-only
            STATUS current
            DESCRIPTION
                "Can either be Fault, Warning or State."
            ::= { txA6ExciterBLogbookEntry 3 }

        
        txA6ExcBLogbookSlope OBJECT-TYPE
            SYNTAX LogbookEntrySlope
            MAX-ACCESS read-only
            STATUS current
            DESCRIPTION
                "Either set (event raises) or reset (event disappears)"
            ::= { txA6ExciterBLogbookEntry 4 }

        
        txA6ExcBLogbookMessage OBJECT-TYPE
            SYNTAX LogbookEntryMessagesExcTv
            MAX-ACCESS read-only
            STATUS current
            DESCRIPTION
                "See RS-XX8000-COMMON-MIB - TextualConvention for details."
            ::= { txA6ExciterBLogbookEntry 5 }

        
        txA6ExcBLogbookDateTime OBJECT-TYPE
            SYNTAX DateAndTime
            MAX-ACCESS read-only
            STATUS current
            DESCRIPTION
                "The time of the logbook entry."
            ::= { txA6ExciterBLogbookEntry 6 }

        
        txA6OutputstageBNumberOfEntries OBJECT-TYPE
            SYNTAX LogbookMaxEntryNumber
            MAX-ACCESS read-only
            STATUS current
            DESCRIPTION
                "The number of entries in logbook of output stage B."
            ::= { logbookTxA6 16 }

        
        txA6OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 17 }

        
        txA6OutputstageBLogbookTable OBJECT-TYPE
            SYNTAX SEQUENCE OF TxA6OutputstageBLogbookEntry
            MAX-ACCESS not-accessible
            STATUS current
            DESCRIPTION
                "Output stage B logbook table."
            ::= { logbookTxA6 18 }

        
        txA6OutputstageBLogbookEntry OBJECT-TYPE
            SYNTAX TxA6OutputstageBLogbookEntry
            MAX-ACCESS not-accessible
            STATUS current
            DESCRIPTION
                "This is a entry in the logbook."
            INDEX { txA6OstBLogbookEntryIdx }
            ::= { txA6OutputstageBLogbookTable 1 }

        
        TxA6OutputstageBLogbookEntry ::=
            SEQUENCE { 
                txA6OstBLogbookEntryIdx
                    LogbookMaxEntryNumber,
                txA6OstBLogbookEntryNbr
                    LogbookMaxEntryNumber,
                txA6OstBLogbookType
                    EventClass,
                txA6OstBLogbookSlope
                    LogbookEntrySlope,
                txA6OstBLogbookMessage
                    LogbookEntryMessagesOST,
                txA6OstBLogbookDateTime
                    DateAndTime
             }

        txA6OstBLogbookEntryIdx OBJECT-TYPE
            SYNTAX LogbookMaxEntryNumber
            MAX-ACCESS not-accessible
            STATUS current
            DESCRIPTION
                "This is an increasing number from 1 to maximum. It is used as an index column for SNMP."
            ::= { txA6OutputstageBLogbookEntry 1 }

        
        txA6OstBLogbookEntryNbr OBJECT-TYPE
            SYNTAX LogbookMaxEntryNumber
            MAX-ACCESS read-only
            STATUS current
            DESCRIPTION
                "This is the number of the logbook entry. It is an decreasing number from maximum down to 1."
            ::= { txA6OutputstageBLogbookEntry 2 }

        
        txA6OstBLogbookType OBJECT-TYPE
            SYNTAX EventClass
            MAX-ACCESS read-only
            STATUS current
            DESCRIPTION
                "Can either be Fault, Warning or State."
            ::= { txA6OutputstageBLogbookEntry 3 }

        
        txA6OstBLogbookSlope OBJECT-TYPE
            SYNTAX LogbookEntrySlope
            MAX-ACCESS read-only
            STATUS current
            DESCRIPTION
                "Either set (event raises) or reset (event disappears)"
            ::= { txA6OutputstageBLogbookEntry 4 }

        
        txA6OstBLogbookMessage OBJECT-TYPE
            SYNTAX LogbookEntryMessagesOST
            MAX-ACCESS read-only
            STATUS current
            DESCRIPTION
                "See RS-XX8000-COMMON-MIB - TextualConvention for details."
            ::= { txA6OutputstageBLogbookEntry 5 }

        
        txA6OstBLogbookDateTime OBJECT-TYPE
            SYNTAX DateAndTime
            MAX-ACCESS read-only
            STATUS current
            DESCRIPTION
                "The time of the logbook entry."
            ::= { txA6OutputstageBLogbookEntry 6 }

        
        outputstageATxA6 OBJECT IDENTIFIER ::= { txA6 2 }

        
        txA6OstARackTable OBJECT-TYPE
            SYNTAX SEQUENCE OF TxA6OstARackEntry
            MAX-ACCESS not-accessible
            STATUS current
            DESCRIPTION
                "The table of racks."
            ::= { outputstageATxA6 1 }

        
        txA6OstARackEntry OBJECT-TYPE
            SYNTAX TxA6OstARackEntry
            MAX-ACCESS not-accessible
            STATUS current
            DESCRIPTION
                "A row (an entry) for one rack."
            INDEX { txA6OstARackIdx }
            ::= { txA6OstARackTable 1 }

        
        TxA6OstARackEntry ::=
            SEQUENCE { 
                txA6OstARackIdx
                    IndexRack,
                txA6OstARackInletTemperature
                    FloatingPoint,
                txA6OstARackOutletTemperature
                    FloatingPoint,
                txA6OstARackAuxPowerSupply
                    FloatingPoint
             }

        txA6OstARackIdx OBJECT-TYPE
            SYNTAX IndexRack
            MAX-ACCESS not-accessible
            STATUS current
            DESCRIPTION
                "The rack number (1..10)."
            ::= { txA6OstARackEntry 1 }

        
        txA6OstARackInletTemperature OBJECT-TYPE
            SYNTAX FloatingPoint
            UNITS "Degree Celsius"
            MAX-ACCESS read-only
            STATUS current
            DESCRIPTION
                "The inlet temperature."
            ::= { txA6OstARackEntry 2 }

        
        txA6OstARackOutletTemperature OBJECT-TYPE
            SYNTAX FloatingPoint
            UNITS "Degree Celsius"
            MAX-ACCESS read-only
            STATUS current
            DESCRIPTION
                "The outlet temperature."
            ::= { txA6OstARackEntry 3 }

        
        txA6OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA6OstARackEntry 4 }

        
        exciterTxA6 OBJECT IDENTIFIER ::= { txA6 3 }

        
        txA6ExcInputTable OBJECT-TYPE
            SYNTAX SEQUENCE OF TxA6ExcInputEntry
            MAX-ACCESS not-accessible
            STATUS current
            DESCRIPTION
                "A table for more detailed information about the exciter.
                These values are all read-only. For settings, refer to commandsTxTable."
            ::= { exciterTxA6 1 }

        
        txA6ExcInputEntry OBJECT-TYPE
            SYNTAX TxA6ExcInputEntry
            MAX-ACCESS not-accessible
            STATUS current
            DESCRIPTION
                "An entry for a designated input channel."
            INDEX { txA6ExcInputExcIdx, txA6ExcInputChannelIdx }
            ::= { txA6ExcInputTable 1 }

        
        TxA6ExcInputEntry ::=
            SEQUENCE { 
                txA6ExcInputExcIdx
                    INTEGER,
                txA6ExcInputChannelIdx
                    Integer32,
                txA6ExcInputChannelName
                    INTEGER,
                txA6ExcInputConnected
                    TruthValue,
                txA6ExcInputSeamless
                    TruthValue,
                txA6ExcInputPreselected
                    TruthValue,
                txA6ExcInputActive
                    TruthValue,
                txA6ExcInputMipFail
                    TruthValue,
                txA6ExcInputBandwidth
                    INTEGER,
                txA6ExcInputFFTLength
                    INTEGER,
                txA6ExcInputGuardInterval
                    INTEGER,
                txA6ExcInputConstellation
                    INTEGER,
                txA6ExcInputAlpha
                    INTEGER,
                txA6ExcInputCellID
                    Integer32,
                txA6ExcInputInterleaver
                    INTEGER,
                txA6ExcInputCodeRate
                    INTEGER,
                txA6ExcInputPacketLength
                    Integer32,
                txA6ExcInputMeasuredDatarate
                    Integer32,
                txA6ExcInputRequiredDatarate
                    Integer32,
                txA6ExcInputMaximumDelay
                    Integer32
             }

        txA6ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA6ExcInputEntry 1 }

        
        txA6ExcInputChannelIdx OBJECT-TYPE
            SYNTAX Integer32 (1..6)
            MAX-ACCESS not-accessible
            STATUS current
            DESCRIPTION
                "The index for the different input channels."
            ::= { txA6ExcInputEntry 2 }

        
        txA6ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA6ExcInputEntry 3 }

        
        txA6ExcInputConnected OBJECT-TYPE
            SYNTAX TruthValue
            MAX-ACCESS read-only
            STATUS current
            DESCRIPTION
                "The input channel is connected."
            ::= { txA6ExcInputEntry 4 }

        
        txA6ExcInputSeamless OBJECT-TYPE
            SYNTAX TruthValue
            MAX-ACCESS read-only
            STATUS current
            DESCRIPTION
                "The input channel is in seamless mode."
            ::= { txA6ExcInputEntry 5 }

        
        txA6ExcInputPreselected OBJECT-TYPE
            SYNTAX TruthValue
            MAX-ACCESS read-only
            STATUS current
            DESCRIPTION
                "The input channel is the preselected."
            ::= { txA6ExcInputEntry 6 }

        
        txA6ExcInputActive OBJECT-TYPE
            SYNTAX TruthValue
            MAX-ACCESS read-only
            STATUS current
            DESCRIPTION
                "The input channel is active."
            ::= { txA6ExcInputEntry 7 }

        
        txA6ExcInputMipFail OBJECT-TYPE
            SYNTAX TruthValue
            MAX-ACCESS read-only
            STATUS current
            DESCRIPTION
                "Input channel MIP fail."
            ::= { txA6ExcInputEntry 8 }

        
        txA6ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA6ExcInputEntry 9 }

        
        txA6ExcInputFFTLength OBJECT-TYPE
            SYNTAX INTEGER
                {
                k2(1),
                k8(2),
                k4(3)
                }
            MAX-ACCESS read-only
            STATUS current
            DESCRIPTION
                "The used FFT length (depends on the DVB network)."
            ::= { txA6ExcInputEntry 10 }

        
        txA6ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA6ExcInputEntry 11 }

        
        txA6ExcInputConstellation OBJECT-TYPE
            SYNTAX INTEGER
                {
                qpsk(1),
                qam16(2),
                qam64(3)
                }
            MAX-ACCESS read-only
            STATUS current
            DESCRIPTION
                "This parameter sets the modulation mode."
            ::= { txA6ExcInputEntry 12 }

        
        txA6ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA6ExcInputEntry 13 }

        
        txA6ExcInputCellID OBJECT-TYPE
            SYNTAX Integer32 (0..65535)
            MAX-ACCESS read-only
            STATUS current
            DESCRIPTION
                "Via Cell ID the receiver knows the current network."
            ::= { txA6ExcInputEntry 14 }

        
        txA6ExcInputInterleaver OBJECT-TYPE
            SYNTAX INTEGER
                {
                indepth(1),
                nat(2)
                }
            MAX-ACCESS read-only
            STATUS current
            DESCRIPTION
                "Enables the bit interleaver for hierarchical coding"
            ::= { txA6ExcInputEntry 15 }

        
        txA6ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA6ExcInputEntry 16 }

        
        txA6ExcInputPacketLength OBJECT-TYPE
            SYNTAX Integer32 (188..208)
            MAX-ACCESS read-only
            STATUS current
            DESCRIPTION
                "The Packet length for the channel."
            ::= { txA6ExcInputEntry 17 }

        
        txA6ExcInputMeasuredDatarate OBJECT-TYPE
            SYNTAX Integer32
            MAX-ACCESS read-only
            STATUS current
            DESCRIPTION
                "The measured datarate of the input."
            ::= { txA6ExcInputEntry 18 }

        
        txA6ExcInputRequiredDatarate OBJECT-TYPE
            SYNTAX Integer32
            MAX-ACCESS read-only
            STATUS current
            DESCRIPTION
                "The required datarate of the input."
            ::= { txA6ExcInputEntry 19 }

        
        txA6ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA6ExcInputEntry 20 }

        
        outputstageBTxA6 OBJECT IDENTIFIER ::= { txA6 4 }

        
        txA6OstBRackTable OBJECT-TYPE
            SYNTAX SEQUENCE OF TxA6OstBRackEntry
            MAX-ACCESS not-accessible
            STATUS current
            DESCRIPTION
                "The table of racks for output stage B."
            ::= { outputstageBTxA6 1 }

        
        txA6OstBRackEntry OBJECT-TYPE
            SYNTAX TxA6OstBRackEntry
            MAX-ACCESS not-accessible
            STATUS current
            DESCRIPTION
                "A row (an entry) for one rack."
            INDEX { txA6OstBRackIdx }
            ::= { txA6OstBRackTable 1 }

        
        TxA6OstBRackEntry ::=
            SEQUENCE { 
                txA6OstBRackIdx
                    IndexRack,
                txA6OstBRackInletTemperature
                    FloatingPoint,
                txA6OstBRackOutletTemperature
                    FloatingPoint,
                txA6OstBRackAuxPowerSupply
                    FloatingPoint
             }

        txA6OstBRackIdx OBJECT-TYPE
            SYNTAX IndexRack
            MAX-ACCESS not-accessible
            STATUS current
            DESCRIPTION
                "The rack number (1..10)."
            ::= { txA6OstBRackEntry 1 }

        
        txA6OstBRackInletTemperature OBJECT-TYPE
            SYNTAX FloatingPoint
            UNITS "Degree Celsius"
            MAX-ACCESS read-only
            STATUS current
            DESCRIPTION
                "The inlet temperature."
            ::= { txA6OstBRackEntry 2 }

        
        txA6OstBRackOutletTemperature OBJECT-TYPE
            SYNTAX FloatingPoint
            UNITS "Degree Celsius"
            MAX-ACCESS read-only
            STATUS current
            DESCRIPTION
                "The outlet temperature."
            ::= { txA6OstBRackEntry 3 }

        
        txA6OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA6OstBRackEntry 4 }

        
        txA7 OBJECT IDENTIFIER ::= { transmitter 11 }

        
        logbookTxA7 OBJECT IDENTIFIER ::= { txA7 1 }

        
        txA7NetCCUNumberOfEntries OBJECT-TYPE
            SYNTAX LogbookMaxEntryNumber
            MAX-ACCESS read-only
            STATUS current
            DESCRIPTION
                "The number of entries in logbook."
            ::= { logbookTxA7 1 }

        
        txA7NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 2 }

        
        txA7NetCCULogbookTable OBJECT-TYPE
            SYNTAX SEQUENCE OF TxA7NetCCULogbookEntry
            MAX-ACCESS not-accessible
            STATUS current
            DESCRIPTION
                "NetCCU logbook table."
            ::= { logbookTxA7 3 }

        
        txA7NetCCULogbookEntry OBJECT-TYPE
            SYNTAX TxA7NetCCULogbookEntry
            MAX-ACCESS not-accessible
            STATUS current
            DESCRIPTION
                "This is a entry in the logbook."
            INDEX { txA7NetCCULogbookEntryIdx }
            ::= { txA7NetCCULogbookTable 1 }

        
        TxA7NetCCULogbookEntry ::=
            SEQUENCE { 
                txA7NetCCULogbookEntryIdx
                    LogbookMaxEntryNumber,
                txA7NetCCULogbookEntryNbr
                    LogbookMaxEntryNumber,
                txA7NetCCULogbookType
                    EventClass,
                txA7NetCCULogbookSlope
                    LogbookEntrySlope,
                txA7NetCCULogbookMessage
                    LogbookEntryMessagesNetCCU,
                txA7NetCCULogbookDateTime
                    DateAndTime
             }

        txA7NetCCULogbookEntryIdx OBJECT-TYPE
            SYNTAX LogbookMaxEntryNumber
            MAX-ACCESS not-accessible
            STATUS current
            DESCRIPTION
                "This is an increasing number from 1 to maximum. It is used as an index column for SNMP."
            ::= { txA7NetCCULogbookEntry 1 }

        
        txA7NetCCULogbookEntryNbr OBJECT-TYPE
            SYNTAX LogbookMaxEntryNumber
            MAX-ACCESS read-only
            STATUS current
            DESCRIPTION
                "This is the number of the logbook entry. It is an decreasing number from maximum down to 1."
            ::= { txA7NetCCULogbookEntry 2 }

        
        txA7NetCCULogbookType OBJECT-TYPE
            SYNTAX EventClass
            MAX-ACCESS read-only
            STATUS current
            DESCRIPTION
                "Can either be Fault, Warning or State."
            ::= { txA7NetCCULogbookEntry 3 }

        
        txA7NetCCULogbookSlope OBJECT-TYPE
            SYNTAX LogbookEntrySlope
            MAX-ACCESS read-only
            STATUS current
            DESCRIPTION
                "Either set (event raises) or reset (event disappears)"
            ::= { txA7NetCCULogbookEntry 4 }

        
        txA7NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA7NetCCULogbookEntry 5 }

        
        txA7NetCCULogbookDateTime OBJECT-TYPE
            SYNTAX DateAndTime
            MAX-ACCESS read-only
            STATUS current
            DESCRIPTION
                "The time of the logbook entry."
            ::= { txA7NetCCULogbookEntry 6 }

        
        txA7ExciterANumberOfEntries OBJECT-TYPE
            SYNTAX LogbookMaxEntryNumber
            MAX-ACCESS read-only
            STATUS current
            DESCRIPTION
                "The number of entries in logbook."
            ::= { logbookTxA7 4 }

        
        txA7ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 5 }

        
        txA7ExciterALogbookTable OBJECT-TYPE
            SYNTAX SEQUENCE OF TxA7ExciterALogbookEntry
            MAX-ACCESS not-accessible
            STATUS current
            DESCRIPTION
                "ExciterA logbook table."
            ::= { logbookTxA7 6 }

        
        txA7ExciterALogbookEntry OBJECT-TYPE
            SYNTAX TxA7ExciterALogbookEntry
            MAX-ACCESS not-accessible
            STATUS current
            DESCRIPTION
                "This is a entry in the logbook."
            INDEX { txA7ExcALogbookEntryIdx }
            ::= { txA7ExciterALogbookTable 1 }

        
        TxA7ExciterALogbookEntry ::=
            SEQUENCE { 
                txA7ExcALogbookEntryIdx
                    LogbookMaxEntryNumber,
                txA7ExcALogbookEntryNbr
                    LogbookMaxEntryNumber,
                txA7ExcALogbookType
                    EventClass,
                txA7ExcALogbookSlope
                    LogbookEntrySlope,
                txA7ExcALogbookMessage
                    LogbookEntryMessagesExcTv,
                txA7ExcALogbookDateTime
                    DateAndTime
             }

        txA7ExcALogbookEntryIdx OBJECT-TYPE
            SYNTAX LogbookMaxEntryNumber
            MAX-ACCESS not-accessible
            STATUS current
            DESCRIPTION
                "This is an increasing number from 1 to 128. It is used as an index column for SNMP."
            ::= { txA7ExciterALogbookEntry 1 }

        
        txA7ExcALogbookEntryNbr OBJECT-TYPE
            SYNTAX LogbookMaxEntryNumber
            MAX-ACCESS read-only
            STATUS current
            DESCRIPTION
                "This is the number of the logbook entry. It is an decreasing number from max 128 down to 1."
            ::= { txA7ExciterALogbookEntry 2 }

        
        txA7ExcALogbookType OBJECT-TYPE
            SYNTAX EventClass
            MAX-ACCESS read-only
            STATUS current
            DESCRIPTION
                "Can either be Fault, Warning or State."
            ::= { txA7ExciterALogbookEntry 3 }

        
        txA7ExcALogbookSlope OBJECT-TYPE
            SYNTAX LogbookEntrySlope
            MAX-ACCESS read-only
            STATUS current
            DESCRIPTION
                "Either set (event raises) or reset (event disappears)"
            ::= { txA7ExciterALogbookEntry 4 }

        
        txA7ExcALogbookMessage OBJECT-TYPE
            SYNTAX LogbookEntryMessagesExcTv
            MAX-ACCESS read-only
            STATUS current
            DESCRIPTION
                "See RS-XX8000-COMMON-MIB - TextualConvention for details."
            ::= { txA7ExciterALogbookEntry 5 }

        
        txA7ExcALogbookDateTime OBJECT-TYPE
            SYNTAX DateAndTime
            MAX-ACCESS read-only
            STATUS current
            DESCRIPTION
                "The time of the logbook entry."
            ::= { txA7ExciterALogbookEntry 6 }

        
        txA7OutputstageANumberOfEntries OBJECT-TYPE
            SYNTAX LogbookMaxEntryNumber
            MAX-ACCESS read-only
            STATUS current
            DESCRIPTION
                "The number of entries in logbook."
            ::= { logbookTxA7 7 }

        
        txA7OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 8 }

        
        txA7OutputstageALogbookTable OBJECT-TYPE
            SYNTAX SEQUENCE OF TxA7OutputstageALogbookEntry
            MAX-ACCESS not-accessible
            STATUS current
            DESCRIPTION
                "OutputstageA logbook table."
            ::= { logbookTxA7 9 }

        
        txA7OutputstageALogbookEntry OBJECT-TYPE
            SYNTAX TxA7OutputstageALogbookEntry
            MAX-ACCESS not-accessible
            STATUS current
            DESCRIPTION
                "This is a entry in the logbook."
            INDEX { txA7OstALogbookEntryIdx }
            ::= { txA7OutputstageALogbookTable 1 }

        
        TxA7OutputstageALogbookEntry ::=
            SEQUENCE { 
                txA7OstALogbookEntryIdx
                    LogbookMaxEntryNumber,
                txA7OstALogbookEntryNbr
                    LogbookMaxEntryNumber,
                txA7OstALogbookType
                    EventClass,
                txA7OstALogbookSlope
                    LogbookEntrySlope,
                txA7OstALogbookMessage
                    LogbookEntryMessagesOST,
                txA7OstALogbookDateTime
                    DateAndTime
             }

        txA7OstALogbookEntryIdx OBJECT-TYPE
            SYNTAX LogbookMaxEntryNumber
            MAX-ACCESS not-accessible
            STATUS current
            DESCRIPTION
                "This is an increasing number from 1 to maximum. It is used as an index column for SNMP."
            ::= { txA7OutputstageALogbookEntry 1 }

        
        txA7OstALogbookEntryNbr OBJECT-TYPE
            SYNTAX LogbookMaxEntryNumber
            MAX-ACCESS read-only
            STATUS current
            DESCRIPTION
                "This is the number of the logbook entry. It is an decreasing number from maximum down to 1."
            ::= { txA7OutputstageALogbookEntry 2 }

        
        txA7OstALogbookType OBJECT-TYPE
            SYNTAX EventClass
            MAX-ACCESS read-only
            STATUS current
            DESCRIPTION
                "Can either be Fault, Warning or State."
            ::= { txA7OutputstageALogbookEntry 3 }

        
        txA7OstALogbookSlope OBJECT-TYPE
            SYNTAX LogbookEntrySlope
            MAX-ACCESS read-only
            STATUS current
            DESCRIPTION
                "Either set (event raises) or reset (event disappears)"
            ::= { txA7OutputstageALogbookEntry 4 }

        
        txA7OstALogbookMessage OBJECT-TYPE
            SYNTAX LogbookEntryMessagesOST
            MAX-ACCESS read-only
            STATUS current
            DESCRIPTION
                "See RS-XX8000-COMMON-MIB - TextualConvention for details."
            ::= { txA7OutputstageALogbookEntry 5 }

        
        txA7OstALogbookDateTime OBJECT-TYPE
            SYNTAX DateAndTime
            MAX-ACCESS read-only
            STATUS current
            DESCRIPTION
                "The time of the logbook entry."
            ::= { txA7OutputstageALogbookEntry 6 }

        
        txA7ExciterBNumberOfEntries OBJECT-TYPE
            SYNTAX LogbookMaxEntryNumber
            MAX-ACCESS read-only
            STATUS current
            DESCRIPTION
                "The number of entries in logbook."
            ::= { logbookTxA7 13 }

        
        txA7ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 14 }

        
        txA7ExciterBLogbookTable OBJECT-TYPE
            SYNTAX SEQUENCE OF TxA7ExciterBLogbookEntry
            MAX-ACCESS not-accessible
            STATUS current
            DESCRIPTION
                "ExciterB logbook table."
            ::= { logbookTxA7 15 }

        
        txA7ExciterBLogbookEntry OBJECT-TYPE
            SYNTAX TxA7ExciterBLogbookEntry
            MAX-ACCESS not-accessible
            STATUS current
            DESCRIPTION
                "This is a entry in the logbook."
            INDEX { txA7ExcBLogbookEntryIdx }
            ::= { txA7ExciterBLogbookTable 1 }

        
        TxA7ExciterBLogbookEntry ::=
            SEQUENCE { 
                txA7ExcBLogbookEntryIdx
                    LogbookMaxEntryNumber,
                txA7ExcBLogbookEntryNbr
                    LogbookMaxEntryNumber,
                txA7ExcBLogbookType
                    EventClass,
                txA7ExcBLogbookSlope
                    LogbookEntrySlope,
                txA7ExcBLogbookMessage
                    LogbookEntryMessagesExcTv,
                txA7ExcBLogbookDateTime
                    DateAndTime
             }

        txA7ExcBLogbookEntryIdx OBJECT-TYPE
            SYNTAX LogbookMaxEntryNumber
            MAX-ACCESS not-accessible
            STATUS current
            DESCRIPTION
                "This is an increasing number from 1 to maximum. It is used as an index column for SNMP."
            ::= { txA7ExciterBLogbookEntry 1 }

        
        txA7ExcBLogbookEntryNbr OBJECT-TYPE
            SYNTAX LogbookMaxEntryNumber
            MAX-ACCESS read-only
            STATUS current
            DESCRIPTION
                "This is the number of the logbook entry. It is an decreasing number from maximum down to 1."
            ::= { txA7ExciterBLogbookEntry 2 }

        
        txA7ExcBLogbookType OBJECT-TYPE
            SYNTAX EventClass
            MAX-ACCESS read-only
            STATUS current
            DESCRIPTION
                "Can either be Fault, Warning or State."
            ::= { txA7ExciterBLogbookEntry 3 }

        
        txA7ExcBLogbookSlope OBJECT-TYPE
            SYNTAX LogbookEntrySlope
            MAX-ACCESS read-only
            STATUS current
            DESCRIPTION
                "Either set (event raises) or reset (event disappears)"
            ::= { txA7ExciterBLogbookEntry 4 }

        
        txA7ExcBLogbookMessage OBJECT-TYPE
            SYNTAX LogbookEntryMessagesExcTv
            MAX-ACCESS read-only
            STATUS current
            DESCRIPTION
                "See RS-XX8000-COMMON-MIB - TextualConvention for details."
            ::= { txA7ExciterBLogbookEntry 5 }

        
        txA7ExcBLogbookDateTime OBJECT-TYPE
            SYNTAX DateAndTime
            MAX-ACCESS read-only
            STATUS current
            DESCRIPTION
                "The time of the logbook entry."
            ::= { txA7ExciterBLogbookEntry 6 }

        
        txA7OutputstageBNumberOfEntries OBJECT-TYPE
            SYNTAX LogbookMaxEntryNumber
            MAX-ACCESS read-only
            STATUS current
            DESCRIPTION
                "The number of entries in logbook of output stage B."
            ::= { logbookTxA7 16 }

        
        txA7OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 17 }

        
        txA7OutputstageBLogbookTable OBJECT-TYPE
            SYNTAX SEQUENCE OF TxA7OutputstageBLogbookEntry
            MAX-ACCESS not-accessible
            STATUS current
            DESCRIPTION
                "Output stage B logbook table."
            ::= { logbookTxA7 18 }

        
        txA7OutputstageBLogbookEntry OBJECT-TYPE
            SYNTAX TxA7OutputstageBLogbookEntry
            MAX-ACCESS not-accessible
            STATUS current
            DESCRIPTION
                "This is a entry in the logbook."
            INDEX { txA7OstBLogbookEntryIdx }
            ::= { txA7OutputstageBLogbookTable 1 }

        
        TxA7OutputstageBLogbookEntry ::=
            SEQUENCE { 
                txA7OstBLogbookEntryIdx
                    LogbookMaxEntryNumber,
                txA7OstBLogbookEntryNbr
                    LogbookMaxEntryNumber,
                txA7OstBLogbookType
                    EventClass,
                txA7OstBLogbookSlope
                    LogbookEntrySlope,
                txA7OstBLogbookMessage
                    LogbookEntryMessagesOST,
                txA7OstBLogbookDateTime
                    DateAndTime
             }

        txA7OstBLogbookEntryIdx OBJECT-TYPE
            SYNTAX LogbookMaxEntryNumber
            MAX-ACCESS not-accessible
            STATUS current
            DESCRIPTION
                "This is an increasing number from 1 to maximum. It is used as an index column for SNMP."
            ::= { txA7OutputstageBLogbookEntry 1 }

        
        txA7OstBLogbookEntryNbr OBJECT-TYPE
            SYNTAX LogbookMaxEntryNumber
            MAX-ACCESS read-only
            STATUS current
            DESCRIPTION
                "This is the number of the logbook entry. It is an decreasing number from maximum down to 1."
            ::= { txA7OutputstageBLogbookEntry 2 }

        
        txA7OstBLogbookType OBJECT-TYPE
            SYNTAX EventClass
            MAX-ACCESS read-only
            STATUS current
            DESCRIPTION
                "Can either be Fault, Warning or State."
            ::= { txA7OutputstageBLogbookEntry 3 }

        
        txA7OstBLogbookSlope OBJECT-TYPE
            SYNTAX LogbookEntrySlope
            MAX-ACCESS read-only
            STATUS current
            DESCRIPTION
                "Either set (event raises) or reset (event disappears)"
            ::= { txA7OutputstageBLogbookEntry 4 }

        
        txA7OstBLogbookMessage OBJECT-TYPE
            SYNTAX LogbookEntryMessagesOST
            MAX-ACCESS read-only
            STATUS current
            DESCRIPTION
                "See RS-XX8000-COMMON-MIB - TextualConvention for details."
            ::= { txA7OutputstageBLogbookEntry 5 }

        
        txA7OstBLogbookDateTime OBJECT-TYPE
            SYNTAX DateAndTime
            MAX-ACCESS read-only
            STATUS current
            DESCRIPTION
                "The time of the logbook entry."
            ::= { txA7OutputstageBLogbookEntry 6 }

        
        outputstageATxA7 OBJECT IDENTIFIER ::= { txA7 2 }

        
        txA7OstARackTable OBJECT-TYPE
            SYNTAX SEQUENCE OF TxA7OstARackEntry
            MAX-ACCESS not-accessible
            STATUS current
            DESCRIPTION
                "The table of racks."
            ::= { outputstageATxA7 1 }

        
        txA7OstARackEntry OBJECT-TYPE
            SYNTAX TxA7OstARackEntry
            MAX-ACCESS not-accessible
            STATUS current
            DESCRIPTION
                "A row (an entry) for one rack."
            INDEX { txA7OstARackIdx }
            ::= { txA7OstARackTable 1 }

        
        TxA7OstARackEntry ::=
            SEQUENCE { 
                txA7OstARackIdx
                    IndexRack,
                txA7OstARackInletTemperature
                    FloatingPoint,
                txA7OstARackOutletTemperature
                    FloatingPoint,
                txA7OstARackAuxPowerSupply
                    FloatingPoint
             }

        txA7OstARackIdx OBJECT-TYPE
            SYNTAX IndexRack
            MAX-ACCESS not-accessible
            STATUS current
            DESCRIPTION
                "The rack number (1..10)."
            ::= { txA7OstARackEntry 1 }

        
        txA7OstARackInletTemperature OBJECT-TYPE
            SYNTAX FloatingPoint
            UNITS "Degree Celsius"
            MAX-ACCESS read-only
            STATUS current
            DESCRIPTION
                "The inlet temperature."
            ::= { txA7OstARackEntry 2 }

        
        txA7OstARackOutletTemperature OBJECT-TYPE
            SYNTAX FloatingPoint
            UNITS "Degree Celsius"
            MAX-ACCESS read-only
            STATUS current
            DESCRIPTION
                "The outlet temperature."
            ::= { txA7OstARackEntry 3 }

        
        txA7OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA7OstARackEntry 4 }

        
        exciterTxA7 OBJECT IDENTIFIER ::= { txA7 3 }

        
        txA7ExcInputTable OBJECT-TYPE
            SYNTAX SEQUENCE OF TxA7ExcInputEntry
            MAX-ACCESS not-accessible
            STATUS current
            DESCRIPTION
                "A table for more detailed information about the exciter.
                These values are all read-only. For settings, refer to commandsTxTable."
            ::= { exciterTxA7 1 }

        
        txA7ExcInputEntry OBJECT-TYPE
            SYNTAX TxA7ExcInputEntry
            MAX-ACCESS not-accessible
            STATUS current
            DESCRIPTION
                "An entry for a designated input channel."
            INDEX { txA7ExcInputExcIdx, txA7ExcInputChannelIdx }
            ::= { txA7ExcInputTable 1 }

        
        TxA7ExcInputEntry ::=
            SEQUENCE { 
                txA7ExcInputExcIdx
                    INTEGER,
                txA7ExcInputChannelIdx
                    Integer32,
                txA7ExcInputChannelName
                    INTEGER,
                txA7ExcInputConnected
                    TruthValue,
                txA7ExcInputSeamless
                    TruthValue,
                txA7ExcInputPreselected
                    TruthValue,
                txA7ExcInputActive
                    TruthValue,
                txA7ExcInputMipFail
                    TruthValue,
                txA7ExcInputBandwidth
                    INTEGER,
                txA7ExcInputFFTLength
                    INTEGER,
                txA7ExcInputGuardInterval
                    INTEGER,
                txA7ExcInputConstellation
                    INTEGER,
                txA7ExcInputAlpha
                    INTEGER,
                txA7ExcInputCellID
                    Integer32,
                txA7ExcInputInterleaver
                    INTEGER,
                txA7ExcInputCodeRate
                    INTEGER,
                txA7ExcInputPacketLength
                    Integer32,
                txA7ExcInputMeasuredDatarate
                    Integer32,
                txA7ExcInputRequiredDatarate
                    Integer32,
                txA7ExcInputMaximumDelay
                    Integer32
             }

        txA7ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA7ExcInputEntry 1 }

        
        txA7ExcInputChannelIdx OBJECT-TYPE
            SYNTAX Integer32 (1..6)
            MAX-ACCESS not-accessible
            STATUS current
            DESCRIPTION
                "The index for the different input channels."
            ::= { txA7ExcInputEntry 2 }

        
        txA7ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA7ExcInputEntry 3 }

        
        txA7ExcInputConnected OBJECT-TYPE
            SYNTAX TruthValue
            MAX-ACCESS read-only
            STATUS current
            DESCRIPTION
                "The input channel is connected."
            ::= { txA7ExcInputEntry 4 }

        
        txA7ExcInputSeamless OBJECT-TYPE
            SYNTAX TruthValue
            MAX-ACCESS read-only
            STATUS current
            DESCRIPTION
                "The input channel is in seamless mode."
            ::= { txA7ExcInputEntry 5 }

        
        txA7ExcInputPreselected OBJECT-TYPE
            SYNTAX TruthValue
            MAX-ACCESS read-only
            STATUS current
            DESCRIPTION
                "The input channel is the preselected."
            ::= { txA7ExcInputEntry 6 }

        
        txA7ExcInputActive OBJECT-TYPE
            SYNTAX TruthValue
            MAX-ACCESS read-only
            STATUS current
            DESCRIPTION
                "The input channel is active."
            ::= { txA7ExcInputEntry 7 }

        
        txA7ExcInputMipFail OBJECT-TYPE
            SYNTAX TruthValue
            MAX-ACCESS read-only
            STATUS current
            DESCRIPTION
                "Input channel MIP fail."
            ::= { txA7ExcInputEntry 8 }

        
        txA7ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA7ExcInputEntry 9 }

        
        txA7ExcInputFFTLength OBJECT-TYPE
            SYNTAX INTEGER
                {
                k2(1),
                k8(2),
                k4(3)
                }
            MAX-ACCESS read-only
            STATUS current
            DESCRIPTION
                "The used FFT length (depends on the DVB network)."
            ::= { txA7ExcInputEntry 10 }

        
        txA7ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA7ExcInputEntry 11 }

        
        txA7ExcInputConstellation OBJECT-TYPE
            SYNTAX INTEGER
                {
                qpsk(1),
                qam16(2),
                qam64(3)
                }
            MAX-ACCESS read-only
            STATUS current
            DESCRIPTION
                "This parameter sets the modulation mode."
            ::= { txA7ExcInputEntry 12 }

        
        txA7ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA7ExcInputEntry 13 }

        
        txA7ExcInputCellID OBJECT-TYPE
            SYNTAX Integer32 (0..65535)
            MAX-ACCESS read-only
            STATUS current
            DESCRIPTION
                "Via Cell ID the receiver knows the current network."
            ::= { txA7ExcInputEntry 14 }

        
        txA7ExcInputInterleaver OBJECT-TYPE
            SYNTAX INTEGER
                {
                indepth(1),
                nat(2)
                }
            MAX-ACCESS read-only
            STATUS current
            DESCRIPTION
                "Enables the bit interleaver for hierarchical coding"
            ::= { txA7ExcInputEntry 15 }

        
        txA7ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA7ExcInputEntry 16 }

        
        txA7ExcInputPacketLength OBJECT-TYPE
            SYNTAX Integer32 (188..208)
            MAX-ACCESS read-only
            STATUS current
            DESCRIPTION
                "The Packet length for the channel."
            ::= { txA7ExcInputEntry 17 }

        
        txA7ExcInputMeasuredDatarate OBJECT-TYPE
            SYNTAX Integer32
            MAX-ACCESS read-only
            STATUS current
            DESCRIPTION
                "The measured datarate of the input."
            ::= { txA7ExcInputEntry 18 }

        
        txA7ExcInputRequiredDatarate OBJECT-TYPE
            SYNTAX Integer32
            MAX-ACCESS read-only
            STATUS current
            DESCRIPTION
                "The required datarate of the input."
            ::= { txA7ExcInputEntry 19 }

        
        txA7ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA7ExcInputEntry 20 }

        
        outputstageBTxA7 OBJECT IDENTIFIER ::= { txA7 4 }

        
        txA7OstBRackTable OBJECT-TYPE
            SYNTAX SEQUENCE OF TxA7OstBRackEntry
            MAX-ACCESS not-accessible
            STATUS current
            DESCRIPTION
                "The table of racks for output stage B."
            ::= { outputstageBTxA7 1 }

        
        txA7OstBRackEntry OBJECT-TYPE
            SYNTAX TxA7OstBRackEntry
            MAX-ACCESS not-accessible
            STATUS current
            DESCRIPTION
                "A row (an entry) for one rack."
            INDEX { txA7OstBRackIdx }
            ::= { txA7OstBRackTable 1 }

        
        TxA7OstBRackEntry ::=
            SEQUENCE { 
                txA7OstBRackIdx
                    IndexRack,
                txA7OstBRackInletTemperature
                    FloatingPoint,
                txA7OstBRackOutletTemperature
                    FloatingPoint,
                txA7OstBRackAuxPowerSupply
                    FloatingPoint
             }

        txA7OstBRackIdx OBJECT-TYPE
            SYNTAX IndexRack
            MAX-ACCESS not-accessible
            STATUS current
            DESCRIPTION
                "The rack number (1..10)."
            ::= { txA7OstBRackEntry 1 }

        
        txA7OstBRackInletTemperature OBJECT-TYPE
            SYNTAX FloatingPoint
            UNITS "Degree Celsius"
            MAX-ACCESS read-only
            STATUS current
            DESCRIPTION
                "The inlet temperature."
            ::= { txA7OstBRackEntry 2 }

        
        txA7OstBRackOutletTemperature OBJECT-TYPE
            SYNTAX FloatingPoint
            UNITS "Degree Celsius"
            MAX-ACCESS read-only
            STATUS current
            DESCRIPTION
                "The outlet temperature."
            ::= { txA7OstBRackEntry 3 }

        
        txA7OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA7OstBRackEntry 4 }

        
        txA8 OBJECT IDENTIFIER ::= { transmitter 12 }

        
        logbookTxA8 OBJECT IDENTIFIER ::= { txA8 1 }

        
        txA8NetCCUNumberOfEntries OBJECT-TYPE
            SYNTAX LogbookMaxEntryNumber
            MAX-ACCESS read-only
            STATUS current
            DESCRIPTION
                "The number of entries in logbook."
            ::= { logbookTxA8 1 }

        
        txA8NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 2 }

        
        txA8NetCCULogbookTable OBJECT-TYPE
            SYNTAX SEQUENCE OF TxA8NetCCULogbookEntry
            MAX-ACCESS not-accessible
            STATUS current
            DESCRIPTION
                "NetCCU logbook table."
            ::= { logbookTxA8 3 }

        
        txA8NetCCULogbookEntry OBJECT-TYPE
            SYNTAX TxA8NetCCULogbookEntry
            MAX-ACCESS not-accessible
            STATUS current
            DESCRIPTION
                "This is a entry in the logbook."
            INDEX { txA8NetCCULogbookEntryIdx }
            ::= { txA8NetCCULogbookTable 1 }

        
        TxA8NetCCULogbookEntry ::=
            SEQUENCE { 
                txA8NetCCULogbookEntryIdx
                    LogbookMaxEntryNumber,
                txA8NetCCULogbookEntryNbr
                    LogbookMaxEntryNumber,
                txA8NetCCULogbookType
                    EventClass,
                txA8NetCCULogbookSlope
                    LogbookEntrySlope,
                txA8NetCCULogbookMessage
                    LogbookEntryMessagesNetCCU,
                txA8NetCCULogbookDateTime
                    DateAndTime
             }

        txA8NetCCULogbookEntryIdx OBJECT-TYPE
            SYNTAX LogbookMaxEntryNumber
            MAX-ACCESS not-accessible
            STATUS current
            DESCRIPTION
                "This is an increasing number from 1 to maximum. It is used as an index column for SNMP."
            ::= { txA8NetCCULogbookEntry 1 }

        
        txA8NetCCULogbookEntryNbr OBJECT-TYPE
            SYNTAX LogbookMaxEntryNumber
            MAX-ACCESS read-only
            STATUS current
            DESCRIPTION
                "This is the number of the logbook entry. It is an decreasing number from maximum down to 1."
            ::= { txA8NetCCULogbookEntry 2 }

        
        txA8NetCCULogbookType OBJECT-TYPE
            SYNTAX EventClass
            MAX-ACCESS read-only
            STATUS current
            DESCRIPTION
                "Can either be Fault, Warning or State."
            ::= { txA8NetCCULogbookEntry 3 }

        
        txA8NetCCULogbookSlope OBJECT-TYPE
            SYNTAX LogbookEntrySlope
            MAX-ACCESS read-only
            STATUS current
            DESCRIPTION
                "Either set (event raises) or reset (event disappears)"
            ::= { txA8NetCCULogbookEntry 4 }

        
        txA8NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA8NetCCULogbookEntry 5 }

        
        txA8NetCCULogbookDateTime OBJECT-TYPE
            SYNTAX DateAndTime
            MAX-ACCESS read-only
            STATUS current
            DESCRIPTION
                "The time of the logbook entry."
            ::= { txA8NetCCULogbookEntry 6 }

        
        txA8ExciterANumberOfEntries OBJECT-TYPE
            SYNTAX LogbookMaxEntryNumber
            MAX-ACCESS read-only
            STATUS current
            DESCRIPTION
                "The number of entries in logbook."
            ::= { logbookTxA8 4 }

        
        txA8ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 5 }

        
        txA8ExciterALogbookTable OBJECT-TYPE
            SYNTAX SEQUENCE OF TxA8ExciterALogbookEntry
            MAX-ACCESS not-accessible
            STATUS current
            DESCRIPTION
                "ExciterA logbook table."
            ::= { logbookTxA8 6 }

        
        txA8ExciterALogbookEntry OBJECT-TYPE
            SYNTAX TxA8ExciterALogbookEntry
            MAX-ACCESS not-accessible
            STATUS current
            DESCRIPTION
                "This is a entry in the logbook."
            INDEX { txA8ExcALogbookEntryIdx }
            ::= { txA8ExciterALogbookTable 1 }

        
        TxA8ExciterALogbookEntry ::=
            SEQUENCE { 
                txA8ExcALogbookEntryIdx
                    LogbookMaxEntryNumber,
                txA8ExcALogbookEntryNbr
                    LogbookMaxEntryNumber,
                txA8ExcALogbookType
                    EventClass,
                txA8ExcALogbookSlope
                    LogbookEntrySlope,
                txA8ExcALogbookMessage
                    LogbookEntryMessagesExcTv,
                txA8ExcALogbookDateTime
                    DateAndTime
             }

        txA8ExcALogbookEntryIdx OBJECT-TYPE
            SYNTAX LogbookMaxEntryNumber
            MAX-ACCESS not-accessible
            STATUS current
            DESCRIPTION
                "This is an increasing number from 1 to 128. It is used as an index column for SNMP."
            ::= { txA8ExciterALogbookEntry 1 }

        
        txA8ExcALogbookEntryNbr OBJECT-TYPE
            SYNTAX LogbookMaxEntryNumber
            MAX-ACCESS read-only
            STATUS current
            DESCRIPTION
                "This is the number of the logbook entry. It is an decreasing number from max 128 down to 1."
            ::= { txA8ExciterALogbookEntry 2 }

        
        txA8ExcALogbookType OBJECT-TYPE
            SYNTAX EventClass
            MAX-ACCESS read-only
            STATUS current
            DESCRIPTION
                "Can either be Fault, Warning or State."
            ::= { txA8ExciterALogbookEntry 3 }

        
        txA8ExcALogbookSlope OBJECT-TYPE
            SYNTAX LogbookEntrySlope
            MAX-ACCESS read-only
            STATUS current
            DESCRIPTION
                "Either set (event raises) or reset (event disappears)"
            ::= { txA8ExciterALogbookEntry 4 }

        
        txA8ExcALogbookMessage OBJECT-TYPE
            SYNTAX LogbookEntryMessagesExcTv
            MAX-ACCESS read-only
            STATUS current
            DESCRIPTION
                "See RS-XX8000-COMMON-MIB - TextualConvention for details."
            ::= { txA8ExciterALogbookEntry 5 }

        
        txA8ExcALogbookDateTime OBJECT-TYPE
            SYNTAX DateAndTime
            MAX-ACCESS read-only
            STATUS current
            DESCRIPTION
                "The time of the logbook entry."
            ::= { txA8ExciterALogbookEntry 6 }

        
        txA8OutputstageANumberOfEntries OBJECT-TYPE
            SYNTAX LogbookMaxEntryNumber
            MAX-ACCESS read-only
            STATUS current
            DESCRIPTION
                "The number of entries in logbook."
            ::= { logbookTxA8 7 }

        
        txA8OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 8 }

        
        txA8OutputstageALogbookTable OBJECT-TYPE
            SYNTAX SEQUENCE OF TxA8OutputstageALogbookEntry
            MAX-ACCESS not-accessible
            STATUS current
            DESCRIPTION
                "OutputstageA logbook table."
            ::= { logbookTxA8 9 }

        
        txA8OutputstageALogbookEntry OBJECT-TYPE
            SYNTAX TxA8OutputstageALogbookEntry
            MAX-ACCESS not-accessible
            STATUS current
            DESCRIPTION
                "This is a entry in the logbook."
            INDEX { txA8OstALogbookEntryIdx }
            ::= { txA8OutputstageALogbookTable 1 }

        
        TxA8OutputstageALogbookEntry ::=
            SEQUENCE { 
                txA8OstALogbookEntryIdx
                    LogbookMaxEntryNumber,
                txA8OstALogbookEntryNbr
                    LogbookMaxEntryNumber,
                txA8OstALogbookType
                    EventClass,
                txA8OstALogbookSlope
                    LogbookEntrySlope,
                txA8OstALogbookMessage
                    LogbookEntryMessagesOST,
                txA8OstALogbookDateTime
                    DateAndTime
             }

        txA8OstALogbookEntryIdx OBJECT-TYPE
            SYNTAX LogbookMaxEntryNumber
            MAX-ACCESS not-accessible
            STATUS current
            DESCRIPTION
                "This is an increasing number from 1 to maximum. It is used as an index column for SNMP."
            ::= { txA8OutputstageALogbookEntry 1 }

        
        txA8OstALogbookEntryNbr OBJECT-TYPE
            SYNTAX LogbookMaxEntryNumber
            MAX-ACCESS read-only
            STATUS current
            DESCRIPTION
                "This is the number of the logbook entry. It is an decreasing number from maximum down to 1."
            ::= { txA8OutputstageALogbookEntry 2 }

        
        txA8OstALogbookType OBJECT-TYPE
            SYNTAX EventClass
            MAX-ACCESS read-only
            STATUS current
            DESCRIPTION
                "Can either be Fault, Warning or State."
            ::= { txA8OutputstageALogbookEntry 3 }

        
        txA8OstALogbookSlope OBJECT-TYPE
            SYNTAX LogbookEntrySlope
            MAX-ACCESS read-only
            STATUS current
            DESCRIPTION
                "Either set (event raises) or reset (event disappears)"
            ::= { txA8OutputstageALogbookEntry 4 }

        
        txA8OstALogbookMessage OBJECT-TYPE
            SYNTAX LogbookEntryMessagesOST
            MAX-ACCESS read-only
            STATUS current
            DESCRIPTION
                "See RS-XX8000-COMMON-MIB - TextualConvention for details."
            ::= { txA8OutputstageALogbookEntry 5 }

        
        txA8OstALogbookDateTime OBJECT-TYPE
            SYNTAX DateAndTime
            MAX-ACCESS read-only
            STATUS current
            DESCRIPTION
                "The time of the logbook entry."
            ::= { txA8OutputstageALogbookEntry 6 }

        
        txA8ExciterBNumberOfEntries OBJECT-TYPE
            SYNTAX LogbookMaxEntryNumber
            MAX-ACCESS read-only
            STATUS current
            DESCRIPTION
                "The number of entries in logbook."
            ::= { logbookTxA8 13 }

        
        txA8ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 14 }

        
        txA8ExciterBLogbookTable OBJECT-TYPE
            SYNTAX SEQUENCE OF TxA8ExciterBLogbookEntry
            MAX-ACCESS not-accessible
            STATUS current
            DESCRIPTION
                "ExciterB logbook table."
            ::= { logbookTxA8 15 }

        
        txA8ExciterBLogbookEntry OBJECT-TYPE
            SYNTAX TxA8ExciterBLogbookEntry
            MAX-ACCESS not-accessible
            STATUS current
            DESCRIPTION
                "This is a entry in the logbook."
            INDEX { txA8ExcBLogbookEntryIdx }
            ::= { txA8ExciterBLogbookTable 1 }

        
        TxA8ExciterBLogbookEntry ::=
            SEQUENCE { 
                txA8ExcBLogbookEntryIdx
                    LogbookMaxEntryNumber,
                txA8ExcBLogbookEntryNbr
                    LogbookMaxEntryNumber,
                txA8ExcBLogbookType
                    EventClass,
                txA8ExcBLogbookSlope
                    LogbookEntrySlope,
                txA8ExcBLogbookMessage
                    LogbookEntryMessagesExcTv,
                txA8ExcBLogbookDateTime
                    DateAndTime
             }

        txA8ExcBLogbookEntryIdx OBJECT-TYPE
            SYNTAX LogbookMaxEntryNumber
            MAX-ACCESS not-accessible
            STATUS current
            DESCRIPTION
                "This is an increasing number from 1 to maximum. It is used as an index column for SNMP."
            ::= { txA8ExciterBLogbookEntry 1 }

        
        txA8ExcBLogbookEntryNbr OBJECT-TYPE
            SYNTAX LogbookMaxEntryNumber
            MAX-ACCESS read-only
            STATUS current
            DESCRIPTION
                "This is the number of the logbook entry. It is an decreasing number from maximum down to 1."
            ::= { txA8ExciterBLogbookEntry 2 }

        
        txA8ExcBLogbookType OBJECT-TYPE
            SYNTAX EventClass
            MAX-ACCESS read-only
            STATUS current
            DESCRIPTION
                "Can either be Fault, Warning or State."
            ::= { txA8ExciterBLogbookEntry 3 }

        
        txA8ExcBLogbookSlope OBJECT-TYPE
            SYNTAX LogbookEntrySlope
            MAX-ACCESS read-only
            STATUS current
            DESCRIPTION
                "Either set (event raises) or reset (event disappears)"
            ::= { txA8ExciterBLogbookEntry 4 }

        
        txA8ExcBLogbookMessage OBJECT-TYPE
            SYNTAX LogbookEntryMessagesExcTv
            MAX-ACCESS read-only
            STATUS current
            DESCRIPTION
                "See RS-XX8000-COMMON-MIB - TextualConvention for details."
            ::= { txA8ExciterBLogbookEntry 5 }

        
        txA8ExcBLogbookDateTime OBJECT-TYPE
            SYNTAX DateAndTime
            MAX-ACCESS read-only
            STATUS current
            DESCRIPTION
                "The time of the logbook entry."
            ::= { txA8ExciterBLogbookEntry 6 }

        
        txA8OutputstageBNumberOfEntries OBJECT-TYPE
            SYNTAX LogbookMaxEntryNumber
            MAX-ACCESS read-only
            STATUS current
            DESCRIPTION
                "The number of entries in logbook of output stage B."
            ::= { logbookTxA8 16 }

        
        txA8OutputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 17 }

        
        txA8OutputstageBLogbookTable OBJECT-TYPE
            SYNTAX SEQUENCE OF TxA8OutputstageBLogbookEntry
            MAX-ACCESS not-accessible
            STATUS current
            DESCRIPTION
                "Output stage B logbook table."
            ::= { logbookTxA8 18 }

        
        txA8OutputstageBLogbookEntry OBJECT-TYPE
            SYNTAX TxA8OutputstageBLogbookEntry
            MAX-ACCESS not-accessible
            STATUS current
            DESCRIPTION
                "This is a entry in the logbook."
            INDEX { txA8OstBLogbookEntryIdx }
            ::= { txA8OutputstageBLogbookTable 1 }

        
        TxA8OutputstageBLogbookEntry ::=
            SEQUENCE { 
                txA8OstBLogbookEntryIdx
                    LogbookMaxEntryNumber,
                txA8OstBLogbookEntryNbr
                    LogbookMaxEntryNumber,
                txA8OstBLogbookType
                    EventClass,
                txA8OstBLogbookSlope
                    LogbookEntrySlope,
                txA8OstBLogbookMessage
                    LogbookEntryMessagesOST,
                txA8OstBLogbookDateTime
                    DateAndTime
             }

        txA8OstBLogbookEntryIdx OBJECT-TYPE
            SYNTAX LogbookMaxEntryNumber
            MAX-ACCESS not-accessible
            STATUS current
            DESCRIPTION
                "This is an increasing number from 1 to maximum. It is used as an index column for SNMP."
            ::= { txA8OutputstageBLogbookEntry 1 }

        
        txA8OstBLogbookEntryNbr OBJECT-TYPE
            SYNTAX LogbookMaxEntryNumber
            MAX-ACCESS read-only
            STATUS current
            DESCRIPTION
                "This is the number of the logbook entry. It is an decreasing number from maximum down to 1."
            ::= { txA8OutputstageBLogbookEntry 2 }

        
        txA8OstBLogbookType OBJECT-TYPE
            SYNTAX EventClass
            MAX-ACCESS read-only
            STATUS current
            DESCRIPTION
                "Can either be Fault, Warning or State."
            ::= { txA8OutputstageBLogbookEntry 3 }

        
        txA8OstBLogbookSlope OBJECT-TYPE
            SYNTAX LogbookEntrySlope
            MAX-ACCESS read-only
            STATUS current
            DESCRIPTION
                "Either set (event raises) or reset (event disappears)"
            ::= { txA8OutputstageBLogbookEntry 4 }

        
        txA8OstBLogbookMessage OBJECT-TYPE
            SYNTAX LogbookEntryMessagesOST
            MAX-ACCESS read-only
            STATUS current
            DESCRIPTION
                "See RS-XX8000-COMMON-MIB - TextualConvention for details."
            ::= { txA8OutputstageBLogbookEntry 5 }

        
        txA8OstBLogbookDateTime OBJECT-TYPE
            SYNTAX DateAndTime
            MAX-ACCESS read-only
            STATUS current
            DESCRIPTION
                "The time of the logbook entry."
            ::= { txA8OutputstageBLogbookEntry 6 }

        
        outputstageATxA8 OBJECT IDENTIFIER ::= { txA8 2 }

        
        txA8OstARackTable OBJECT-TYPE
            SYNTAX SEQUENCE OF TxA8OstARackEntry
            MAX-ACCESS not-accessible
            STATUS current
            DESCRIPTION
                "The table of racks."
            ::= { outputstageATxA8 1 }

        
        txA8OstARackEntry OBJECT-TYPE
            SYNTAX TxA8OstARackEntry
            MAX-ACCESS not-accessible
            STATUS current
            DESCRIPTION
                "A row (an entry) for one rack."
            INDEX { txA8OstARackIdx }
            ::= { txA8OstARackTable 1 }

        
        TxA8OstARackEntry ::=
            SEQUENCE { 
                txA8OstARackIdx
                    IndexRack,
                txA8OstARackInletTemperature
                    FloatingPoint,
                txA8OstARackOutletTemperature
                    FloatingPoint,
                txA8OstARackAuxPowerSupply
                    FloatingPoint
             }

        txA8OstARackIdx OBJECT-TYPE
            SYNTAX IndexRack
            MAX-ACCESS not-accessible
            STATUS current
            DESCRIPTION
                "The rack number (1..10)."
            ::= { txA8OstARackEntry 1 }

        
        txA8OstARackInletTemperature OBJECT-TYPE
            SYNTAX FloatingPoint
            UNITS "Degree Celsius"
            MAX-ACCESS read-only
            STATUS current
            DESCRIPTION
                "The inlet temperature."
            ::= { txA8OstARackEntry 2 }

        
        txA8OstARackOutletTemperature OBJECT-TYPE
            SYNTAX FloatingPoint
            UNITS "Degree Celsius"
            MAX-ACCESS read-only
            STATUS current
            DESCRIPTION
                "The outlet temperature."
            ::= { txA8OstARackEntry 3 }

        
        txA8OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA8OstARackEntry 4 }

        
        exciterTxA8 OBJECT IDENTIFIER ::= { txA8 3 }

        
        txA8ExcInputTable OBJECT-TYPE
            SYNTAX SEQUENCE OF TxA8ExcInputEntry
            MAX-ACCESS not-accessible
            STATUS current
            DESCRIPTION
                "A table for more detailed information about the exciter.
                These values are all read-only. For settings, refer to commandsTxTable."
            ::= { exciterTxA8 1 }

        
        txA8ExcInputEntry OBJECT-TYPE
            SYNTAX TxA8ExcInputEntry
            MAX-ACCESS not-accessible
            STATUS current
            DESCRIPTION
                "An entry for a designated input channel."
            INDEX { txA8ExcInputExcIdx, txA8ExcInputChannelIdx }
            ::= { txA8ExcInputTable 1 }

        
        TxA8ExcInputEntry ::=
            SEQUENCE { 
                txA8ExcInputExcIdx
                    INTEGER,
                txA8ExcInputChannelIdx
                    Integer32,
                txA8ExcInputChannelName
                    INTEGER,
                txA8ExcInputConnected
                    TruthValue,
                txA8ExcInputSeamless
                    TruthValue,
                txA8ExcInputPreselected
                    TruthValue,
                txA8ExcInputActive
                    TruthValue,
                txA8ExcInputMipFail
                    TruthValue,
                txA8ExcInputBandwidth
                    INTEGER,
                txA8ExcInputFFTLength
                    INTEGER,
                txA8ExcInputGuardInterval
                    INTEGER,
                txA8ExcInputConstellation
                    INTEGER,
                txA8ExcInputAlpha
                    INTEGER,
                txA8ExcInputCellID
                    Integer32,
                txA8ExcInputInterleaver
                    INTEGER,
                txA8ExcInputCodeRate
                    INTEGER,
                txA8ExcInputPacketLength
                    Integer32,
                txA8ExcInputMeasuredDatarate
                    Integer32,
                txA8ExcInputRequiredDatarate
                    Integer32,
                txA8ExcInputMaximumDelay
                    Integer32
             }

        txA8ExcInputExcIdx OBJECT-TYPE
            SYNTAX INTEGER
                {
                exciterA(1),
                exciterB(2)
                }
            MAX-ACCESS not-accessible
            STATUS current
            DESCRIPTION
                "The index for exciterA (and exciterB if there are DualDrive systems)."
            ::= { txA8ExcInputEntry 1 }

        
        txA8ExcInputChannelIdx OBJECT-TYPE
            SYNTAX Integer32 (1..6)
            MAX-ACCESS not-accessible
            STATUS current
            DESCRIPTION
                "The index for the different input channels."
            ::= { txA8ExcInputEntry 2 }

        
        txA8ExcInputChannelName OBJECT-TYPE
            SYNTAX INTEGER
                {
                hp1(1),
                hp2(2),
                lp1(3),
                lp2(4),
                activeHP(5),
                activeLP(6)
                }
            MAX-ACCESS read-only
            STATUS current
            DESCRIPTION
                "This is the logical name for the index for the different input channels."
            ::= { txA8ExcInputEntry 3 }

        
        txA8ExcInputConnected OBJECT-TYPE
            SYNTAX TruthValue
            MAX-ACCESS read-only
            STATUS current
            DESCRIPTION
                "The input channel is connected."
            ::= { txA8ExcInputEntry 4 }

        
        txA8ExcInputSeamless OBJECT-TYPE
            SYNTAX TruthValue
            MAX-ACCESS read-only
            STATUS current
            DESCRIPTION
                "The input channel is in seamless mode."
            ::= { txA8ExcInputEntry 5 }

        
        txA8ExcInputPreselected OBJECT-TYPE
            SYNTAX TruthValue
            MAX-ACCESS read-only
            STATUS current
            DESCRIPTION
                "The input channel is the preselected."
            ::= { txA8ExcInputEntry 6 }

        
        txA8ExcInputActive OBJECT-TYPE
            SYNTAX TruthValue
            MAX-ACCESS read-only
            STATUS current
            DESCRIPTION
                "The input channel is active."
            ::= { txA8ExcInputEntry 7 }

        
        txA8ExcInputMipFail OBJECT-TYPE
            SYNTAX TruthValue
            MAX-ACCESS read-only
            STATUS current
            DESCRIPTION
                "Input channel MIP fail."
            ::= { txA8ExcInputEntry 8 }

        
        txA8ExcInputBandwidth OBJECT-TYPE
            SYNTAX INTEGER
                {
                mhz5(1),
                mhz6(2),
                mhz7(3),
                mhz8(4)
                }
            MAX-ACCESS read-only
            STATUS current
            DESCRIPTION
                "The bandwidth used by the input channel."
            ::= { txA8ExcInputEntry 9 }

        
        txA8ExcInputFFTLength OBJECT-TYPE
            SYNTAX INTEGER
                {
                k2(1),
                k8(2),
                k4(3)
                }
            MAX-ACCESS read-only
            STATUS current
            DESCRIPTION
                "The used FFT length (depends on the DVB network)."
            ::= { txA8ExcInputEntry 10 }

        
        txA8ExcInputGuardInterval OBJECT-TYPE
            SYNTAX INTEGER
                {
                oneOf32(1),
                oneOf16(2),
                oneOf8(3),
                oneOf4(4)
                }
            MAX-ACCESS read-only
            STATUS current
            DESCRIPTION
                "The Guard interval affects the error correction in multipath receiving situations.
                A long Guard Interval reduces the amount of payload data."
            ::= { txA8ExcInputEntry 11 }

        
        txA8ExcInputConstellation OBJECT-TYPE
            SYNTAX INTEGER
                {
                qpsk(1),
                qam16(2),
                qam64(3)
                }
            MAX-ACCESS read-only
            STATUS current
            DESCRIPTION
                "This parameter sets the modulation mode."
            ::= { txA8ExcInputEntry 12 }

        
        txA8ExcInputAlpha OBJECT-TYPE
            SYNTAX INTEGER
                {
                noHierarchy(1),
                one(2),
                two(3),
                four(4)
                }
            MAX-ACCESS read-only
            STATUS obsolete
            DESCRIPTION
                "An alpha greater than zero enables the hierarchical coding mode.
                obsoleted - always returns noHierarchy(1)"
            ::= { txA8ExcInputEntry 13 }

        
        txA8ExcInputCellID OBJECT-TYPE
            SYNTAX Integer32 (0..65535)
            MAX-ACCESS read-only
            STATUS current
            DESCRIPTION
                "Via Cell ID the receiver knows the current network."
            ::= { txA8ExcInputEntry 14 }

        
        txA8ExcInputInterleaver OBJECT-TYPE
            SYNTAX INTEGER
                {
                indepth(1),
                nat(2)
                }
            MAX-ACCESS read-only
            STATUS current
            DESCRIPTION
                "Enables the bit interleaver for hierarchical coding"
            ::= { txA8ExcInputEntry 15 }

        
        txA8ExcInputCodeRate OBJECT-TYPE
            SYNTAX INTEGER
                {
                oneOf2(1),
                twoOf3(2),
                threeOf4(3),
                fiveOf6(4),
                sevenOf8(5)
                }
            MAX-ACCESS read-only
            STATUS current
            DESCRIPTION
                "Coderate can be set separately for HP and LP channel."
            ::= { txA8ExcInputEntry 16 }

        
        txA8ExcInputPacketLength OBJECT-TYPE
            SYNTAX Integer32 (188..208)
            MAX-ACCESS read-only
            STATUS current
            DESCRIPTION
                "The Packet length for the channel."
            ::= { txA8ExcInputEntry 17 }

        
        txA8ExcInputMeasuredDatarate OBJECT-TYPE
            SYNTAX Integer32
            MAX-ACCESS read-only
            STATUS current
            DESCRIPTION
                "The measured datarate of the input."
            ::= { txA8ExcInputEntry 18 }

        
        txA8ExcInputRequiredDatarate OBJECT-TYPE
            SYNTAX Integer32
            MAX-ACCESS read-only
            STATUS current
            DESCRIPTION
                "The required datarate of the input."
            ::= { txA8ExcInputEntry 19 }

        
        txA8ExcInputMaximumDelay OBJECT-TYPE
            SYNTAX Integer32 (0..100000000)
            UNITS "Nanoseconds"
            MAX-ACCESS read-only
            STATUS current
            DESCRIPTION
                "Period of time between the signal leaving the play-out center (MIP inserter) and
                its regular transmission at the antenna.
                This delay is set in the MIP inserter and serves as a basis for all the transmitters in the SFN."
            ::= { txA8ExcInputEntry 20 }

        
        outputstageBTxA8 OBJECT IDENTIFIER ::= { txA8 4 }

        
        txA8OstBRackTable OBJECT-TYPE
            SYNTAX SEQUENCE OF TxA8OstBRackEntry
            MAX-ACCESS not-accessible
            STATUS current
            DESCRIPTION
                "The table of racks for output stage B."
            ::= { outputstageBTxA8 1 }

        
        txA8OstBRackEntry OBJECT-TYPE
            SYNTAX TxA8OstBRackEntry
            MAX-ACCESS not-accessible
            STATUS current
            DESCRIPTION
                "A row (an entry) for one rack."
            INDEX { txA8OstBRackIdx }
            ::= { txA8OstBRackTable 1 }

        
        TxA8OstBRackEntry ::=
            SEQUENCE { 
                txA8OstBRackIdx
                    IndexRack,
                txA8OstBRackInletTemperature
                    FloatingPoint,
                txA8OstBRackOutletTemperature
                    FloatingPoint,
                txA8OstBRackAuxPowerSupply
                    FloatingPoint
             }

        txA8OstBRackIdx OBJECT-TYPE
            SYNTAX IndexRack
            MAX-ACCESS not-accessible
            STATUS current
            DESCRIPTION
                "The rack number (1..10)."
            ::= { txA8OstBRackEntry 1 }

        
        txA8OstBRackInletTemperature OBJECT-TYPE
            SYNTAX FloatingPoint
            UNITS "Degree Celsius"
            MAX-ACCESS read-only
            STATUS current
            DESCRIPTION
                "The inlet temperature."
            ::= { txA8OstBRackEntry 2 }

        
        txA8OstBRackOutletTemperature OBJECT-TYPE
            SYNTAX FloatingPoint
            UNITS "Degree Celsius"
            MAX-ACCESS read-only
            STATUS current
            DESCRIPTION
                "The outlet temperature."
            ::= { txA8OstBRackEntry 3 }

        
        txA8OstBRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA8OstBRackEntry 4 }

        
        exciterStatusTable OBJECT-TYPE
            SYNTAX SEQUENCE OF ExciterStatusEntry
            MAX-ACCESS not-accessible
            STATUS current
            DESCRIPTION
                "Exciter status values."
            ::= { transmitter 20 }

        
        exciterStatusEntry OBJECT-TYPE
            SYNTAX ExciterStatusEntry
            MAX-ACCESS not-accessible
            STATUS current
            DESCRIPTION
                "A row (an entry) for one exciter."
            INDEX { excStatusTxIdx, excStatusExcIdx }
            ::= { exciterStatusTable 1 }

        
        ExciterStatusEntry ::=
            SEQUENCE { 
                excStatusTxIdx
                    IndexTransmitter,
                excStatusTxName
                    IndexTransmitter,
                excStatusExcIdx
                    IndexAB,
                excStatusRfOutputAgcRegulation
                    FloatingPoint,
                excStatusRfIqAdjustAuto
                    INTEGER,
                excStatusRfIqAdjustLO1Frequency
                    FloatingPoint,
                excStatusNominalPower
                    Integer32,
                excStatusVSWR
                    FloatingPoint,
                excStatusSfnDelayProcessing
                    FloatingPoint,
                excStatusSfnDelayDynamic
                    FloatingPoint,
                excStatusSfnDelayNetwork
                    FloatingPoint,
                excStatusSfnDelayTxOffset
                    FloatingPoint,
                excStatusSfnDelayMaximum
                    FloatingPoint,
                excStatusSfnDelayTotal
                    FloatingPoint,
                excStatusAmplifierControl
                    INTEGER,
                excStatusReqDataRateHP
                    Integer32,
                excStatusReqDataRateLP
                    Integer32,
                excStatusFailDelay
                    FailDelayStatus
             }

        excStatusTxIdx OBJECT-TYPE
            SYNTAX IndexTransmitter
            MAX-ACCESS not-accessible
            STATUS current
            DESCRIPTION
                "The transmitter index. There are max. 8 transmitters, if you have an 8+1 system."
            ::= { exciterStatusEntry 1 }

        
        excStatusTxName OBJECT-TYPE
            SYNTAX IndexTransmitter
            MAX-ACCESS read-only
            STATUS current
            DESCRIPTION
                "This is the logical name for the transmitters."
            ::= { exciterStatusEntry 2 }

        
        excStatusExcIdx OBJECT-TYPE
            SYNTAX IndexAB
            MAX-ACCESS not-accessible
            STATUS current
            DESCRIPTION
                "The dedicated exciter (A/B)."
            ::= { exciterStatusEntry 3 }

        
        excStatusRfOutputAgcRegulation OBJECT-TYPE
            SYNTAX FloatingPoint
            UNITS "Percent"
            MAX-ACCESS read-only
            STATUS current
            DESCRIPTION
                "Shows the operating point of the RF regulator. The shown value should be around 50 per cent."
            ::= { exciterStatusEntry 4 }

        
        excStatusRfIqAdjustAuto OBJECT-TYPE
            SYNTAX INTEGER
                {
                notAdjusted(1),
                inProgress(2),
                adjusted(3)
                }
            UNITS "Percent"
            MAX-ACCESS read-only
            STATUS current
            DESCRIPTION
                "Automatic I/Q-Adjust."
            ::= { exciterStatusEntry 5 }

        
        excStatusRfIqAdjustLO1Frequency OBJECT-TYPE
            SYNTAX FloatingPoint
            UNITS "MHz"
            MAX-ACCESS read-only
            STATUS current
            DESCRIPTION
                "Modulator LO1."
            ::= { exciterStatusEntry 6 }

        
        excStatusNominalPower OBJECT-TYPE
            SYNTAX Integer32
            UNITS "W"
            MAX-ACCESS read-write
            STATUS current
            DESCRIPTION
                "Description."
            ::= { exciterStatusEntry 7 }

        
        excStatusVSWR OBJECT-TYPE
            SYNTAX FloatingPoint
            MAX-ACCESS read-only
            STATUS current
            DESCRIPTION
                "Voltage Standing Wave Ratio"
            ::= { exciterStatusEntry 9 }

        
        excStatusSfnDelayProcessing OBJECT-TYPE
            SYNTAX FloatingPoint
            UNITS "Microseconds"
            MAX-ACCESS read-only
            STATUS current
            DESCRIPTION
                "The Minimum signal transmit time through the exciter.
                This delay depends on the DVB transmission parameters."
            ::= { exciterStatusEntry 13 }

        
        excStatusSfnDelayDynamic OBJECT-TYPE
            SYNTAX FloatingPoint
            UNITS "Microseconds"
            MAX-ACCESS read-only
            STATUS current
            DESCRIPTION
                "The period of time by which signal processing is artificially delayed
                so that the desired time of transmission is obtained."
            ::= { exciterStatusEntry 14 }

        
        excStatusSfnDelayNetwork OBJECT-TYPE
            SYNTAX FloatingPoint
            UNITS "Microseconds"
            MAX-ACCESS read-only
            STATUS current
            DESCRIPTION
                "The signal propagation time between the play-out center
                (MIP inserter) and the exciter input. This delay depends
                on the transmission path used."
            ::= { exciterStatusEntry 15 }

        
        excStatusSfnDelayTxOffset OBJECT-TYPE
            SYNTAX FloatingPoint
            UNITS "Microseconds"
            MAX-ACCESS read-only
            STATUS current
            DESCRIPTION
                "An individual transmitter specific delay. It can be adjusted
                via data carousel of the SFN adapter. It is true for a
                specific transmitter address."
            ::= { exciterStatusEntry 16 }

        
        excStatusSfnDelayMaximum OBJECT-TYPE
            SYNTAX FloatingPoint
            UNITS "Microseconds"
            MAX-ACCESS read-only
            STATUS current
            DESCRIPTION
                "The period of time between the signal leaving the play-out center
                (MIP inserter) and its regular transmission at the antenna.
                This delay is set in the MIP inserter and serves as a basis for
                all the transmitters in the SFN."
            ::= { exciterStatusEntry 17 }

        
        excStatusSfnDelayTotal OBJECT-TYPE
            SYNTAX FloatingPoint
            UNITS "Microseconds"
            MAX-ACCESS read-only
            STATUS current
            DESCRIPTION
                "The actual signal transit time through the exciter.
                This is derived from the sum of static-, dynamic-, 
                offset- and processing delay."
            ::= { exciterStatusEntry 18 }

        
        excStatusAmplifierControl OBJECT-TYPE
            SYNTAX INTEGER
                {
                on(1),
                off(2)
                }
            MAX-ACCESS read-only
            STATUS current
            DESCRIPTION
                "Amplifier control status"
            ::= { exciterStatusEntry 20 }

        
        excStatusReqDataRateHP OBJECT-TYPE
            SYNTAX Integer32
            UNITS "bit per seconds"
            MAX-ACCESS read-only
            STATUS current
            DESCRIPTION
                "Required data rate on HP input
                with respect to the current TPS settings."
            ::= { exciterStatusEntry 21 }

        
        excStatusReqDataRateLP OBJECT-TYPE
            SYNTAX Integer32
            UNITS "bit per seconds"
            MAX-ACCESS read-only
            STATUS current
            DESCRIPTION
                "Required data rate on LP input
                with respect to the current TPS settings."
            ::= { exciterStatusEntry 22 }

        
        excStatusFailDelay OBJECT-TYPE
            SYNTAX FailDelayStatus
            MAX-ACCESS read-only
            STATUS current
            DESCRIPTION
                "Shows whether the fail delay time is qualified."
            ::= { exciterStatusEntry 40 }

        
        exciterPrecorrectionTable OBJECT-TYPE
            SYNTAX SEQUENCE OF ExciterPrecorrectionEntry
            MAX-ACCESS not-accessible
            STATUS current
            DESCRIPTION
                "Exciter status values."
            ::= { transmitter 21 }

        
        exciterPrecorrectionEntry OBJECT-TYPE
            SYNTAX ExciterPrecorrectionEntry
            MAX-ACCESS not-accessible
            STATUS current
            DESCRIPTION
                "A row (an entry) for one exciter."
            INDEX { excPrecTxIdx, excPrecExcIdx }
            ::= { exciterPrecorrectionTable 1 }

        
        ExciterPrecorrectionEntry ::=
            SEQUENCE { 
                excPrecTxIdx
                    IndexTransmitter,
                excPrecTxName
                    IndexTransmitter,
                excPrecExcIdx
                    IndexAB,
                excPrecLinCorrection
                    SwitchOnOff,
                excPrecLinAutomaticADE
                    INTEGER,
                excPrecLinMaxAmplitudeRipple
                    FloatingPoint,
                excPrecLinMaxGroupDelayRipple
                    Integer32,
                excPrecLinAmplitudeRipple
                    FloatingPoint,
                excPrecLinGroupDelayRipple
                    Integer32,
                excPrecLinInputLevel
                    INTEGER,
                excPrecLinAutomatic
                    INTEGER,
                excPrecNonlinCorrection
                    SwitchOnOff,
                excPrecNonlinAutomaticADE
                    INTEGER,
                excPrecNonlinThresholdShoulders
                    FloatingPoint,
                excPrecNonlinShoulderLeft
                    FloatingPoint,
                excPrecNonlinShoulderRight
                    FloatingPoint,
                excPrecNonlinInputLevel
                    INTEGER,
                excPrecNonlinAutomatic
                    INTEGER
             }

        excPrecTxIdx OBJECT-TYPE
            SYNTAX IndexTransmitter
            MAX-ACCESS not-accessible
            STATUS current
            DESCRIPTION
                "The transmitter index. There are max. 8 transmitters, if you have an 8+1 system."
            ::= { exciterPrecorrectionEntry 1 }

        
        excPrecTxName OBJECT-TYPE
            SYNTAX IndexTransmitter
            MAX-ACCESS read-only
            STATUS current
            DESCRIPTION
                "This is the logical name for the transmitters."
            ::= { exciterPrecorrectionEntry 2 }

        
        excPrecExcIdx OBJECT-TYPE
            SYNTAX IndexAB
            MAX-ACCESS not-accessible
            STATUS current
            DESCRIPTION
                "The dedicated exciter (A/B)."
            ::= { exciterPrecorrectionEntry 3 }

        
        excPrecLinCorrection OBJECT-TYPE
            SYNTAX SwitchOnOff
            MAX-ACCESS read-write
            STATUS current
            DESCRIPTION
                "Switches on/turns off the linear precorrector."
            ::= { exciterPrecorrectionEntry 4 }

        
        excPrecLinAutomaticADE OBJECT-TYPE
            SYNTAX INTEGER
                {
                manual(1),
                automatic(2),
                adaptive(3)
                }
            MAX-ACCESS read-write
            STATUS current
            DESCRIPTION
                "Enables /disables the automatic precorrector. To get the ADE in work linear precorrection has to be switched on."
            ::= { exciterPrecorrectionEntry 5 }

        
        excPrecLinMaxAmplitudeRipple OBJECT-TYPE
            SYNTAX FloatingPoint
            UNITS "dB"
            MAX-ACCESS read-write
            STATUS current
            DESCRIPTION
                "Sets te maximum ripple for automatic amplitude correction (0.0 ... 2.0)."
            ::= { exciterPrecorrectionEntry 6 }

        
        excPrecLinMaxGroupDelayRipple OBJECT-TYPE
            SYNTAX Integer32 (0..500)
            UNITS "Nanoseconds"
            MAX-ACCESS read-write
            STATUS current
            DESCRIPTION
                "Sets the maximum ripple for automatic group delay correction."
            ::= { exciterPrecorrectionEntry 7 }

        
        excPrecLinAmplitudeRipple OBJECT-TYPE
            SYNTAX FloatingPoint
            UNITS "dB"
            MAX-ACCESS read-only
            STATUS current
            DESCRIPTION
                "Shows the current amplitude ripple."
            ::= { exciterPrecorrectionEntry 8 }

        
        excPrecLinGroupDelayRipple OBJECT-TYPE
            SYNTAX Integer32
            UNITS "Nanoseconds"
            MAX-ACCESS read-only
            STATUS current
            DESCRIPTION
                "Shows the current group delay ripple."
            ::= { exciterPrecorrectionEntry 9 }

        
        excPrecLinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { exciterPrecorrectionEntry 10 }

        
        excPrecLinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 11 }

        
        excPrecNonlinCorrection OBJECT-TYPE
            SYNTAX SwitchOnOff
            MAX-ACCESS read-write
            STATUS current
            DESCRIPTION
                "Switches on/turns off the nonlinear precorrector."
            ::= { exciterPrecorrectionEntry 12 }

        
        excPrecNonlinAutomaticADE OBJECT-TYPE
            SYNTAX INTEGER
                {
                manual(1),
                automatic(2),
                adaptive(3)
                }
            MAX-ACCESS read-write
            STATUS current
            DESCRIPTION
                "Enables /disables the automatic precorrector. To get the ADE in work nonlinear precorrection has to be switched on."
            ::= { exciterPrecorrectionEntry 13 }

        
        excPrecNonlinThresholdShoulders OBJECT-TYPE
            SYNTAX FloatingPoint
            UNITS "dB"
            MAX-ACCESS read-write
            STATUS current
            DESCRIPTION
                "The target shoulder distance for ADE (0.0 ... 40.0)."
            ::= { exciterPrecorrectionEntry 14 }

        
        excPrecNonlinShoulderLeft OBJECT-TYPE
            SYNTAX FloatingPoint
            UNITS "dB"
            MAX-ACCESS read-only
            STATUS current
            DESCRIPTION
                "Displays the current measurement for the left handed shoulder distance."
            ::= { exciterPrecorrectionEntry 15 }

        
        excPrecNonlinShoulderRight OBJECT-TYPE
            SYNTAX FloatingPoint
            UNITS "dB"
            MAX-ACCESS read-only
            STATUS current
            DESCRIPTION
                "Displays the current measurement of the right handed shoulder."
            ::= { exciterPrecorrectionEntry 16 }

        
        excPrecNonlinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { exciterPrecorrectionEntry 17 }

        
        excPrecNonlinAutomatic OBJECT-TYPE
            SYNTAX INTEGER
                {
                disabled(1),
                active(2),
                calculate(3),
                measure(4)
                }
            MAX-ACCESS read-only
            STATUS current
            DESCRIPTION
                "Shows if the automatic precorrector works properly."
            ::= { exciterPrecorrectionEntry 18 }

        
        rfProbesTable OBJECT-TYPE
            SYNTAX SEQUENCE OF RfProbesEntry
            MAX-ACCESS not-accessible
            STATUS current
            DESCRIPTION
                "This table contains all commands for the RF probes."
            ::= { transmitter 24 }

        
        rfProbesEntry OBJECT-TYPE
            SYNTAX RfProbesEntry
            MAX-ACCESS not-accessible
            STATUS current
            DESCRIPTION
                "An entry for a designated transmitter and device."
            INDEX { rfProbesTxIdx }
            ::= { rfProbesTable 1 }

        
        RfProbesEntry ::=
            SEQUENCE { 
                rfProbesNetCCURfProbe1
                    FloatingPoint,
                rfProbesNetCCURfProbe2
                    FloatingPoint,
                rfProbesAntFwdNominal
                    FloatingPoint,
                rfProbesAntFwdWarningLimit
                    FloatingPoint,
                rfProbesAntFwdFailLimit
                    FloatingPoint,
                rfProbesAntFwdDelayTimeRfFail
                    Integer32,
                rfProbesAntFwdSetOffset
                    Trigger,
                rfProbesAntFwdSetGain
                    Trigger,
                rfProbesAntReflWarningLimit
                    FloatingPoint,
                rfProbesAntReflSetOffset
                    Trigger,
                rfProbesAntReflSetGain
                    Trigger,
                rfProbesDLFwdNominal
                    FloatingPoint,
                rfProbesDLFwdWarningLimit
                    FloatingPoint,
                rfProbesDLFwdFailLimit
                    FloatingPoint,
                rfProbesDLFwdDelayTimeRfFail
                    Integer32,
                rfProbesDLFwdSetOffset
                    Trigger,
                rfProbesDLFwdSetGain
                    Trigger,
                rfProbesDLReflWarningLimit
                    FloatingPoint,
                rfProbesDLReflSetOffset
                    Trigger,
                rfProbesDLReflSetGain
                    Trigger,
                rfProbesTxIdx
                    IndexTransmitter
             }

        rfProbesNetCCURfProbe1 OBJECT-TYPE
            SYNTAX FloatingPoint
            UNITS "Volt"
            MAX-ACCESS read-only
            STATUS current
            DESCRIPTION
                "Current voltage on RF Probe 1."
            ::= { rfProbesEntry 1 }

        
        rfProbesNetCCURfProbe2 OBJECT-TYPE
            SYNTAX FloatingPoint
            UNITS "Volt"
            MAX-ACCESS read-only
            STATUS current
            DESCRIPTION
                "Current voltage on RF Probe 2."
            ::= { rfProbesEntry 2 }

        
        rfProbesAntFwdNominal OBJECT-TYPE
            SYNTAX FloatingPoint
            UNITS "Watt"
            MAX-ACCESS read-write
            STATUS current
            DESCRIPTION
                "This sets the nominal value [W] of the transmitter (to antenna)."
            ::= { rfProbesEntry 3 }

        
        rfProbesAntFwdWarningLimit OBJECT-TYPE
            SYNTAX FloatingPoint
            UNITS "dB"
            MAX-ACCESS read-write
            STATUS current
            DESCRIPTION
                "This sets the warning limit for the transmitters RF control (to antenna)."
            ::= { rfProbesEntry 4 }

        
        rfProbesAntFwdFailLimit OBJECT-TYPE
            SYNTAX FloatingPoint
            UNITS "dB"
            MAX-ACCESS read-write
            STATUS current
            DESCRIPTION
                "This sets the fault limit for the transmitters RF control (to antenna)."
            ::= { rfProbesEntry 5 }

        
        rfProbesAntFwdDelayTimeRfFail OBJECT-TYPE
            SYNTAX Integer32 (1..20)
            UNITS "seconds"
            MAX-ACCESS read-write
            STATUS current
            DESCRIPTION
                "This sets the delay time for the RF Fail control (to antenna)."
            ::= { rfProbesEntry 6 }

        
        rfProbesAntFwdSetOffset OBJECT-TYPE
            SYNTAX Trigger
            MAX-ACCESS read-write
            STATUS current
            DESCRIPTION
                "This triggers Set Offset."
            ::= { rfProbesEntry 7 }

        
        rfProbesAntFwdSetGain OBJECT-TYPE
            SYNTAX Trigger
            MAX-ACCESS read-write
            STATUS current
            DESCRIPTION
                "This triggers Set Gain."
            ::= { rfProbesEntry 8 }

        
        rfProbesAntReflWarningLimit OBJECT-TYPE
            SYNTAX FloatingPoint
            UNITS "dB"
            MAX-ACCESS read-write
            STATUS current
            DESCRIPTION
                "This sets the warning limit for the transmitters reflection control (to antenna)."
            ::= { rfProbesEntry 9 }

        
        rfProbesAntReflSetOffset OBJECT-TYPE
            SYNTAX Trigger
            MAX-ACCESS read-write
            STATUS current
            DESCRIPTION
                "This triggers Set Offset."
            ::= { rfProbesEntry 10 }

        
        rfProbesAntReflSetGain OBJECT-TYPE
            SYNTAX Trigger
            MAX-ACCESS read-write
            STATUS current
            DESCRIPTION
                "This triggers Set Gain."
            ::= { rfProbesEntry 11 }

        
        rfProbesDLFwdNominal OBJECT-TYPE
            SYNTAX FloatingPoint
            UNITS "Watt"
            MAX-ACCESS read-write
            STATUS current
            DESCRIPTION
                "This sets the nominal value [W] of the transmitter (to dummyload)."
            ::= { rfProbesEntry 12 }

        
        rfProbesDLFwdWarningLimit OBJECT-TYPE
            SYNTAX FloatingPoint
            UNITS "dB"
            MAX-ACCESS read-write
            STATUS current
            DESCRIPTION
                "This sets the warning limit for the transmitters RF control (to dummyload)."
            ::= { rfProbesEntry 13 }

        
        rfProbesDLFwdFailLimit OBJECT-TYPE
            SYNTAX FloatingPoint
            UNITS "dB"
            MAX-ACCESS read-write
            STATUS current
            DESCRIPTION
                "This sets the fault limit for the transmitters RF control (to dummyload)."
            ::= { rfProbesEntry 14 }

        
        rfProbesDLFwdDelayTimeRfFail OBJECT-TYPE
            SYNTAX Integer32 (1..20)
            UNITS "seconds"
            MAX-ACCESS read-write
            STATUS current
            DESCRIPTION
                "This sets the delay time for the RF Fail control (to dummyload)."
            ::= { rfProbesEntry 15 }

        
        rfProbesDLFwdSetOffset OBJECT-TYPE
            SYNTAX Trigger
            MAX-ACCESS read-write
            STATUS current
            DESCRIPTION
                "This triggers Set Offset."
            ::= { rfProbesEntry 16 }

        
        rfProbesDLFwdSetGain OBJECT-TYPE
            SYNTAX Trigger
            MAX-ACCESS read-write
            STATUS current
            DESCRIPTION
                "This triggers Set Gain."
            ::= { rfProbesEntry 17 }

        
        rfProbesDLReflWarningLimit OBJECT-TYPE
            SYNTAX FloatingPoint
            UNITS "dB"
            MAX-ACCESS read-write
            STATUS current
            DESCRIPTION
                "This sets the warning limit for the transmitters reflection control (to dummyload)."
            ::= { rfProbesEntry 18 }

        
        rfProbesDLReflSetOffset OBJECT-TYPE
            SYNTAX Trigger
            MAX-ACCESS read-write
            STATUS current
            DESCRIPTION
                "This triggers Set Offset."
            ::= { rfProbesEntry 19 }

        
        rfProbesDLReflSetGain OBJECT-TYPE
            SYNTAX Trigger
            MAX-ACCESS read-write
            STATUS current
            DESCRIPTION
                "This triggers Set Gain."
            ::= { rfProbesEntry 20 }

        
        rfProbesTxIdx OBJECT-TYPE
            SYNTAX IndexTransmitter
            MAX-ACCESS not-accessible
            STATUS current
            DESCRIPTION
                "The transmitter index. There are max. 8 transmitters, if you have an 8+1 system."
            ::= { rfProbesEntry 1000 }

        
        rackTable OBJECT-TYPE
            SYNTAX SEQUENCE OF RackEntry
            MAX-ACCESS not-accessible
            STATUS current
            DESCRIPTION
                "This table contains important commands for the racks."
            ::= { transmitter 26 }

        
        rackEntry OBJECT-TYPE
            SYNTAX RackEntry
            MAX-ACCESS not-accessible
            STATUS current
            DESCRIPTION
                "An entry for a designated rack or rack's rf probe."
            INDEX { rackTxIdx, rackOstIdx, rackIdx, rackRfProbeIdx }
            ::= { rackTable 1 }

        
        RackEntry ::=
            SEQUENCE { 
                rackTxIdx
                    IndexTransmitter,
                rackOstIdx
                    IndexAB,
                rackIdx
                    IndexRack,
                rackRfProbeIdx
                    INTEGER,
                amplifiersPerRack
                    Integer32,
                rackRfEventSignalling
                    TruthValue,
                rackReferenceVoltage
                    FloatingPoint,
                amplifiersPowerSupply
                    FloatingPoint,
                rackGeneralPurposeInput
                    INTEGER,
                rackOnOff
                    SwitchOnOff,
                rfProbePresent
                    TruthValue,
                rfProbeConfigurationNominalValue
                    Integer32,
                rfProbeThresholdRfFailLimit
                    FloatingPoint,
                rfProbeThresholdTimeoutRfFailCtr
                    Integer32,
                rfProbeThresholdWarningLimit
                    FloatingPoint,
                rfProbeCalibrationGain
                    FloatingPoint,
                rfProbeCalibrationOffset
                    FloatingPoint,
                rfProbeCalibrationSetGain
                    Trigger,
                rfProbeCalibrationSetOffset
                    Trigger,
                rfProbeMeasuredValue
                    FloatingPoint
             }

        rackTxIdx OBJECT-TYPE
            SYNTAX IndexTransmitter
            MAX-ACCESS not-accessible
            STATUS current
            DESCRIPTION
                "The index to address the transmitter."
            ::= { rackEntry 1 }

        
        rackOstIdx OBJECT-TYPE
            SYNTAX IndexAB
            MAX-ACCESS not-accessible
            STATUS current
            DESCRIPTION
                "The dedicated output stage (A/B)."
            ::= { rackEntry 2 }

        
        rackIdx OBJECT-TYPE
            SYNTAX IndexRack
            MAX-ACCESS not-accessible
            STATUS current
            DESCRIPTION
                "The index to address the racks."
            ::= { rackEntry 3 }

        
        rackRfProbeIdx OBJECT-TYPE
            SYNTAX INTEGER
                {
                forward(1),
                reflected(2)
                }
            MAX-ACCESS not-accessible
            STATUS current
            DESCRIPTION
                "The index to address forward and reflected RF probes.
                For not RF probe parameters this index is always 1."
            ::= { rackEntry 4 }

        
        amplifiersPerRack OBJECT-TYPE
            SYNTAX Integer32 (1..10)
            MAX-ACCESS read-only
            STATUS current
            DESCRIPTION
                "The number of amplifiers of a rack."
            ::= { rackEntry 6 }

        
        rackRfEventSignalling OBJECT-TYPE
            SYNTAX TruthValue
            MAX-ACCESS read-write
            STATUS current
            DESCRIPTION
                "This configures whether to signal rf events or not."
            ::= { rackEntry 7 }

        
        rackReferenceVoltage OBJECT-TYPE
            SYNTAX FloatingPoint
            UNITS "percent"
            MAX-ACCESS read-write
            STATUS current
            DESCRIPTION
                "This parameter controls the reference voltage (31.0 ... 100.0)."
            ::= { rackEntry 8 }

        
        amplifiersPowerSupply OBJECT-TYPE
            SYNTAX FloatingPoint
            UNITS "percent"
            MAX-ACCESS read-write
            STATUS current
            DESCRIPTION
                "This parameter controls the power supplies of the amplifier 
                within the rack (31.0 ... 100.0)."
            ::= { rackEntry 9 }

        
        rackGeneralPurposeInput OBJECT-TYPE
            SYNTAX INTEGER
                {
                unused(1),
                doorOpen(2),
                extCoolingWarning(3),
                extCoolingFault(4)
                }
            MAX-ACCESS read-write
            STATUS current
            DESCRIPTION
                "Setting of the general purpose input behaviour."
            ::= { rackEntry 10 }

        
        rackOnOff OBJECT-TYPE
            SYNTAX SwitchOnOff
            MAX-ACCESS read-write
            STATUS current
            DESCRIPTION
                "This switches the rack on/off."
            ::= { rackEntry 20 }

        
        rfProbePresent OBJECT-TYPE
            SYNTAX TruthValue
            MAX-ACCESS read-only
            STATUS current
            DESCRIPTION
                "If the RF probe of this rack is present."
            ::= { rackEntry 50 }

        
        rfProbeConfigurationNominalValue OBJECT-TYPE
            SYNTAX Integer32 (0..100000)
            UNITS "W"
            MAX-ACCESS read-write
            STATUS current
            DESCRIPTION
                "The nominal value of the measured signal."
            ::= { rackEntry 52 }

        
        rfProbeThresholdRfFailLimit OBJECT-TYPE
            SYNTAX FloatingPoint
            UNITS "dB"
            MAX-ACCESS read-write
            STATUS current
            DESCRIPTION
                "Fault limit for the RF control (-20.0 ... 0.0)."
            ::= { rackEntry 55 }

        
        rfProbeThresholdTimeoutRfFailCtr OBJECT-TYPE
            SYNTAX Integer32 (1..20)
            UNITS "s"
            MAX-ACCESS read-write
            STATUS current
            DESCRIPTION
                "Timeout for RF Fail Control."
            ::= { rackEntry 56 }

        
        rfProbeThresholdWarningLimit OBJECT-TYPE
            SYNTAX FloatingPoint
            UNITS "dB"
            MAX-ACCESS read-write
            STATUS current
            DESCRIPTION
                "Warning limit for the RF control (-20.0 ... 0.0).
                
                For reflected probes:
                Warning limit for the reflection control. This limit is added to the 
                fault limit to generate the real warning limit; e.g. the fault limit 
                is -17.0dB and the warning limit is -3.0dB, so the warning is active 
                on a reflected power higher than -20.0 dB."
            ::= { rackEntry 57 }

        
        rfProbeCalibrationGain OBJECT-TYPE
            SYNTAX FloatingPoint
            UNITS "V"
            MAX-ACCESS read-only
            STATUS current
            DESCRIPTION
                "Measured value of gain calibration."
            ::= { rackEntry 60 }

        
        rfProbeCalibrationOffset OBJECT-TYPE
            SYNTAX FloatingPoint
            UNITS "V"
            MAX-ACCESS read-only
            STATUS current
            DESCRIPTION
                "Measured value of offset calibration."
            ::= { rackEntry 61 }

        
        rfProbeCalibrationSetGain OBJECT-TYPE
            SYNTAX Trigger
            MAX-ACCESS read-write
            STATUS current
            DESCRIPTION
                "Sets the gain calibration."
            ::= { rackEntry 62 }

        
        rfProbeCalibrationSetOffset OBJECT-TYPE
            SYNTAX Trigger
            MAX-ACCESS read-write
            STATUS current
            DESCRIPTION
                "Sets the offset calibration."
            ::= { rackEntry 63 }

        
        rfProbeMeasuredValue OBJECT-TYPE
            SYNTAX FloatingPoint
            UNITS "W"
            MAX-ACCESS read-only
            STATUS current
            DESCRIPTION
                "Measured forward/reflected power of antenna signal."
            ::= { rackEntry 65 }

        
        amplifierTable OBJECT-TYPE
            SYNTAX SEQUENCE OF AmplifierEntry
            MAX-ACCESS not-accessible
            STATUS current
            DESCRIPTION
                "This table contains measured values of an amplifier."
            ::= { transmitter 27 }

        
        amplifierEntry OBJECT-TYPE
            SYNTAX AmplifierEntry
            MAX-ACCESS not-accessible
            STATUS current
            DESCRIPTION
                "An entry for a designated amplifier."
            INDEX { rackTxIdx, rackIdx, ampIdx }
            ::= { amplifierTable 1 }

        
        AmplifierEntry ::=
            SEQUENCE { 
                ampIdx
                    IndexAmplifier,
                ampI1A
                    FloatingPoint,
                ampI2A
                    FloatingPoint,
                ampI3A
                    FloatingPoint,
                ampI4A
                    FloatingPoint,
                ampI1B
                    FloatingPoint,
                ampI2B
                    FloatingPoint,
                ampI3B
                    FloatingPoint,
                ampI4B
                    FloatingPoint,
                ampIDrv
                    FloatingPoint,
                ampUDc
                    FloatingPoint,
                ampIDc
                    FloatingPoint,
                ampUDcControl
                    FloatingPoint,
                ampUReg
                    FloatingPoint,
                ampPowerA
                    FloatingPoint,
                ampPowerB
                    FloatingPoint,
                ampPowerOut
                    FloatingPoint,
                ampPowerReflection
                    FloatingPoint,
                ampPowerReference
                    FloatingPoint,
                ampDeltaPhase
                    FloatingPoint,
                ampCmdDeltaPhase
                    FloatingPoint
             }

        ampIdx OBJECT-TYPE
            SYNTAX IndexAmplifier
            MAX-ACCESS not-accessible
            STATUS current
            DESCRIPTION
                "Amplifier Index"
            ::= { amplifierEntry 400 }

        
        ampI1A OBJECT-TYPE
            SYNTAX FloatingPoint
            UNITS "Ampere"
            MAX-ACCESS read-only
            STATUS current
            DESCRIPTION
                "The power amplifier module current (I_1A)."
            ::= { amplifierEntry 401 }

        
        ampI2A OBJECT-TYPE
            SYNTAX FloatingPoint
            UNITS "Ampere"
            MAX-ACCESS read-only
            STATUS current
            DESCRIPTION
                "The power amplifier module current (I_2A)."
            ::= { amplifierEntry 402 }

        
        ampI3A OBJECT-TYPE
            SYNTAX FloatingPoint
            UNITS "Ampere"
            MAX-ACCESS read-only
            STATUS current
            DESCRIPTION
                "The power amplifier module current (I_3A)."
            ::= { amplifierEntry 403 }

        
        ampI4A OBJECT-TYPE
            SYNTAX FloatingPoint
            UNITS "Ampere"
            MAX-ACCESS read-only
            STATUS current
            DESCRIPTION
                "The power amplifier module current (I_4A)."
            ::= { amplifierEntry 404 }

        
        ampI1B OBJECT-TYPE
            SYNTAX FloatingPoint
            UNITS "Ampere"
            MAX-ACCESS read-only
            STATUS current
            DESCRIPTION
                "The power amplifier module current (I_1B)."
            ::= { amplifierEntry 405 }

        
        ampI2B OBJECT-TYPE
            SYNTAX FloatingPoint
            UNITS "Ampere"
            MAX-ACCESS read-only
            STATUS current
            DESCRIPTION
                "The power amplifier module current (I_2B)."
            ::= { amplifierEntry 406 }

        
        ampI3B OBJECT-TYPE
            SYNTAX FloatingPoint
            UNITS "Ampere"
            MAX-ACCESS read-only
            STATUS current
            DESCRIPTION
                "The power amplifier module current (I_3B)."
            ::= { amplifierEntry 407 }

        
        ampI4B OBJECT-TYPE
            SYNTAX FloatingPoint
            UNITS "Ampere"
            MAX-ACCESS read-only
            STATUS current
            DESCRIPTION
                "The power amplifier module current (I_4B)."
            ::= { amplifierEntry 408 }

        
        ampIDrv OBJECT-TYPE
            SYNTAX FloatingPoint
            UNITS "Ampere"
            MAX-ACCESS read-only
            STATUS current
            DESCRIPTION
                "The driver module current (I_DRV)."
            ::= { amplifierEntry 409 }

        
        ampUDc OBJECT-TYPE
            SYNTAX FloatingPoint
            UNITS "Volt"
            MAX-ACCESS read-only
            STATUS current
            DESCRIPTION
                "The power amplifier supply voltage."
            ::= { amplifierEntry 410 }

        
        ampIDc OBJECT-TYPE
            SYNTAX FloatingPoint
            UNITS "Ampere"
            MAX-ACCESS read-only
            STATUS current
            DESCRIPTION
                "The power amplifier supply current."
            ::= { amplifierEntry 411 }

        
        ampUDcControl OBJECT-TYPE
            SYNTAX FloatingPoint
            UNITS "Volt"
            MAX-ACCESS read-only
            STATUS current
            DESCRIPTION
                "The power supply control voltage."
            ::= { amplifierEntry 412 }

        
        ampUReg OBJECT-TYPE
            SYNTAX FloatingPoint
            UNITS "Volt"
            MAX-ACCESS read-only
            STATUS current
            DESCRIPTION
                "The power amplifier AGC voltage."
            ::= { amplifierEntry 413 }

        
        ampPowerA OBJECT-TYPE
            SYNTAX FloatingPoint
            UNITS "Volt"
            MAX-ACCESS read-only
            STATUS current
            DESCRIPTION
                "The voltage power detector A."
            ::= { amplifierEntry 414 }

        
        ampPowerB OBJECT-TYPE
            SYNTAX FloatingPoint
            UNITS "Volt"
            MAX-ACCESS read-only
            STATUS current
            DESCRIPTION
                "The voltage power detector B."
            ::= { amplifierEntry 415 }

        
        ampPowerOut OBJECT-TYPE
            SYNTAX FloatingPoint
            UNITS "Volt"
            MAX-ACCESS read-only
            STATUS current
            DESCRIPTION
                "The voltage forward power detector."
            ::= { amplifierEntry 416 }

        
        ampPowerReflection OBJECT-TYPE
            SYNTAX FloatingPoint
            UNITS "Volt"
            MAX-ACCESS read-only
            STATUS current
            DESCRIPTION
                "The voltage reflected power detector."
            ::= { amplifierEntry 417 }

        
        ampPowerReference OBJECT-TYPE
            SYNTAX FloatingPoint
            UNITS "Volt"
            MAX-ACCESS read-only
            STATUS current
            DESCRIPTION
                "The reference voltage for output power."
            ::= { amplifierEntry 418 }

        
        ampDeltaPhase OBJECT-TYPE
            SYNTAX FloatingPoint
            UNITS "Percent"
            MAX-ACCESS read-only
            STATUS current
            DESCRIPTION
                "The measured phase delta for output power."
            ::= { amplifierEntry 419 }

        
        ampCmdDeltaPhase OBJECT-TYPE
            SYNTAX FloatingPoint
            UNITS "Percent"
            MAX-ACCESS read-write
            STATUS current
            DESCRIPTION
                "The phase delta setting for output power.
                The range is -50.0% to 50.0%."
            ::= { amplifierEntry 420 }

        
        ostBAmplifierTable OBJECT-TYPE
            SYNTAX SEQUENCE OF OstBAmplifierEntry
            MAX-ACCESS not-accessible
            STATUS current
            DESCRIPTION
                "This table contains measured values of an output stage B amplifier."
            ::= { transmitter 29 }

        
        ostBAmplifierEntry OBJECT-TYPE
            SYNTAX OstBAmplifierEntry
            MAX-ACCESS not-accessible
            STATUS current
            DESCRIPTION
                "An entry for a designated amplifier."
            INDEX { rackTxIdx, rackIdx, ostBAmpIdx }
            ::= { ostBAmplifierTable 1 }

        
        OstBAmplifierEntry ::=
            SEQUENCE { 
                ostBAmpIdx
                    IndexAmplifier,
                ostBAmpI1A
                    FloatingPoint,
                ostBAmpI2A
                    FloatingPoint,
                ostBAmpI3A
                    FloatingPoint,
                ostBAmpI4A
                    FloatingPoint,
                ostBAmpI1B
                    FloatingPoint,
                ostBAmpI2B
                    FloatingPoint,
                ostBAmpI3B
                    FloatingPoint,
                ostBAmpI4B
                    FloatingPoint,
                ostBAmpIDrv
                    FloatingPoint,
                ostBAmpUDc
                    FloatingPoint,
                ostBAmpIDc
                    FloatingPoint,
                ostBAmpUDcControl
                    FloatingPoint,
                ostBAmpUReg
                    FloatingPoint,
                ostBAmpPowerA
                    FloatingPoint,
                ostBAmpPowerB
                    FloatingPoint,
                ostBAmpPowerOut
                    FloatingPoint,
                ostBAmpPowerReflection
                    FloatingPoint,
                ostBAmpPowerReference
                    FloatingPoint,
                ostBAmpDeltaPhase
                    FloatingPoint,
                ostBAmpCmdDeltaPhase
                    FloatingPoint
             }

        ostBAmpIdx OBJECT-TYPE
            SYNTAX IndexAmplifier
            MAX-ACCESS not-accessible
            STATUS current
            DESCRIPTION
                "Amplifier Index"
            ::= { ostBAmplifierEntry 400 }

        
        ostBAmpI1A OBJECT-TYPE
            SYNTAX FloatingPoint
            UNITS "Ampere"
            MAX-ACCESS read-only
            STATUS current
            DESCRIPTION
                "The power amplifier module current (I_1A)."
            ::= { ostBAmplifierEntry 401 }

        
        ostBAmpI2A OBJECT-TYPE
            SYNTAX FloatingPoint
            UNITS "Ampere"
            MAX-ACCESS read-only
            STATUS current
            DESCRIPTION
                "The power amplifier module current (I_2A)."
            ::= { ostBAmplifierEntry 402 }

        
        ostBAmpI3A OBJECT-TYPE
            SYNTAX FloatingPoint
            UNITS "Ampere"
            MAX-ACCESS read-only
            STATUS current
            DESCRIPTION
                "The power amplifier module current (I_3A)."
            ::= { ostBAmplifierEntry 403 }

        
        ostBAmpI4A OBJECT-TYPE
            SYNTAX FloatingPoint
            UNITS "Ampere"
            MAX-ACCESS read-only
            STATUS current
            DESCRIPTION
                "The power amplifier module current (I_4A)."
            ::= { ostBAmplifierEntry 404 }

        
        ostBAmpI1B OBJECT-TYPE
            SYNTAX FloatingPoint
            UNITS "Ampere"
            MAX-ACCESS read-only
            STATUS current
            DESCRIPTION
                "The power amplifier module current (I_1B)."
            ::= { ostBAmplifierEntry 405 }

        
        ostBAmpI2B OBJECT-TYPE
            SYNTAX FloatingPoint
            UNITS "Ampere"
            MAX-ACCESS read-only
            STATUS current
            DESCRIPTION
                "The power amplifier module current (I_2B)."
            ::= { ostBAmplifierEntry 406 }

        
        ostBAmpI3B OBJECT-TYPE
            SYNTAX FloatingPoint
            UNITS "Ampere"
            MAX-ACCESS read-only
            STATUS current
            DESCRIPTION
                "The power amplifier module current (I_3B)."
            ::= { ostBAmplifierEntry 407 }

        
        ostBAmpI4B OBJECT-TYPE
            SYNTAX FloatingPoint
            UNITS "Ampere"
            MAX-ACCESS read-only
            STATUS current
            DESCRIPTION
                "The power amplifier module current (I_4B)."
            ::= { ostBAmplifierEntry 408 }

        
        ostBAmpIDrv OBJECT-TYPE
            SYNTAX FloatingPoint
            UNITS "Ampere"
            MAX-ACCESS read-only
            STATUS current
            DESCRIPTION
                "The driver module current (I_DRV)."
            ::= { ostBAmplifierEntry 409 }

        
        ostBAmpUDc OBJECT-TYPE
            SYNTAX FloatingPoint
            UNITS "Volt"
            MAX-ACCESS read-only
            STATUS current
            DESCRIPTION
                "The power amplifier supply voltage."
            ::= { ostBAmplifierEntry 410 }

        
        ostBAmpIDc OBJECT-TYPE
            SYNTAX FloatingPoint
            UNITS "Ampere"
            MAX-ACCESS read-only
            STATUS current
            DESCRIPTION
                "The power amplifier supply current."
            ::= { ostBAmplifierEntry 411 }

        
        ostBAmpUDcControl OBJECT-TYPE
            SYNTAX FloatingPoint
            UNITS "Volt"
            MAX-ACCESS read-only
            STATUS current
            DESCRIPTION
                "The power supply control voltage."
            ::= { ostBAmplifierEntry 412 }

        
        ostBAmpUReg OBJECT-TYPE
            SYNTAX FloatingPoint
            UNITS "Volt"
            MAX-ACCESS read-only
            STATUS current
            DESCRIPTION
                "The power amplifier AGC voltage."
            ::= { ostBAmplifierEntry 413 }

        
        ostBAmpPowerA OBJECT-TYPE
            SYNTAX FloatingPoint
            UNITS "Volt"
            MAX-ACCESS read-only
            STATUS current
            DESCRIPTION
                "The voltage power detector A."
            ::= { ostBAmplifierEntry 414 }

        
        ostBAmpPowerB OBJECT-TYPE
            SYNTAX FloatingPoint
            UNITS "Volt"
            MAX-ACCESS read-only
            STATUS current
            DESCRIPTION
                "The voltage power detector B."
            ::= { ostBAmplifierEntry 415 }

        
        ostBAmpPowerOut OBJECT-TYPE
            SYNTAX FloatingPoint
            UNITS "Volt"
            MAX-ACCESS read-only
            STATUS current
            DESCRIPTION
                "The voltage forward power detector."
            ::= { ostBAmplifierEntry 416 }

        
        ostBAmpPowerReflection OBJECT-TYPE
            SYNTAX FloatingPoint
            UNITS "Volt"
            MAX-ACCESS read-only
            STATUS current
            DESCRIPTION
                "The voltage reflected power detector."
            ::= { ostBAmplifierEntry 417 }

        
        ostBAmpPowerReference OBJECT-TYPE
            SYNTAX FloatingPoint
            UNITS "Volt"
            MAX-ACCESS read-only
            STATUS current
            DESCRIPTION
                "The reference voltage for output power."
            ::= { ostBAmplifierEntry 418 }

        
        ostBAmpDeltaPhase OBJECT-TYPE
            SYNTAX FloatingPoint
            UNITS "Percent"
            MAX-ACCESS read-only
            STATUS current
            DESCRIPTION
                "The measured phase delta for output power."
            ::= { ostBAmplifierEntry 419 }

        
        ostBAmpCmdDeltaPhase OBJECT-TYPE
            SYNTAX FloatingPoint
            UNITS "Percent"
            MAX-ACCESS read-write
            STATUS current
            DESCRIPTION
                "The phase delta setting for output power.
                The range is -50.0% to 50.0%."
            ::= { ostBAmplifierEntry 420 }

        
        sx801AmplifierTable OBJECT-TYPE
            SYNTAX SEQUENCE OF Sx801AmplifierEntry
            MAX-ACCESS not-accessible
            STATUS current
            DESCRIPTION
                "Amplifier status values for SX801 amplifiers."
            ::= { transmitter 30 }

        
        sx801AmplifierEntry OBJECT-TYPE
            SYNTAX Sx801AmplifierEntry
            MAX-ACCESS not-accessible
            STATUS current
            DESCRIPTION
                "A row (an entry) for one amplifier."
            INDEX { statusTxIdx, sx801AmpIdx }
            ::= { sx801AmplifierTable 1 }

        
        Sx801AmplifierEntry ::=
            SEQUENCE { 
                sx801AmpIdx
                    IndexAmplifier,
                sx801AmpRfOut
                    Sx801AmplifierState,
                sx801AmpRfIn
                    Sx801AmplifierState,
                sx801AmpReflection
                    INTEGER,
                sx801AmpOn
                    INTEGER,
                sx801AmpAC
                    Sx801AmplifierState,
                sx801AmpCommunication
                    INTEGER,
                sx801AmpTransistor
                    Sx801AmplifierState,
                sx801AmpDriver
                    Sx801AmplifierState,
                sx801AmpTemperature
                    Sx801AmplifierState,
                sx801AmpBlower
                    Sx801AmplifierState,
                sx801AmpRegulation
                    Sx801AmplifierState,
                sx801AmpUpdate
                    TruthValue,
                sx801Supply1Temperature
                    Sx801AmplifierState,
                sx801Supply2Temperature
                    Sx801AmplifierState,
                sx801SupplyRTemperature
                    Sx801AmplifierState,
                sx801Supply1DC
                    Sx801AmplifierState,
                sx801Supply2DC
                    Sx801AmplifierState,
                sx801SupplyRDC
                    Sx801AmplifierState,
                sx801AmpValueI1
                    FloatingPoint,
                sx801AmpValueI2
                    FloatingPoint,
                sx801AmpValueI3
                    FloatingPoint,
                sx801AmpValueI4
                    FloatingPoint,
                sx801AmpValueIPre
                    FloatingPoint,
                sx801AmpValueIDrv1
                    FloatingPoint,
                sx801AmpValueIDrv2
                    FloatingPoint,
                sx801AmpValuePowerOut
                    FloatingPoint,
                sx801AmpValueReflection
                    FloatingPoint,
                sx801AmpValueVRef
                    FloatingPoint,
                sx801AmpValueVReg
                    FloatingPoint,
                sx801AmpValueTemperature
                    FloatingPoint,
                sx801AmpValueMonAtt
                    FloatingPoint,
                sx801AmpValueVAux1
                    FloatingPoint,
                sx801AmpValueVAux2
                    FloatingPoint,
                sx801Supply1ValuePwr
                    FloatingPoint,
                sx801Supply2ValuePwr
                    FloatingPoint,
                sx801Supply1ValueDc
                    FloatingPoint,
                sx801Supply2ValueDc
                    FloatingPoint
             }

        sx801AmpIdx OBJECT-TYPE
            SYNTAX IndexAmplifier
            MAX-ACCESS not-accessible
            STATUS current
            DESCRIPTION
                "The amplifier index."
            ::= { sx801AmplifierEntry 1 }

        
        sx801AmpRfOut OBJECT-TYPE
            SYNTAX Sx801AmplifierState
            MAX-ACCESS read-only
            STATUS current
            DESCRIPTION
                "Shows if the amplifier generates an RF or not.
                off(1): The amplifier output is switched off
                e.g. because the amplifier gets no input signal or the transmitter has been switched off
                warning(2): There is an RF but its level is less than the RF warning limit.
                ok(3): The RF level is greater than the RF warning limit."
            ::= { sx801AmplifierEntry 2 }

        
        sx801AmpRfIn OBJECT-TYPE
            SYNTAX Sx801AmplifierState
            MAX-ACCESS read-only
            STATUS current
            DESCRIPTION
                "Displays the state of the amplifier input.
                off(1): no input signal detected
                warning(2): the level of the input signal is too low or too high.
                ok(3): input signal is OK."
            ::= { sx801AmplifierEntry 3 }

        
        sx801AmpReflection OBJECT-TYPE
            SYNTAX INTEGER
                {
                off(1),
                warning(2),
                unknown(3),
                fault(4)
                }
            MAX-ACCESS read-only
            STATUS current
            DESCRIPTION
                " A reflection on RF output of this Amplifier module has been detected.
                This leads to a reduction of output power of the amplifier.
                
                "
            ::= { sx801AmplifierEntry 4 }

        
        sx801AmpOn OBJECT-TYPE
            SYNTAX INTEGER
                {
                off(1),
                on(3),
                unknown(4)
                }
            MAX-ACCESS read-only
            STATUS current
            DESCRIPTION
                "Shows if the amplifier has been switched on by the control unit."
            ::= { sx801AmplifierEntry 5 }

        
        sx801AmpAC OBJECT-TYPE
            SYNTAX Sx801AmplifierState
            MAX-ACCESS read-only
            STATUS current
            DESCRIPTION
                "Shows the state of primary voltage of the power supply."
            ::= { sx801AmplifierEntry 6 }

        
        sx801AmpCommunication OBJECT-TYPE
            SYNTAX INTEGER
                {
                off(1),
                unknown(2),
                ok(3),
                fault(4)
                }
            MAX-ACCESS read-only
            STATUS current
            DESCRIPTION
                "Displays if the CAN communication between amplifier and Sx801 is working or not."
            ::= { sx801AmplifierEntry 7 }

        
        sx801AmpTransistor OBJECT-TYPE
            SYNTAX Sx801AmplifierState
            MAX-ACCESS read-only
            STATUS current
            DESCRIPTION
                "A transistor fail is displayed here.
                For further information please see the amplifiers service menue."
            ::= { sx801AmplifierEntry 8 }

        
        sx801AmpDriver OBJECT-TYPE
            SYNTAX Sx801AmplifierState
            MAX-ACCESS read-only
            STATUS current
            DESCRIPTION
                "Shows a failure if one of the internal driver transistors does not work properly.
                For further information please see the amplifiers service menue."
            ::= { sx801AmplifierEntry 9 }

        
        sx801AmpTemperature OBJECT-TYPE
            SYNTAX Sx801AmplifierState
            MAX-ACCESS read-only
            STATUS current
            DESCRIPTION
                "Shows a fault if the temperature of amplifier module is too high."
            ::= { sx801AmplifierEntry 10 }

        
        sx801AmpBlower OBJECT-TYPE
            SYNTAX Sx801AmplifierState
            MAX-ACCESS read-only
            STATUS current
            DESCRIPTION
                "Displays the state of the internal blowers."
            ::= { sx801AmplifierEntry 11 }

        
        sx801AmpRegulation OBJECT-TYPE
            SYNTAX Sx801AmplifierState
            MAX-ACCESS read-only
            STATUS current
            DESCRIPTION
                "Shows a fault if the amplifier is not able to control its output power."
            ::= { sx801AmplifierEntry 12 }

        
        sx801AmpUpdate OBJECT-TYPE
            SYNTAX TruthValue
            MAX-ACCESS read-only
            STATUS current
            DESCRIPTION
                "Firmware update is in progress.
                This will be started automatically during a software update procedure of the transmitter."
            ::= { sx801AmplifierEntry 13 }

        
        sx801Supply1Temperature OBJECT-TYPE
            SYNTAX Sx801AmplifierState
            MAX-ACCESS read-only
            STATUS current
            DESCRIPTION
                "Shows a fault if the temperature of power supply one is too high."
            ::= { sx801AmplifierEntry 14 }

        
        sx801Supply2Temperature OBJECT-TYPE
            SYNTAX Sx801AmplifierState
            MAX-ACCESS read-only
            STATUS current
            DESCRIPTION
                "Shows a fault if the temperature of power supply two is too high."
            ::= { sx801AmplifierEntry 15 }

        
        sx801SupplyRTemperature OBJECT-TYPE
            SYNTAX Sx801AmplifierState
            MAX-ACCESS read-only
            STATUS current
            DESCRIPTION
                "Shows a fault if the temperature of the reserve power supply is too high."
            ::= { sx801AmplifierEntry 16 }

        
        sx801Supply1DC OBJECT-TYPE
            SYNTAX Sx801AmplifierState
            MAX-ACCESS read-only
            STATUS current
            DESCRIPTION
                "Shows a fault if the output voltage of power supply one is not ok."
            ::= { sx801AmplifierEntry 17 }

        
        sx801Supply2DC OBJECT-TYPE
            SYNTAX Sx801AmplifierState
            MAX-ACCESS read-only
            STATUS current
            DESCRIPTION
                "Shows a fault if the output voltage of power supply two is not ok."
            ::= { sx801AmplifierEntry 18 }

        
        sx801SupplyRDC OBJECT-TYPE
            SYNTAX Sx801AmplifierState
            MAX-ACCESS read-only
            STATUS current
            DESCRIPTION
                "Shows a fault if the output voltage of the reserve power supply is not ok."
            ::= { sx801AmplifierEntry 19 }

        
        sx801AmpValueI1 OBJECT-TYPE
            SYNTAX FloatingPoint
            UNITS "Ampere"
            MAX-ACCESS read-only
            STATUS current
            DESCRIPTION
                "The internal current from transistor pair 1."
            ::= { sx801AmplifierEntry 50 }

        
        sx801AmpValueI2 OBJECT-TYPE
            SYNTAX FloatingPoint
            UNITS "Ampere"
            MAX-ACCESS read-only
            STATUS current
            DESCRIPTION
                "The internal current from transistor pair 2."
            ::= { sx801AmplifierEntry 51 }

        
        sx801AmpValueI3 OBJECT-TYPE
            SYNTAX FloatingPoint
            UNITS "Ampere"
            MAX-ACCESS read-only
            STATUS current
            DESCRIPTION
                "The internal current from transistor pair 3."
            ::= { sx801AmplifierEntry 52 }

        
        sx801AmpValueI4 OBJECT-TYPE
            SYNTAX FloatingPoint
            UNITS "Ampere"
            MAX-ACCESS read-only
            STATUS current
            DESCRIPTION
                "The internal current from transistor pair 4."
            ::= { sx801AmplifierEntry 53 }

        
        sx801AmpValueIPre OBJECT-TYPE
            SYNTAX FloatingPoint
            UNITS "Ampere"
            MAX-ACCESS read-only
            STATUS current
            DESCRIPTION
                "The internal current from preamplifier."
            ::= { sx801AmplifierEntry 54 }

        
        sx801AmpValueIDrv1 OBJECT-TYPE
            SYNTAX FloatingPoint
            UNITS "Ampere"
            MAX-ACCESS read-only
            STATUS current
            DESCRIPTION
                "The internal current from driver transistor pair 1."
            ::= { sx801AmplifierEntry 55 }

        
        sx801AmpValueIDrv2 OBJECT-TYPE
            SYNTAX FloatingPoint
            UNITS "Ampere"
            MAX-ACCESS read-only
            STATUS current
            DESCRIPTION
                "The internal current from driver transistor pair 2."
            ::= { sx801AmplifierEntry 56 }

        
        sx801AmpValuePowerOut OBJECT-TYPE
            SYNTAX FloatingPoint
            UNITS "Watt"
            MAX-ACCESS read-only
            STATUS current
            DESCRIPTION
                "The base value in Volt to calculate the output power
                of this amplifier module."
            ::= { sx801AmplifierEntry 57 }

        
        sx801AmpValueReflection OBJECT-TYPE
            SYNTAX FloatingPoint
            UNITS "Watt"
            MAX-ACCESS read-only
            STATUS current
            DESCRIPTION
                "The base value in Volt for detection of reflections."
            ::= { sx801AmplifierEntry 58 }

        
        sx801AmpValueVRef OBJECT-TYPE
            SYNTAX FloatingPoint
            UNITS "Volt"
            MAX-ACCESS read-only
            STATUS current
            DESCRIPTION
                "The internal reference voltage to set the output power."
            ::= { sx801AmplifierEntry 59 }

        
        sx801AmpValueVReg OBJECT-TYPE
            SYNTAX FloatingPoint
            UNITS "Volt"
            MAX-ACCESS read-only
            STATUS current
            DESCRIPTION
                "The internal value for output power regulation."
            ::= { sx801AmplifierEntry 60 }

        
        sx801AmpValueTemperature OBJECT-TYPE
            SYNTAX FloatingPoint
            UNITS "degree Celsius"
            MAX-ACCESS read-only
            STATUS current
            DESCRIPTION
                "The internal temperature of Amplifier.
                In case of L-band amplifier, the shown temperature is valid only,
                if the amplifier is switched on."
            ::= { sx801AmplifierEntry 61 }

        
        sx801AmpValueMonAtt OBJECT-TYPE
            SYNTAX FloatingPoint
            UNITS "dB"
            MAX-ACCESS read-only
            STATUS current
            DESCRIPTION
                "The attenuation of monitoring output on the front of the
                amplifier module (Amp RF Mon)."
            ::= { sx801AmplifierEntry 62 }

        
        sx801AmpValueVAux1 OBJECT-TYPE
            SYNTAX FloatingPoint
            UNITS "Volt"
            MAX-ACCESS read-only
            STATUS current
            DESCRIPTION
                "The voltage power detector 1."
            ::= { sx801AmplifierEntry 63 }

        
        sx801AmpValueVAux2 OBJECT-TYPE
            SYNTAX FloatingPoint
            UNITS "Volt"
            MAX-ACCESS read-only
            STATUS current
            DESCRIPTION
                "The voltage power detector 2."
            ::= { sx801AmplifierEntry 64 }

        
        sx801Supply1ValuePwr OBJECT-TYPE
            SYNTAX FloatingPoint
            UNITS "Volt"
            MAX-ACCESS read-only
            STATUS current
            DESCRIPTION
                "The power supply one control voltage."
            ::= { sx801AmplifierEntry 65 }

        
        sx801Supply2ValuePwr OBJECT-TYPE
            SYNTAX FloatingPoint
            UNITS "Volt"
            MAX-ACCESS read-only
            STATUS current
            DESCRIPTION
                "The power supply two control voltage."
            ::= { sx801AmplifierEntry 66 }

        
        sx801Supply1ValueDc OBJECT-TYPE
            SYNTAX FloatingPoint
            UNITS "Volt"
            MAX-ACCESS read-only
            STATUS current
            DESCRIPTION
                "The internal supply voltage of transistor path two.
                In systems with two power supplies this value is equal
                to the output voltage of supply one."
            ::= { sx801AmplifierEntry 67 }

        
        sx801Supply2ValueDc OBJECT-TYPE
            SYNTAX FloatingPoint
            UNITS "Volt"
            MAX-ACCESS read-only
            STATUS current
            DESCRIPTION
                "The internal supply voltage of transistor path two.
                In systems with two power supplies this value is equal
                to the output voltage of supply two."
            ::= { sx801AmplifierEntry 68 }

        
        productInfoTable OBJECT-TYPE
            SYNTAX SEQUENCE OF ProductInfoEntry
            MAX-ACCESS not-accessible
            STATUS current
            DESCRIPTION
                "The table for product typeplates."
            ::= { transmitter 100 }

        
        productInfoEntry OBJECT-TYPE
            SYNTAX ProductInfoEntry
            MAX-ACCESS not-accessible
            STATUS current
            DESCRIPTION
                "A row (an entry) for one typeplate."
            INDEX { prodInfoModuleIdx, prodInfoTxIdx, prodInfoDeviceIdx, prodInfoRackIdx, prodInfoAmpIdx
                 }
            ::= { productInfoTable 1 }

        
        ProductInfoEntry ::=
            SEQUENCE { 
                prodInfoModuleIdx
                    ProdInfoModuleNameTv,
                prodInfoTxIdx
                    IndexTransmitter,
                prodInfoDeviceIdx
                    IndexAB,
                prodInfoRackIdx
                    IndexRack,
                prodInfoAmpIdx
                    IndexAmplifier,
                prodInfoModuleName
                    ProdInfoModuleNameTv,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime
             }

        prodInfoModuleIdx OBJECT-TYPE
            SYNTAX ProdInfoModuleNameTv
            MAX-ACCESS not-accessible
            STATUS current
            DESCRIPTION
                "The module index."
            ::= { productInfoEntry 1 }

        
        prodInfoTxIdx OBJECT-TYPE
            SYNTAX IndexTransmitter
            MAX-ACCESS not-accessible
            STATUS current
            DESCRIPTION
                "The transmitter index. There are max. 8 transmitters, if you have an 8+1 system."
            ::= { productInfoEntry 2 }

        
        prodInfoDeviceIdx OBJECT-TYPE
            SYNTAX IndexAB
            MAX-ACCESS not-accessible
            STATUS current
            DESCRIPTION
                "The dedicated device (A/B)."
            ::= { productInfoEntry 3 }

        
        prodInfoRackIdx OBJECT-TYPE
            SYNTAX IndexRack
            MAX-ACCESS not-accessible
            STATUS current
            DESCRIPTION
                "The rack number (1..10)."
            ::= { productInfoEntry 4 }

        
        prodInfoAmpIdx OBJECT-TYPE
            SYNTAX IndexAmplifier
            MAX-ACCESS not-accessible
            STATUS current
            DESCRIPTION
                "Amplifier Index"
            ::= { productInfoEntry 5 }

        
        prodInfoModuleName OBJECT-TYPE
            SYNTAX ProdInfoModuleNameTv
            MAX-ACCESS read-only
            STATUS current
            DESCRIPTION
                "The name of the module as a text."
            ::= { productInfoEntry 6 }

        
        prodInfoSerialNumber OBJECT-TYPE
            SYNTAX ReadableString
            MAX-ACCESS read-only
            STATUS current
            DESCRIPTION
                "The serial number of the subdevice."
            ::= { productInfoEntry 7 }

        
        prodInfoIdentNumberSW OBJECT-TYPE
            SYNTAX ReadableString
            MAX-ACCESS read-only
            STATUS current
            DESCRIPTION
                "The Rohde&Schwarz identification number of the software, for example 2094.2090.02."
            ::= { productInfoEntry 8 }

        
        prodInfoVersionNumberSW OBJECT-TYPE
            SYNTAX ReadableString
            MAX-ACCESS read-only
            STATUS current
            DESCRIPTION
                "The Rohde&Schwarz revision number of the software, for example 1.2.1."
            ::= { productInfoEntry 9 }

        
        prodInfoIdentNumberHW OBJECT-TYPE
            SYNTAX ReadableString
            MAX-ACCESS read-only
            STATUS current
            DESCRIPTION
                "The Rohde&Schwarz identification number of the hardware, for example 2095.8007.02 (NetCCU)."
            ::= { productInfoEntry 10 }

        
        prodInfoVersionNumberHW OBJECT-TYPE
            SYNTAX ReadableString
            MAX-ACCESS read-only
            STATUS current
            DESCRIPTION
                "The Rohde&Schwarz revision number (product index) of the hardware, for example 03.03."
            ::= { productInfoEntry 11 }

        
        productInfoProductDateHW OBJECT-TYPE
            SYNTAX DateAndTime
            MAX-ACCESS read-only
            STATUS current
            DESCRIPTION
                "The Rohde&Schwarz production date of the hardware,"
            ::= { productInfoEntry 12 }

        
-- *****************************************************************************
-- **          event definitions
-- *****************************************************************************
        rsXx8000DvbNTxEvents OBJECT IDENTIFIER ::= { rsXx8000DvbNTx 3 }

        
-- *****************************************************************************
-- **          events NetCCU control unit
-- *****************************************************************************
        eventNcu OBJECT IDENTIFIER ::= { rsXx8000DvbNTxEvents 1 }

        
        eventsNcuV2 OBJECT-IDENTITY
            STATUS current
            DESCRIPTION 
                "Compatibility to SMIv1."
            ::= { eventNcu 0 }

        
        ncuSummaryFault NOTIFICATION-TYPE
            OBJECTS { eventAlarmPriority, eventAlarmClass, eventEvent }
            STATUS current
            DESCRIPTION 
                "NetCCU Tx Control Unit Summary Fault"
            ::= { eventsNcuV2 1 }

        
        ncuSummaryWarning NOTIFICATION-TYPE
            OBJECTS { eventAlarmPriority, eventAlarmClass, eventEvent }
            STATUS current
            DESCRIPTION 
                "NetCCU Tx Control Unit Summary Warning"
            ::= { eventsNcuV2 2 }

        
        ncuLocal NOTIFICATION-TYPE
            OBJECTS { eventAlarmPriority, eventAlarmClass, eventEvent }
            STATUS current
            DESCRIPTION 
                "NetCCU Tx Control Unit Local/Remote"
            ::= { eventsNcuV2 3 }

        
        ncuFanWarning NOTIFICATION-TYPE
            OBJECTS { eventAlarmPriority, eventAlarmClass, eventEvent }
            STATUS current
            DESCRIPTION 
                "NetCCU Tx Control Unit Fan Warning"
            ::= { eventsNcuV2 6 }

        
        ncuBoardTemperatureFault NOTIFICATION-TYPE
            OBJECTS { eventAlarmPriority, eventAlarmClass, eventEvent }
            STATUS deprecated
            DESCRIPTION 
                "NetCCU Tx Control Unit Mainboard Temperature Fault
                
                deprecated: this information is now handled as a warning
                (ncuBoardTemperatureWarning)"
            ::= { eventsNcuV2 7 }

        
        ncuPowerSupply NOTIFICATION-TYPE
            OBJECTS { eventAlarmPriority, eventAlarmClass, eventEvent }
            STATUS current
            DESCRIPTION 
                "NetCCU Tx Control UnitPower Supply"
            ::= { eventsNcuV2 8 }

        
        ncuInternalPowerSupplyWarning NOTIFICATION-TYPE
            OBJECTS { eventAlarmPriority, eventAlarmClass, eventEvent }
            STATUS current
            DESCRIPTION 
                "NetCCU internal Power Supply warning"
            ::= { eventsNcuV2 11 }

        
        ncuExternalPowerSupplyWarning NOTIFICATION-TYPE
            OBJECTS { eventAlarmPriority, eventAlarmClass, eventEvent }
            STATUS current
            DESCRIPTION 
                "NetCCU external Power Supply warning"
            ::= { eventsNcuV2 12 }

        
        ncuBoardTemperatureWarning NOTIFICATION-TYPE
            OBJECTS { eventAlarmPriority, eventAlarmClass, eventEvent }
            STATUS current
            DESCRIPTION 
                "NetCCU Mainboard Temperature Warning"
            ::= { eventsNcuV2 13 }

        
        eventsNcuTable OBJECT-TYPE
            SYNTAX SEQUENCE OF EventsNcuEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventNcu 1 }

        
        eventsNcuEntry OBJECT-TYPE
            SYNTAX EventsNcuEntry
            MAX-ACCESS not-accessible
            STATUS current
            DESCRIPTION
                "An event entry always consists of 4 values:
                - name: an enumerated list of all possible notifications
                - mask: the corresponding mask (enable/disable)
                - priority: the corresponding priority (value in range 0..255)
                - event: the event itself (active/inactive)"
            INDEX { eventNcuIdx }
            ::= { eventsNcuTable 1 }

        
        EventsNcuEntry ::=
            SEQUENCE { 
                eventNcuIdx
                    EventMaxEntryNumber,
                eventNcuName
                    INTEGER,
                eventNcuMask
                    EventMask,
                eventNcuPriority
                    EventPriority,
                eventNcuEvent
                    EventState
             }

        eventNcuIdx OBJECT-TYPE
            SYNTAX EventMaxEntryNumber
            MAX-ACCESS not-accessible
            STATUS current
            DESCRIPTION
                "The event number as integer."
            ::= { eventsNcuEntry 1 }

        
        eventNcuName OBJECT-TYPE
            SYNTAX INTEGER
                {
                ncuSummaryFault(1),
                ncuSummaryWarning(2),
                ncuLocal(3),
                ncuFanWarning(6),
                ncuBoardTemperatureFault(7),
                ncuPowerSupply(8),
                ncuInternalPowerSupplyWarning(11),
                ncuExternalPowerSupplyWarning(12),
                ncuBoardTemperatureWarning(13)
                }
            MAX-ACCESS read-only
            STATUS current
            DESCRIPTION
                "The event number as integer and the value as readable text."
            ::= { eventsNcuEntry 2 }

        
        eventNcuMask OBJECT-TYPE
            SYNTAX EventMask
            MAX-ACCESS read-write
            STATUS current
            DESCRIPTION
                "See TextualConvention for details."
            ::= { eventsNcuEntry 3 }

        
        eventNcuPriority OBJECT-TYPE
            SYNTAX EventPriority
            MAX-ACCESS read-write
            STATUS current
            DESCRIPTION
                "See TextualConvention for details."
            ::= { eventsNcuEntry 4 }

        
        eventNcuEvent OBJECT-TYPE
            SYNTAX EventState
            MAX-ACCESS read-only
            STATUS current
            DESCRIPTION
                "See TextualConvention for details."
            ::= { eventsNcuEntry 5 }

        
-- *****************************************************************************
-- **          events transmitter
-- *****************************************************************************
        eventTx OBJECT IDENTIFIER ::= { rsXx8000DvbNTxEvents 2 }

        
        eventsTxV2 OBJECT-IDENTITY
            STATUS current
            DESCRIPTION 
                "Compatibility to SMIv1."
            ::= { eventTx 0 }

        
        txSummaryFault NOTIFICATION-TYPE
            OBJECTS { eventAlarmPriority, eventAlarmClass, eventEvent, indexTransmitter }
            STATUS current
            DESCRIPTION 
                "Transmitter Summary Fault"
            ::= { eventsTxV2 1 }

        
        txSummaryWarning NOTIFICATION-TYPE
            OBJECTS { eventAlarmPriority, eventAlarmClass, eventEvent, indexTransmitter }
            STATUS current
            DESCRIPTION 
                "Transmitter Summary Warning"
            ::= { eventsTxV2 2 }

        
        txLocal NOTIFICATION-TYPE
            OBJECTS { eventAlarmPriority, eventAlarmClass, eventEvent, indexTransmitter }
            STATUS current
            DESCRIPTION 
                "Transmitter Local/Remote"
            ::= { eventsTxV2 3 }

        
        txRfOn NOTIFICATION-TYPE
            OBJECTS { eventAlarmPriority, eventAlarmClass, eventEvent, indexTransmitter }
            STATUS current
            DESCRIPTION 
                "Transmitter RF On/Off"
            ::= { eventsTxV2 4 }

        
        txRfOk NOTIFICATION-TYPE
            OBJECTS { eventAlarmPriority, eventAlarmClass, eventEvent, indexTransmitter }
            STATUS current
            DESCRIPTION 
                "Transmitter RF Ok / Not OK"
            ::= { eventsTxV2 5 }

        
        txParamSetSubDeviceDiffers NOTIFICATION-TYPE
            OBJECTS { eventAlarmPriority, eventAlarmClass, eventEvent, indexTransmitter }
            STATUS obsolete
            DESCRIPTION 
                "Parameterset of subdevice is different.
                The currently loaded parameterset is inconsistent because
                a subdevice (e.g. an exciter) has a different configuration than expected.
                To correct this, save settings to the current or save a complete new."
            ::= { eventsTxV2 6 }

        
        txParamSetValuesChanged NOTIFICATION-TYPE
            OBJECTS { eventAlarmPriority, eventAlarmClass, eventEvent, indexTransmitter }
            STATUS current
            DESCRIPTION 
                "Value Of Current Parameterset Changed.
                The currently loaded parameterset is inconsistent because
                there were changes happening since the load/save of it.
                To correct this, save settings to the current or save a complete new."
            ::= { eventsTxV2 7 }

        
        txRfLoopProgram NOTIFICATION-TYPE
            OBJECTS { eventAlarmPriority, eventAlarmClass, eventEvent, indexTransmitter }
            STATUS current
            DESCRIPTION 
                "NetCCU Loop Program"
            ::= { eventsTxV2 8 }

        
        txRfLoopReserve NOTIFICATION-TYPE
            OBJECTS { eventAlarmPriority, eventAlarmClass, eventEvent, indexTransmitter }
            STATUS current
            DESCRIPTION 
                "NetCCU Loop Reserve"
            ::= { eventsTxV2 9 }

        
        txRfWarning NOTIFICATION-TYPE
            OBJECTS { eventAlarmPriority, eventAlarmClass, eventEvent, indexTransmitter }
            STATUS current
            DESCRIPTION 
                "NetCCU RF Warning"
            ::= { eventsTxV2 10 }

        
        txReflectionWarning NOTIFICATION-TYPE
            OBJECTS { eventAlarmPriority, eventAlarmClass, eventEvent, indexTransmitter }
            STATUS current
            DESCRIPTION 
                "NetCCU Reflection Warning"
            ::= { eventsTxV2 11 }

        
        txNoConnection NOTIFICATION-TYPE
            OBJECTS { eventAlarmPriority, eventAlarmClass, eventEvent, indexTransmitter }
            STATUS current
            DESCRIPTION 
                "NSU connection to NetCCU faulty."
            ::= { eventsTxV2 12 }

        
        txNetCCUFanFault NOTIFICATION-TYPE
            OBJECTS { eventAlarmPriority, eventAlarmClass, eventEvent, indexTransmitter }
            STATUS current
            DESCRIPTION 
                "NetCCU Fan Fault"
            ::= { eventsTxV2 14 }

        
        txNetCCUPowerSupply NOTIFICATION-TYPE
            OBJECTS { eventAlarmPriority, eventAlarmClass, eventEvent, indexTransmitter }
            STATUS current
            DESCRIPTION 
                "NetCCU Power Supply"
            ::= { eventsTxV2 15 }

        
        txRfFail NOTIFICATION-TYPE
            OBJECTS { eventAlarmPriority, eventAlarmClass, eventEvent, indexTransmitter }
            STATUS current
            DESCRIPTION 
                "NetCCU (Transmitter) RF Fail"
            ::= { eventsTxV2 16 }

        
        txReflectionFault NOTIFICATION-TYPE
            OBJECTS { eventAlarmPriority, eventAlarmClass, eventEvent, indexTransmitter }
            STATUS current
            DESCRIPTION 
                "NetCCU Reflection Fault"
            ::= { eventsTxV2 17 }

        
        txNetCCUBoardTemperatureFault NOTIFICATION-TYPE
            OBJECTS { eventAlarmPriority, eventAlarmClass, eventEvent, indexTransmitter }
            STATUS deprecated
            DESCRIPTION 
                "NetCCU Board Temperature Fault
                
                deprecated: this information is now handled as a warning
                (txNetCCUBoardTemperatureWarning)"
            ::= { eventsTxV2 18 }

        
        txNetCCUNoConnectionToExcA NOTIFICATION-TYPE
            OBJECTS { eventAlarmPriority, eventAlarmClass, eventEvent, indexTransmitter }
            STATUS current
            DESCRIPTION 
                "NetCCU Connection To ExciterA Faulty"
            ::= { eventsTxV2 19 }

        
        txNetCCUNoConnectionToOstA NOTIFICATION-TYPE
            OBJECTS { eventAlarmPriority, eventAlarmClass, eventEvent, indexTransmitter }
            STATUS current
            DESCRIPTION 
                "NetCCU Connection To OutputstageA Faulty"
            ::= { eventsTxV2 20 }

        
        txNetCCUNoConnectionToExcB NOTIFICATION-TYPE
            OBJECTS { eventAlarmPriority, eventAlarmClass, eventEvent, indexTransmitter }
            STATUS current
            DESCRIPTION 
                "NetCCU Connection To ExciterB Faulty"
            ::= { eventsTxV2 21 }

        
        txNetCCUNoConnectionToOstB NOTIFICATION-TYPE
            OBJECTS { eventAlarmPriority, eventAlarmClass, eventEvent, indexTransmitter }
            STATUS current
            DESCRIPTION 
                "NetCCU Connection To OutputstageB Faulty"
            ::= { eventsTxV2 22 }

        
        txAutomaticExcReady NOTIFICATION-TYPE
            OBJECTS { eventAlarmPriority, eventAlarmClass, eventEvent, indexTransmitter }
            STATUS current
            DESCRIPTION 
                "Exciter Automatic Ready."
            ::= { eventsTxV2 23 }

        
        txAutomaticExcChanged NOTIFICATION-TYPE
            OBJECTS { eventAlarmPriority, eventAlarmClass, eventEvent, indexTransmitter }
            STATUS current
            DESCRIPTION 
                "Exciter Automatic Changed."
            ::= { eventsTxV2 24 }

        
        txAutomaticExcFault NOTIFICATION-TYPE
            OBJECTS { eventAlarmPriority, eventAlarmClass, eventEvent, indexTransmitter }
            STATUS current
            DESCRIPTION 
                "Exciter Automatic Fault."
            ::= { eventsTxV2 25 }

        
        txAutomaticOstReady NOTIFICATION-TYPE
            OBJECTS { eventAlarmPriority, eventAlarmClass, eventEvent, indexTransmitter }
            STATUS current
            DESCRIPTION 
                "Outputstage Automatic Ready.
                
                This paramter is only available for systems with an automatic output switch."
            ::= { eventsTxV2 26 }

        
        txAutomaticOstChanged NOTIFICATION-TYPE
            OBJECTS { eventAlarmPriority, eventAlarmClass, eventEvent, indexTransmitter }
            STATUS current
            DESCRIPTION 
                "Outputstage Automatic Changed.
                
                This paramter is only available for systems with an automatic output switch."
            ::= { eventsTxV2 27 }

        
        txAutomaticOstFault NOTIFICATION-TYPE
            OBJECTS { eventAlarmPriority, eventAlarmClass, eventEvent, indexTransmitter }
            STATUS current
            DESCRIPTION 
                "Outputstage Automatic Fault.
                
                This paramter is only available for systems with an automatic output switch."
            ::= { eventsTxV2 28 }

        
        txNetCCUBoardTemperatureWarning NOTIFICATION-TYPE
            OBJECTS { eventAlarmPriority, eventAlarmClass, eventEvent, indexTransmitter }
            STATUS current
            DESCRIPTION 
                "NetCCU Board Temperature Warning"
            ::= { eventsTxV2 29 }

        
        txInternalPowerSupplyWarning NOTIFICATION-TYPE
            OBJECTS { eventAlarmPriority, eventAlarmClass, eventEvent, indexTransmitter }
            STATUS current
            DESCRIPTION 
                "NetCCU internal Power Supply warning"
            ::= { eventsTxV2 30 }

        
        txExternalPowerSupplyWarning NOTIFICATION-TYPE
            OBJECTS { eventAlarmPriority, eventAlarmClass, eventEvent, indexTransmitter }
            STATUS current
            DESCRIPTION 
                "NetCCU external (additional) Power Supply warning"
            ::= { eventsTxV2 31 }

        
        txNoConnectionApaIf NOTIFICATION-TYPE
            OBJECTS { eventAlarmPriority, eventAlarmClass, eventEvent, indexTransmitter }
            STATUS current
            DESCRIPTION 
                "NetCCU can not communicate to the APA-Interface."
            ::= { eventsTxV2 32 }

        
        txAbsorberFault NOTIFICATION-TYPE
            OBJECTS { eventAlarmPriority, eventAlarmClass, eventEvent, indexTransmitter }
            STATUS current
            DESCRIPTION 
                "Absorber fault occurred.
                "
            ::= { eventsTxV2 33 }

        
        txExcSummaryFault NOTIFICATION-TYPE
            OBJECTS { eventAlarmPriority, eventAlarmClass, eventEvent, indexTransmitter, indexAB
                 }
            STATUS current
            DESCRIPTION 
                "Exciter Summary Fault"
            ::= { eventsTxV2 100 }

        
        txExcSummaryWarning NOTIFICATION-TYPE
            OBJECTS { eventAlarmPriority, eventAlarmClass, eventEvent, indexTransmitter, indexAB
                 }
            STATUS current
            DESCRIPTION 
                "Exciter Summary Warning"
            ::= { eventsTxV2 101 }

        
        txExcRfOk NOTIFICATION-TYPE
            OBJECTS { eventAlarmPriority, eventAlarmClass, eventEvent, indexTransmitter, indexAB
                 }
            STATUS current
            DESCRIPTION 
                "Exciter RF Ok"
            ::= { eventsTxV2 104 }

        
        txExcInputNoConnectHP1 NOTIFICATION-TYPE
            OBJECTS { eventAlarmPriority, eventAlarmClass, eventEvent, indexTransmitter, indexAB
                 }
            STATUS current
            DESCRIPTION 
                "Exciter Input HP1 has no connected input signal"
            ::= { eventsTxV2 105 }

        
        txExcInputNoConnectLP1 NOTIFICATION-TYPE
            OBJECTS { eventAlarmPriority, eventAlarmClass, eventEvent, indexTransmitter, indexAB
                 }
            STATUS current
            DESCRIPTION 
                "Exciter Input LP1 has no connected input signal"
            ::= { eventsTxV2 106 }

        
        txExcInputNoConnectHP2 NOTIFICATION-TYPE
            OBJECTS { eventAlarmPriority, eventAlarmClass, eventEvent, indexTransmitter, indexAB
                 }
            STATUS current
            DESCRIPTION 
                "Exciter Input HP2 has no connected input signal"
            ::= { eventsTxV2 107 }

        
        txExcInputNoConnectLP2 NOTIFICATION-TYPE
            OBJECTS { eventAlarmPriority, eventAlarmClass, eventEvent, indexTransmitter, indexAB
                 }
            STATUS current
            DESCRIPTION 
                "Exciter Input LP2 has no connected input signal"
            ::= { eventsTxV2 108 }

        
        txExcInputActiveHP1 NOTIFICATION-TYPE
            OBJECTS { eventAlarmPriority, eventAlarmClass, eventEvent, indexTransmitter, indexAB
                 }
            STATUS current
            DESCRIPTION 
                "Exciter Input HP1 is active"
            ::= { eventsTxV2 109 }

        
        txExcInputActiveLP1 NOTIFICATION-TYPE
            OBJECTS { eventAlarmPriority, eventAlarmClass, eventEvent, indexTransmitter, indexAB
                 }
            STATUS current
            DESCRIPTION 
                "Exciter Input LP1 is active"
            ::= { eventsTxV2 110 }

        
        txExcInputActiveHP2 NOTIFICATION-TYPE
            OBJECTS { eventAlarmPriority, eventAlarmClass, eventEvent, indexTransmitter, indexAB
                 }
            STATUS current
            DESCRIPTION 
                "Exciter Input HP2 is active"
            ::= { eventsTxV2 111 }

        
        txExcInputActiveLP2 NOTIFICATION-TYPE
            OBJECTS { eventAlarmPriority, eventAlarmClass, eventEvent, indexTransmitter, indexAB
                 }
            STATUS current
            DESCRIPTION 
                "Exciter Input LP2 is active"
            ::= { eventsTxV2 112 }

        
        txExcOn NOTIFICATION-TYPE
            OBJECTS { eventAlarmPriority, eventAlarmClass, eventEvent, indexTransmitter, indexAB
                 }
            STATUS current
            DESCRIPTION 
                "Exciter On"
            ::= { eventsTxV2 113 }

        
        txExcRfOn NOTIFICATION-TYPE
            OBJECTS { eventAlarmPriority, eventAlarmClass, eventEvent, indexTransmitter, indexAB
                 }
            STATUS current
            DESCRIPTION 
                "Exciter RF On"
            ::= { eventsTxV2 114 }

        
        txExcNoInput NOTIFICATION-TYPE
            OBJECTS { eventAlarmPriority, eventAlarmClass, eventEvent, indexTransmitter, indexAB
                 }
            STATUS current
            DESCRIPTION 
                "Exciter has no valid input signal."
            ::= { eventsTxV2 115 }

        
        txExcRfLoop NOTIFICATION-TYPE
            OBJECTS { eventAlarmPriority, eventAlarmClass, eventEvent, indexTransmitter, indexAB
                 }
            STATUS current
            DESCRIPTION 
                "Exciter RF loop"
            ::= { eventsTxV2 116 }

        
        txExcRfFail NOTIFICATION-TYPE
            OBJECTS { eventAlarmPriority, eventAlarmClass, eventEvent, indexTransmitter, indexAB
                 }
            STATUS current
            DESCRIPTION 
                "Exciter RF Fail"
            ::= { eventsTxV2 117 }

        
        txExcSelfTest NOTIFICATION-TYPE
            OBJECTS { eventAlarmPriority, eventAlarmClass, eventEvent, indexTransmitter, indexAB
                 }
            STATUS current
            DESCRIPTION 
                "Exciter hardware self test"
            ::= { eventsTxV2 118 }

        
        txExcOutputOpen NOTIFICATION-TYPE
            OBJECTS { eventAlarmPriority, eventAlarmClass, eventEvent, indexTransmitter, indexAB
                 }
            STATUS current
            DESCRIPTION 
                "Exciter output open"
            ::= { eventsTxV2 119 }

        
        txExcBoardTemperatureWarning NOTIFICATION-TYPE
            OBJECTS { eventAlarmPriority, eventAlarmClass, eventEvent, indexTransmitter, indexAB
                 }
            STATUS current
            DESCRIPTION 
                "Exciter Board Temperature"
            ::= { eventsTxV2 120 }

        
        txExcFanWarning NOTIFICATION-TYPE
            OBJECTS { eventAlarmPriority, eventAlarmClass, eventEvent, indexTransmitter, indexAB
                 }
            STATUS current
            DESCRIPTION 
                "Exciter has one faulty fan"
            ::= { eventsTxV2 121 }

        
        txExcFanFault NOTIFICATION-TYPE
            OBJECTS { eventAlarmPriority, eventAlarmClass, eventEvent, indexTransmitter, indexAB
                 }
            STATUS current
            DESCRIPTION 
                "Both exciter fans are faulty."
            ::= { eventsTxV2 122 }

        
        txExcFifoWarning NOTIFICATION-TYPE
            OBJECTS { eventAlarmPriority, eventAlarmClass, eventEvent, indexTransmitter, indexAB
                 }
            STATUS current
            DESCRIPTION 
                "Exciter Fifo"
            ::= { eventsTxV2 123 }

        
        txExcTestSignal NOTIFICATION-TYPE
            OBJECTS { eventAlarmPriority, eventAlarmClass, eventEvent, indexTransmitter, indexAB
                 }
            STATUS current
            DESCRIPTION 
                "Exciter Testsignal Active"
            ::= { eventsTxV2 124 }

        
        txExcSFNDelay NOTIFICATION-TYPE
            OBJECTS { eventAlarmPriority, eventAlarmClass, eventEvent, indexTransmitter, indexAB
                 }
            STATUS current
            DESCRIPTION 
                "Exciter SFN Delay Fault"
            ::= { eventsTxV2 125 }

        
        txExcWrongDatarate NOTIFICATION-TYPE
            OBJECTS { eventAlarmPriority, eventAlarmClass, eventEvent, indexTransmitter, indexAB
                 }
            STATUS current
            DESCRIPTION 
                "Exciter Wrong Datarate"
            ::= { eventsTxV2 126 }

        
        txExcMute NOTIFICATION-TYPE
            OBJECTS { eventAlarmPriority, eventAlarmClass, eventEvent, indexTransmitter, indexAB
                 }
            STATUS current
            DESCRIPTION 
                "Exciter Mute"
            ::= { eventsTxV2 127 }

        
        txExcPPSFail NOTIFICATION-TYPE
            OBJECTS { eventAlarmPriority, eventAlarmClass, eventEvent, indexTransmitter, indexAB
                 }
            STATUS current
            DESCRIPTION 
                "Exciter PPS Fail"
            ::= { eventsTxV2 128 }

        
        txExcReferenceFail NOTIFICATION-TYPE
            OBJECTS { eventAlarmPriority, eventAlarmClass, eventEvent, indexTransmitter, indexAB
                 }
            STATUS current
            DESCRIPTION 
                "Exciter Reference Fail"
            ::= { eventsTxV2 129 }

        
        txExcMIPFail NOTIFICATION-TYPE
            OBJECTS { eventAlarmPriority, eventAlarmClass, eventEvent, indexTransmitter, indexAB
                 }
            STATUS current
            DESCRIPTION 
                "Exciter MIP Fail"
            ::= { eventsTxV2 130 }

        
        txExcInputAutomaticSwitchReady NOTIFICATION-TYPE
            OBJECTS { eventAlarmPriority, eventAlarmClass, eventEvent, indexTransmitter, indexAB
                 }
            STATUS current
            DESCRIPTION 
                "Input automatic is ready."
            ::= { eventsTxV2 131 }

        
        txExcInputAutomaticChangedOver NOTIFICATION-TYPE
            OBJECTS { eventAlarmPriority, eventAlarmClass, eventEvent, indexTransmitter, indexAB
                 }
            STATUS current
            DESCRIPTION 
                "Input automatic changed over."
            ::= { eventsTxV2 132 }

        
        txExcInputReseveMissing NOTIFICATION-TYPE
            STATUS current
            DESCRIPTION 
                "Missing input, or automatic switching enabled with only one input present.
                Disable automatic switching or press reset fault to remove this warning.
                Monitoring of a second input will start automatically if two input signals have been detected.
                
                This event will be generated only if cmdExcExpectInputReserve is set to on(1)."
            ::= { eventsTxV2 133 }

        
        txOstSummaryFault NOTIFICATION-TYPE
            OBJECTS { eventAlarmPriority, eventAlarmClass, eventEvent, indexTransmitter, indexAB
                 }
            STATUS current
            DESCRIPTION 
                "Outputstage Summary Fault"
            ::= { eventsTxV2 200 }

        
        txOstSummaryWarning NOTIFICATION-TYPE
            OBJECTS { eventAlarmPriority, eventAlarmClass, eventEvent, indexTransmitter, indexAB
                 }
            STATUS current
            DESCRIPTION 
                "Outputstage Summary Warning"
            ::= { eventsTxV2 201 }

        
        txOstRfOn NOTIFICATION-TYPE
            OBJECTS { eventAlarmPriority, eventAlarmClass, eventEvent, indexTransmitter, indexAB
                 }
            STATUS current
            DESCRIPTION 
                "Outputstage RF On"
            ::= { eventsTxV2 202 }

        
        txOstRfOk NOTIFICATION-TYPE
            OBJECTS { eventAlarmPriority, eventAlarmClass, eventEvent, indexTransmitter, indexAB
                 }
            STATUS current
            DESCRIPTION 
                "Outputstage RF Ok"
            ::= { eventsTxV2 203 }

        
        txOstNoInput NOTIFICATION-TYPE
            OBJECTS { eventAlarmPriority, eventAlarmClass, eventEvent, indexTransmitter, indexAB
                 }
            STATUS current
            DESCRIPTION 
                "Outputstage no input signal"
            ::= { eventsTxV2 204 }

        
        txOstRfWarning NOTIFICATION-TYPE
            OBJECTS { eventAlarmPriority, eventAlarmClass, eventEvent, indexTransmitter, indexAB
                 }
            STATUS current
            DESCRIPTION 
                "Outputstage RF Warning"
            ::= { eventsTxV2 205 }

        
        txOstReflectionWarning NOTIFICATION-TYPE
            OBJECTS { eventAlarmPriority, eventAlarmClass, eventEvent, indexTransmitter, indexAB
                 }
            STATUS current
            DESCRIPTION 
                "Outputstage Reflection Warning"
            ::= { eventsTxV2 206 }

        
        txOstRackWarning NOTIFICATION-TYPE
            OBJECTS { eventAlarmPriority, eventAlarmClass, eventEvent, indexTransmitter, indexAB
                 }
            STATUS current
            DESCRIPTION 
                "Outputstage Rack Warning. At least one rack has an error pending."
            ::= { eventsTxV2 207 }

        
        txOstCoolingWarning NOTIFICATION-TYPE
            OBJECTS { eventAlarmPriority, eventAlarmClass, eventEvent, indexTransmitter, indexAB
                 }
            STATUS current
            DESCRIPTION 
                "Outputstage Cooling Warning"
            ::= { eventsTxV2 208 }

        
        txOstRfFail NOTIFICATION-TYPE
            OBJECTS { eventAlarmPriority, eventAlarmClass, eventEvent, indexTransmitter, indexAB
                 }
            STATUS current
            DESCRIPTION 
                "Outputstage RF Fail"
            ::= { eventsTxV2 209 }

        
        txOstReflectionFault NOTIFICATION-TYPE
            OBJECTS { eventAlarmPriority, eventAlarmClass, eventEvent, indexTransmitter, indexAB
                 }
            STATUS current
            DESCRIPTION 
                "Outputstage Reflection Fault"
            ::= { eventsTxV2 210 }

        
        txOstACFault NOTIFICATION-TYPE
            OBJECTS { eventAlarmPriority, eventAlarmClass, eventEvent, indexTransmitter, indexAB
                 }
            STATUS current
            DESCRIPTION 
                "Outputstage AC Fault"
            ::= { eventsTxV2 211 }

        
        txOstCoolingFault NOTIFICATION-TYPE
            OBJECTS { eventAlarmPriority, eventAlarmClass, eventEvent, indexTransmitter, indexAB
                 }
            STATUS current
            DESCRIPTION 
                "Outputstage Cooling Fault"
            ::= { eventsTxV2 212 }

        
        txOstCommFault NOTIFICATION-TYPE
            OBJECTS { eventAlarmPriority, eventAlarmClass, eventEvent, indexTransmitter, indexAB
                 }
            STATUS current
            DESCRIPTION 
                "Outputstage Communication Fault"
            ::= { eventsTxV2 213 }

        
        txRackSumFault NOTIFICATION-TYPE
            OBJECTS { eventAlarmPriority, eventAlarmClass, eventEvent, indexTransmitter, indexAB, 
                indexRack }
            STATUS current
            DESCRIPTION 
                "Summary Fault at a designated rack.
                This event automatically leads to txOstRackWarning."
            ::= { eventsTxV2 300 }

        
        txRackSumWarning NOTIFICATION-TYPE
            OBJECTS { eventAlarmPriority, eventAlarmClass, eventEvent, indexTransmitter, indexAB, 
                indexRack }
            STATUS current
            DESCRIPTION 
                "Summary Warning at a designated rack."
            ::= { eventsTxV2 301 }

        
        txRackOn NOTIFICATION-TYPE
            OBJECTS { eventAlarmPriority, eventAlarmClass, eventEvent, indexTransmitter, indexAB, 
                indexRack }
            STATUS current
            DESCRIPTION 
                "The designated racks operation mode is on."
            ::= { eventsTxV2 302 }

        
        txRackGpiWarning NOTIFICATION-TYPE
            OBJECTS { eventAlarmPriority, eventAlarmClass, eventEvent, indexTransmitter, indexAB, 
                indexRack }
            STATUS current
            DESCRIPTION 
                "A warning on the general purpose input occurred.
                This depends on the current configuration of the GPI. (See:Rack Setup/Rack Controller)"
            ::= { eventsTxV2 303 }

        
        txRackFan1Fault NOTIFICATION-TYPE
            OBJECTS { eventAlarmPriority, eventAlarmClass, eventEvent, indexTransmitter, indexAB, 
                indexRack }
            STATUS current
            DESCRIPTION 
                "The designated rack signals a fault of fan 1."
            ::= { eventsTxV2 304 }

        
        txRackFan2Fault NOTIFICATION-TYPE
            OBJECTS { eventAlarmPriority, eventAlarmClass, eventEvent, indexTransmitter, indexAB, 
                indexRack }
            STATUS current
            DESCRIPTION 
                "The designated rack signals a fault of fan 2."
            ::= { eventsTxV2 305 }

        
        txRackCoolingSumWarning NOTIFICATION-TYPE
            OBJECTS { eventAlarmPriority, eventAlarmClass, eventEvent, indexTransmitter, indexAB, 
                indexRack }
            STATUS current
            DESCRIPTION 
                "The designated rack signals a summary cooling warning."
            ::= { eventsTxV2 306 }

        
        txRackAmplifierSumFault NOTIFICATION-TYPE
            OBJECTS { eventAlarmPriority, eventAlarmClass, eventEvent, indexTransmitter, indexAB, 
                indexRack }
            STATUS current
            DESCRIPTION 
                "The designated rack signals at least one faulty amplifier."
            ::= { eventsTxV2 307 }

        
        txRackNoLink NOTIFICATION-TYPE
            OBJECTS { eventAlarmPriority, eventAlarmClass, eventEvent, indexTransmitter, indexAB, 
                indexRack }
            STATUS current
            DESCRIPTION 
                "No communication to the designated rack."
            ::= { eventsTxV2 308 }

        
        txRackGpiFault NOTIFICATION-TYPE
            OBJECTS { eventAlarmPriority, eventAlarmClass, eventEvent, indexTransmitter, indexAB, 
                indexRack }
            STATUS current
            DESCRIPTION 
                "A fault on the general purpose input occurred.
                This depends on the current configuration of the GPI. (See:Rack Setup/Rack Controller)"
            ::= { eventsTxV2 309 }

        
        txRackTemperatureFault NOTIFICATION-TYPE
            OBJECTS { eventAlarmPriority, eventAlarmClass, eventEvent, indexTransmitter, indexAB, 
                indexRack }
            STATUS current
            DESCRIPTION 
                "The designated rack signals a temperature fault - temperature too high."
            ::= { eventsTxV2 310 }

        
        txRackACFault NOTIFICATION-TYPE
            OBJECTS { eventAlarmPriority, eventAlarmClass, eventEvent, indexTransmitter, indexAB, 
                indexRack }
            STATUS current
            DESCRIPTION 
                "The designated rack signals an AC (phase) fault."
            ::= { eventsTxV2 311 }

        
        txRackCoolingSumFault NOTIFICATION-TYPE
            OBJECTS { eventAlarmPriority, eventAlarmClass, eventEvent, indexTransmitter, indexAB, 
                indexRack }
            STATUS current
            DESCRIPTION 
                "The designated rack signals a summary cooling fault."
            ::= { eventsTxV2 312 }

        
        txRackTempFaultAbs1 NOTIFICATION-TYPE
            OBJECTS { eventAlarmPriority, eventAlarmClass, eventEvent, indexTransmitter, indexAB, 
                indexRack }
            STATUS current
            DESCRIPTION 
                "The designated rack signals a temperature fault of absorber 1."
            ::= { eventsTxV2 313 }

        
        txRackTempFaultAbs2 NOTIFICATION-TYPE
            OBJECTS { eventAlarmPriority, eventAlarmClass, eventEvent, indexTransmitter, indexAB, 
                indexRack }
            STATUS current
            DESCRIPTION 
                "The designated rack signals a temperature fault of absorber 2."
            ::= { eventsTxV2 314 }

        
        txRackDCFault NOTIFICATION-TYPE
            OBJECTS { eventAlarmPriority, eventAlarmClass, eventEvent, indexTransmitter, indexAB, 
                indexRack }
            STATUS current
            DESCRIPTION 
                "The designated rack signals a DC fault."
            ::= { eventsTxV2 315 }

        
        txRackRfOn NOTIFICATION-TYPE
            OBJECTS { eventAlarmPriority, eventAlarmClass, eventEvent, indexAB, indexRack
                 }
            STATUS current
            DESCRIPTION 
                "RF power is on."
            ::= { eventsTxV2 318 }

        
        txRackRfOk NOTIFICATION-TYPE
            OBJECTS { eventAlarmPriority, eventAlarmClass, eventEvent, indexAB, indexRack
                 }
            STATUS current
            DESCRIPTION 
                "RF power is ok."
            ::= { eventsTxV2 319 }

        
        txRackRfWarning NOTIFICATION-TYPE
            OBJECTS { eventAlarmPriority, eventAlarmClass, eventEvent, indexTransmitter, indexAB, 
                indexRack }
            STATUS current
            DESCRIPTION 
                "RF power decreased the warning threshold."
            ::= { eventsTxV2 320 }

        
        txRackRfFault NOTIFICATION-TYPE
            OBJECTS { eventAlarmPriority, eventAlarmClass, eventEvent, indexTransmitter, indexAB, 
                indexRack }
            STATUS current
            DESCRIPTION 
                "RF output power decreased the fault threshold."
            ::= { eventsTxV2 321 }

        
        txRackReflectionWarning NOTIFICATION-TYPE
            OBJECTS { eventAlarmPriority, eventAlarmClass, eventEvent, indexTransmitter, indexAB, 
                indexRack }
            STATUS current
            DESCRIPTION 
                "The reflected power increased the warning threshold"
            ::= { eventsTxV2 322 }

        
        txRackReflectionFault NOTIFICATION-TYPE
            OBJECTS { eventAlarmPriority, eventAlarmClass, eventEvent, indexTransmitter, indexAB, 
                indexRack }
            STATUS current
            DESCRIPTION 
                "The reflected power increased the fault threshold."
            ::= { eventsTxV2 323 }

        
        txRackProbeNotCalibrated NOTIFICATION-TYPE
            OBJECTS { eventAlarmPriority, eventAlarmClass, eventEvent, indexTransmitter, indexAB, 
                indexRack }
            STATUS current
            DESCRIPTION 
                "At least one probe is not calibrated."
            ::= { eventsTxV2 330 }

        
        txRackTemperatureWarning NOTIFICATION-TYPE
            OBJECTS { eventAlarmPriority, eventAlarmClass, eventEvent, indexAB, indexRack
                 }
            STATUS current
            DESCRIPTION 
                "Rack temperature exceeded the warning threshold."
            ::= { eventsTxV2 331 }

        
        txRackOvervoltProtectWarning NOTIFICATION-TYPE
            OBJECTS { eventAlarmPriority, eventAlarmClass, eventEvent, indexAB, indexRack
                 }
            STATUS current
            DESCRIPTION 
                "Overvoltage protection is out of order."
            ::= { eventsTxV2 335 }

        
        txAmpSumFault NOTIFICATION-TYPE
            OBJECTS { eventAlarmPriority, eventAlarmClass, eventEvent, indexTransmitter, indexAB, 
                indexRack, indexAmplifier }
            STATUS current
            DESCRIPTION 
                "The designated amplifier signals summary fault."
            ::= { eventsTxV2 400 }

        
        txAmpSumWarning NOTIFICATION-TYPE
            OBJECTS { eventAlarmPriority, eventAlarmClass, eventEvent, indexTransmitter, indexAB, 
                indexRack, indexAmplifier }
            STATUS current
            DESCRIPTION 
                "The designated amplifier signals summary warning."
            ::= { eventsTxV2 401 }

        
        txAmpPowerOn NOTIFICATION-TYPE
            OBJECTS { eventAlarmPriority, eventAlarmClass, eventEvent, indexTransmitter, indexAB, 
                indexRack, indexAmplifier }
            STATUS current
            DESCRIPTION 
                "The designated amplifiers power is on."
            ::= { eventsTxV2 402 }

        
        txAmpDCOk NOTIFICATION-TYPE
            OBJECTS { eventAlarmPriority, eventAlarmClass, eventEvent, indexTransmitter, indexAB, 
                indexRack, indexAmplifier }
            STATUS current
            DESCRIPTION 
                "The designated amplifiers DC is ok."
            ::= { eventsTxV2 403 }

        
        txAmpACOk NOTIFICATION-TYPE
            OBJECTS { eventAlarmPriority, eventAlarmClass, eventEvent, indexTransmitter, indexAB, 
                indexRack, indexAmplifier }
            STATUS current
            DESCRIPTION 
                "The designated amplifiers AC is ok."
            ::= { eventsTxV2 404 }

        
        txAmpRfInFail NOTIFICATION-TYPE
            OBJECTS { eventAlarmPriority, eventAlarmClass, eventEvent, indexTransmitter, indexAB, 
                indexRack, indexAmplifier }
            STATUS current
            DESCRIPTION 
                "The designated amplifier signals RF input fail."
            ::= { eventsTxV2 405 }

        
        txAmpRfFail NOTIFICATION-TYPE
            OBJECTS { eventAlarmPriority, eventAlarmClass, eventEvent, indexTransmitter, indexAB, 
                indexRack, indexAmplifier }
            STATUS current
            DESCRIPTION 
                "The designated amplifier signals RF fail."
            ::= { eventsTxV2 406 }

        
        txAmpReflectionFault NOTIFICATION-TYPE
            OBJECTS { eventAlarmPriority, eventAlarmClass, eventEvent, indexTransmitter, indexAB, 
                indexRack, indexAmplifier }
            STATUS current
            DESCRIPTION 
                "The designated amplifier signals a reflection fault."
            ::= { eventsTxV2 407 }

        
        txAmpTemperatureFault NOTIFICATION-TYPE
            OBJECTS { eventAlarmPriority, eventAlarmClass, eventEvent, indexTransmitter, indexAB, 
                indexRack, indexAmplifier }
            STATUS current
            DESCRIPTION 
                "The designated amplifier signals a temperature fault - temperature is too high."
            ::= { eventsTxV2 408 }

        
        txAmpTransistorFault NOTIFICATION-TYPE
            OBJECTS { eventAlarmPriority, eventAlarmClass, eventEvent, indexTransmitter, indexAB, 
                indexRack, indexAmplifier }
            STATUS current
            DESCRIPTION 
                "The designated amplifier signals at least one faulty transistor."
            ::= { eventsTxV2 409 }

        
        eventsTxTable OBJECT-TYPE
            SYNTAX SEQUENCE OF EventsTxEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventTx 1 }

        
        eventsTxEntry OBJECT-TYPE
            SYNTAX EventsTxEntry
            MAX-ACCESS not-accessible
            STATUS current
            DESCRIPTION
                "An event entry always consists of its indexes
                (used for addressing within redundancy systems) and 3 values:
                - name: an enumerated list of all possible notifications
                - mask: the corresponding mask (enable/disable)
                - priority: the corresponding priority (value in range 0..255)
                - event: the event itself (active/inactive)"
            INDEX { eventTxIdx, eventTxABIdx, eventTxRackIdx, eventTxAmpIdx, eventTxNameIdx
                 }
            ::= { eventsTxTable 1 }

        
        EventsTxEntry ::=
            SEQUENCE { 
                eventTxIdx
                    IndexTransmitter,
                eventTxABIdx
                    IndexAB,
                eventTxRackIdx
                    IndexRack,
                eventTxAmpIdx
                    IndexAmplifier,
                eventTxNameIdx
                    EventMaxEntryNumber,
                eventTxName
                    INTEGER,
                eventTxMask
                    EventMask,
                eventTxPriority
                    EventPriority,
                eventTxEvent
                    EventState
             }

        eventTxIdx OBJECT-TYPE
            SYNTAX IndexTransmitter
            MAX-ACCESS not-accessible
            STATUS current
            DESCRIPTION
                "The transmitter index.
                This is a helper column and therefore not-accessible.."
            ::= { eventsTxEntry 1 }

        
        eventTxABIdx OBJECT-TYPE
            SYNTAX IndexAB
            MAX-ACCESS not-accessible
            STATUS current
            DESCRIPTION
                "The value for the module A (exciterA, outputstageA) or 
                B (exciterB, outputstageB) for alarms.
                This is a helper column and therefore not-accessible."
            ::= { eventsTxEntry 2 }

        
        eventTxRackIdx OBJECT-TYPE
            SYNTAX IndexRack
            MAX-ACCESS not-accessible
            STATUS current
            DESCRIPTION
                "The number of the designated rack.
                This is a helper column and therefore not-accessible."
            ::= { eventsTxEntry 3 }

        
        eventTxAmpIdx OBJECT-TYPE
            SYNTAX IndexAmplifier
            MAX-ACCESS not-accessible
            STATUS current
            DESCRIPTION
                "The number of the designated amplifier.
                This is a helper column and therefore not-accessible."
            ::= { eventsTxEntry 4 }

        
        eventTxNameIdx OBJECT-TYPE
            SYNTAX EventMaxEntryNumber
            MAX-ACCESS not-accessible
            STATUS current
            DESCRIPTION
                "The event number as integer.
                This is a helper column and therefore not-accessible."
            ::= { eventsTxEntry 5 }

        
        eventTxName OBJECT-TYPE
            SYNTAX INTEGER
                {
                txSummaryFault(1),
                txSummaryWarning(2),
                txLocal(3),
                txRfOn(4),
                txRfOk(5),
                txParamSetSubDeviceDiffers(6),
                txParamSetValuesChanged(7),
                txRfLoopProgram(8),
                txRfLoopReserve(9),
                txRfWarning(10),
                txReflectionWarning(11),
                txNoConnection(12),
                txNetCCUFanFault(14),
                txNetCCUPowerSupply(15),
                txRfFail(16),
                txReflectionFault(17),
                txNetCCUBoardTemperatureFault(18),
                txNetCCUNoConnectionToExcA(19),
                txNetCCUNoConnectionToOstA(20),
                txNetCCUNoConnectionToExcB(21),
                txNetCCUNoConnectionToOstB(22),
                txAutomaticExcReady(23),
                txAutomaticExcChanged(24),
                txAutomaticExcFault(25),
                txAutomaticOstReady(26),
                txAutomaticOstChanged(27),
                txAutomaticOstFault(28),
                txNetCCUBoardTemperatureWarning(29),
                txInternalPowerSupplyWarning(30),
                txExternalPowerSupplyWarning(31),
                txNoConnectionApaIf(32),
                txAbsorberFault(33),
                txExcSummaryFault(100),
                txExcSummaryWarning(101),
                txExcRfOk(104),
                txExcInputNoConnectHP1(105),
                txExcInputNoConnectLP1(106),
                txExcInputNoConnectHP2(107),
                txExcInputNoConnectLP2(108),
                txExcInputActiveHP1(109),
                txExcInputActiveLP1(110),
                txExcInputActiveHP2(111),
                txExcInputActiveLP2(112),
                txExcOn(113),
                txExcRfOn(114),
                txExcNoInput(115),
                txExcRfLoop(116),
                txExcRfFail(117),
                txExcSelfTest(118),
                txExcOutputOpen(119),
                txExcBoardTemperatureWarning(120),
                txExcFanWarning(121),
                txExcFanFault(122),
                txExcFifoWarning(123),
                txExcTestSignal(124),
                txExcSFNDelay(125),
                txExcWrongDatarate(126),
                txExcMute(127),
                txExcPPSFail(128),
                txExcReferenceFail(129),
                txExcMIPFail(130),
                txExcInputAutomaticSwitchReady(131),
                txExcInputAutomaticChangedOver(132),
                txExcInputReseveMissing(133),
                txOstSummaryFault(200),
                txOstSummaryWarning(201),
                txOstRfOn(202),
                txOstRfOk(203),
                txOstNoInput(204),
                txOstRfWarning(205),
                txOstReflectionWarning(206),
                txOstRackWarning(207),
                txOstCoolingWarning(208),
                txOstRfFail(209),
                txOstReflectionFault(210),
                txOstACFault(211),
                txOstCoolingFault(212),
                txOstCommFault(213),
                txRackSumFault(300),
                txRackSumWarning(301),
                txRackOn(302),
                txRackGpiWarning(303),
                txRackFan1Fault(304),
                txRackFan2Fault(305),
                txRackCoolingSumWarning(306),
                txRackAmplifierSumFault(307),
                txRackNoLink(308),
                txRackGpiFault(309),
                txRackTemperatureFault(310),
                txRackACFault(311),
                txRackCoolingSumFault(312),
                txRackTempFaultAbs1(313),
                txRackTempFaultAbs2(314),
                txRackDCFault(315),
                txRackRfOn(318),
                txRackRfOk(319),
                txRackRfWarning(320),
                txRackRfFault(321),
                txRackReflectionWarning(322),
                txRackReflectionFault(323),
                txRackProbeNotCalibrated(330),
                txRackTemperatureWarning(331),
                txRackOvervoltProtectWarning(335),
                txAmpSumFault(400),
                txAmpSumWarning(401),
                txAmpPowerOn(402),
                txAmpDCOk(403),
                txAmpACOk(404),
                txAmpRfInFail(405),
                txAmpRfFail(406),
                txAmpReflectionFault(407),
                txAmpTemperatureFault(408),
                txAmpTransistorFault(409)
                }
            MAX-ACCESS read-only
            STATUS current
            DESCRIPTION
                "The event number as integer and the value as readable text.
                The enumeration correlates with the notifications under eventsTxV2."
            ::= { eventsTxEntry 6 }

        
        eventTxMask OBJECT-TYPE
            SYNTAX EventMask
            MAX-ACCESS read-write
            STATUS current
            DESCRIPTION
                "See TextualConvention for details."
            ::= { eventsTxEntry 7 }

        
        eventTxPriority OBJECT-TYPE
            SYNTAX EventPriority
            MAX-ACCESS read-write
            STATUS current
            DESCRIPTION
                "See TextualConvention for details."
            ::= { eventsTxEntry 8 }

        
        eventTxEvent OBJECT-TYPE
            SYNTAX EventState
            MAX-ACCESS read-only
            STATUS current
            DESCRIPTION
                "See TextualConvention for details."
            ::= { eventsTxEntry 9 }

        
-- *****************************************************************************
-- **          conformance statements
-- *****************************************************************************
        rsXx8000DvbNTxConf OBJECT IDENTIFIER ::= { rsXx8000DvbNTx 5 }

        
        rsXx8000DvbNTxGroups OBJECT IDENTIFIER ::= { rsXx8000DvbNTxConf 1 }

        
        groupNcuObjs OBJECT-GROUP
            OBJECTS { resetAllFaults, summaryFaultNCU, summaryWarningNCU, localModeNCU, ncuNumberOfEntries, 
                ncuLogbookClear, ncuLogbookEntryNbr, ncuLogbookType, ncuLogbookSlope, ncuLogbookMessage, 
                ncuLogbookDateTime, additionalPowerSupply, powerSupply }
            STATUS current
            DESCRIPTION 
                "Group for all objects of the designated NCU (Tx Control Unit)."
            ::= { rsXx8000DvbNTxGroups 1 }

        
        groupNcuEvents NOTIFICATION-GROUP
            NOTIFICATIONS { ncuSummaryFault, ncuSummaryWarning, ncuLocal, ncuFanWarning, ncuPowerSupply, 
                ncuBoardTemperatureWarning }
            STATUS current
            DESCRIPTION 
                "Group for all events of the NCU (Tx Control Unit)."
            ::= { rsXx8000DvbNTxGroups 2 }

        
        groupNcuEventsAddPowerSupply NOTIFICATION-GROUP
            NOTIFICATIONS { ncuInternalPowerSupplyWarning, ncuExternalPowerSupplyWarning }
            STATUS current
            DESCRIPTION 
                "Events that are available only when additionalPowerSupply is true."
            ::= { rsXx8000DvbNTxGroups 3 }

        
        groupNsuObjsAddPowerSupply OBJECT-GROUP
            OBJECTS { internalPowerSupply, externalPowerSupply }
            STATUS current
            DESCRIPTION 
                "Objects that are available only when additionalPowerSupply is true."
            ::= { rsXx8000DvbNTxGroups 4 }

        
        groupTxObjsMp OBJECT-GROUP
            OBJECTS { cmdTxName, cmdTxResetSumFault, cmdTxParametersetLoad, cmdTxParametersetSave, cmdOstRefVoltageVision, 
                cmdOstMaxOutletTempThreshold, statusTxName, statusTxNoConnection, statusTxSummaryFault, statusTxSummaryWarning, 
                statusTxLocalMode, statusTxRfOn, statusTxForwardPower, statusTxReflectedPower, statusTxSummaryFaultExcA, 
                statusTxSummaryFaultOstA, statusTxNoConnectionExcA, statusTxAdditionalPowerSupply, statusTxPowerSupply, statusTxNoConnectionOstA, 
                cmdTxOpModeProgram }
            STATUS current
            DESCRIPTION 
                "Group for objects of transmitters in case of MediumPower."
            ::= { rsXx8000DvbNTxGroups 11 }

        
        groupTxObjsLp OBJECT-GROUP
            OBJECTS { cmdTxName, cmdTxResetSumFault, cmdTxParametersetLoad, cmdTxParametersetSave, cmdTxOpModeProgram, 
                statusTxName, statusTxNoConnection, statusTxSummaryFault, statusTxSummaryWarning, statusTxLocalMode, 
                statusTxRfOn, statusTxForwardPower, statusTxSummaryFaultExcA, statusTxSummaryFaultOstA }
            STATUS current
            DESCRIPTION 
                "Group for objects of transmitters in case of LowPower."
            ::= { rsXx8000DvbNTxGroups 13 }

        
        groupTxObjsExc OBJECT-GROUP
            OBJECTS { cmdExcOpModeInputAutomatic, cmdExcPreselectInput, cmdExcMode, cmdExcNetworkMode, cmdExcTPSSource, 
                cmdExcEnableCellID, cmdExcTxAddress, cmdExcTxAutomatic, cmdExcInputSeamless, cmdExcInputPriority, 
                cmdExcInputCheckTimeForward, cmdExcInputCheckTimeSwitchback, cmdExcInputMuteOnFail, cmdExcInputManualPreseletionHP1, cmdExcInputManualPreseletionHP2, 
                cmdExcInputManualPreseletionLP1, cmdExcInputManualPreseletionLP2, cmdExcTPSManualBandwidth, cmdExcTPSManualFFTLength, cmdExcTPSManualGuardInterval, 
                cmdExcTPSManualConstellation, cmdExcTPSManualCellID, cmdExcTPSManualInterleaver, cmdExcTPSManualCoderateHP, cmdExcTPSManualCoderateLP, 
                cmdExcTPSManualTimeSlicingHP, cmdExcTPSManualTimeSlicingLP, cmdExcTPSManualFECHP, cmdExcTPSManualFECLP, cmdExcSFNStaticDelay, 
                cmdExcSFNDeviationTime, cmdExcFrequency, cmdExcReferenceSource, cmdExcMuteOnPPSFail, cmdExcMuteOnReferenceFail, 
                cmdExcTypeLossOfInput, cmdExcRfOutput, cmdExcRfOutputRegulation, cmdExcRfOutputManualRfLevel, cmdExcRfOutputAttenuation, 
                cmdExcRfOutputRfSlope, cmdExcRfOutputModulationSlope, cmdExcRfIqAdjustStart, cmdExcRfIqAdjustTestsignal, cmdExcRfIqAdjustBiasCoarseI, 
                cmdExcRfIqAdjustBiasCoarseQ, cmdExcRfIqAdjustBiasFineI, cmdExcRfIqAdjustBiasFineQ, cmdExcRfIqAdjustGainI, cmdExcRfIqAdjustGainQ, 
                cmdExcRfIqAdjustPhase, cmdExcInpAutoReadyAfterChangeOv, excStatusTxName, excStatusRfOutputAgcRegulation, excStatusRfIqAdjustAuto, 
                excStatusRfIqAdjustLO1Frequency, excStatusSfnDelayProcessing, excStatusSfnDelayDynamic, excStatusSfnDelayNetwork, excStatusSfnDelayTxOffset, 
                excStatusSfnDelayMaximum, excStatusSfnDelayTotal, excPrecTxName, excPrecLinCorrection, excPrecLinAutomaticADE, 
                excPrecLinMaxAmplitudeRipple, excPrecLinMaxGroupDelayRipple, excPrecLinAmplitudeRipple, excPrecLinGroupDelayRipple, excPrecLinInputLevel, 
                excPrecLinAutomatic, excPrecNonlinCorrection, excPrecNonlinAutomaticADE, excPrecNonlinThresholdShoulders, excPrecNonlinShoulderLeft, 
                excPrecNonlinShoulderRight, excPrecNonlinInputLevel, cmdExcInputFailDelayTime, cmdExcOcxoAdjust, cmdExcExpectInputReserve, 
                statusTxOstSwitch, statusTxExcSwitch, excStatusReqDataRateLP, excStatusReqDataRateHP, excStatusAmplifierControl, 
                excStatusFailDelay, cmdExcFailDelayMode, cmdExcTransparentTs, excPrecNonlinAutomatic, cmdExcRefFailDelayTime
                 }
            STATUS current
            DESCRIPTION 
                "Group for objects of exciter."
            ::= { rsXx8000DvbNTxGroups 20 }

        
        groupObjectsSx801Amplifier OBJECT-GROUP
            OBJECTS { sx801AmpRfOut, sx801AmpRfIn, sx801AmpReflection, sx801AmpOn, sx801AmpAC, 
                sx801AmpCommunication, sx801AmpTransistor, sx801AmpDriver, sx801AmpTemperature, sx801AmpBlower, 
                sx801AmpRegulation, sx801AmpUpdate, sx801Supply1Temperature, sx801Supply2Temperature, sx801SupplyRTemperature, 
                sx801Supply1DC, sx801Supply2DC, sx801SupplyRDC, sx801AmpValueI1, sx801AmpValueI2, 
                sx801AmpValueI3, sx801AmpValueI4, sx801AmpValueIPre, sx801AmpValueIDrv1, sx801AmpValueIDrv2, 
                sx801AmpValuePowerOut, sx801AmpValueReflection, sx801AmpValueVRef, sx801AmpValueVReg, sx801AmpValueTemperature, 
                sx801AmpValueMonAtt, sx801AmpValueVAux1, sx801AmpValueVAux2, sx801Supply1ValuePwr, sx801Supply2ValuePwr, 
                sx801Supply1ValueDc, sx801Supply2ValueDc }
            STATUS current
            DESCRIPTION 
                "Objects for Sx801 amplifier status."
            ::= { rsXx8000DvbNTxGroups 21 }

        
        groupTxObjsLogbookNetCCU OBJECT-GROUP
            OBJECTS { txA1NetCCUNumberOfEntries, txA1NetCCULogbookClear, txA1NetCCULogbookEntryNbr, txA1NetCCULogbookType, txA1NetCCULogbookSlope, 
                txA1NetCCULogbookMessage, txA1NetCCULogbookDateTime, txA2NetCCUNumberOfEntries, txA2NetCCULogbookClear, txA2NetCCULogbookEntryNbr, 
                txA2NetCCULogbookType, txA2NetCCULogbookSlope, txA2NetCCULogbookMessage, txA2NetCCULogbookDateTime, txA3NetCCUNumberOfEntries, 
                txA3NetCCULogbookClear, txA3NetCCULogbookEntryNbr, txA3NetCCULogbookType, txA3NetCCULogbookSlope, txA3NetCCULogbookMessage, 
                txA3NetCCULogbookDateTime, txA4NetCCUNumberOfEntries, txA4NetCCULogbookClear, txA4NetCCULogbookEntryNbr, txA4NetCCULogbookType, 
                txA4NetCCULogbookSlope, txA4NetCCULogbookMessage, txA4NetCCULogbookDateTime, txA5NetCCUNumberOfEntries, txA5NetCCULogbookClear, 
                txA5NetCCULogbookEntryNbr, txA5NetCCULogbookType, txA5NetCCULogbookSlope, txA5NetCCULogbookMessage, txA5NetCCULogbookDateTime, 
                txA6NetCCUNumberOfEntries, txA6NetCCULogbookClear, txA6NetCCULogbookEntryNbr, txA6NetCCULogbookType, txA6NetCCULogbookSlope, 
                txA6NetCCULogbookMessage, txA6NetCCULogbookDateTime, txA7NetCCUNumberOfEntries, txA7NetCCULogbookClear, txA7NetCCULogbookEntryNbr, 
                txA7NetCCULogbookType, txA7NetCCULogbookSlope, txA7NetCCULogbookMessage, txA7NetCCULogbookDateTime, txA8NetCCUNumberOfEntries, 
                txA8NetCCULogbookClear, txA8NetCCULogbookEntryNbr, txA8NetCCULogbookType, txA8NetCCULogbookSlope, txA8NetCCULogbookMessage, 
                txA8NetCCULogbookDateTime }
            STATUS current
            DESCRIPTION 
                "Group for objects of logbooks of NetCCU."
            ::= { rsXx8000DvbNTxGroups 30 }

        
        groupTxObjsLogbookExcA OBJECT-GROUP
            OBJECTS { txA1ExciterANumberOfEntries, txA1ExciterALogbookClear, txA1ExcALogbookEntryNbr, txA1ExcALogbookType, txA1ExcALogbookSlope, 
                txA1ExcALogbookMessage, txA1ExcALogbookDateTime, txA2ExciterANumberOfEntries, txA2ExciterALogbookClear, txA2ExcALogbookEntryNbr, 
                txA2ExcALogbookType, txA2ExcALogbookSlope, txA2ExcALogbookMessage, txA2ExcALogbookDateTime, txA3ExciterANumberOfEntries, 
                txA3ExciterALogbookClear, txA3ExcALogbookEntryNbr, txA3ExcALogbookType, txA3ExcALogbookSlope, txA3ExcALogbookMessage, 
                txA3ExcALogbookDateTime, txA4ExciterANumberOfEntries, txA4ExciterALogbookClear, txA4ExcALogbookEntryNbr, txA4ExcALogbookType, 
                txA4ExcALogbookSlope, txA4ExcALogbookMessage, txA4ExcALogbookDateTime, txA5ExciterANumberOfEntries, txA5ExciterALogbookClear, 
                txA5ExcALogbookEntryNbr, txA5ExcALogbookType, txA5ExcALogbookSlope, txA5ExcALogbookMessage, txA5ExcALogbookDateTime, 
                txA6ExciterANumberOfEntries, txA6ExciterALogbookClear, txA6ExcALogbookEntryNbr, txA6ExcALogbookType, txA6ExcALogbookSlope, 
                txA6ExcALogbookMessage, txA6ExcALogbookDateTime, txA7ExciterANumberOfEntries, txA7ExciterALogbookClear, txA7ExcALogbookEntryNbr, 
                txA7ExcALogbookType, txA7ExcALogbookSlope, txA7ExcALogbookMessage, txA7ExcALogbookDateTime, txA8ExciterANumberOfEntries, 
                txA8ExciterALogbookClear, txA8ExcALogbookEntryNbr, txA8ExcALogbookType, txA8ExcALogbookSlope, txA8ExcALogbookMessage, 
                txA8ExcALogbookDateTime }
            STATUS current
            DESCRIPTION 
                "Group for objects of logbooks of exciters A."
            ::= { rsXx8000DvbNTxGroups 31 }

        
        groupTxObjsLogbookOstA OBJECT-GROUP
            OBJECTS { txA1OutputstageANumberOfEntries, txA1OutputstageALogbookClear, txA1OstALogbookEntryNbr, txA1OstALogbookType, txA1OstALogbookSlope, 
                txA1OstALogbookMessage, txA1OstALogbookDateTime, txA2OutputstageANumberOfEntries, txA2OutputstageALogbookClear, txA2OstALogbookEntryNbr, 
                txA2OstALogbookType, txA2OstALogbookSlope, txA2OstALogbookMessage, txA2OstALogbookDateTime, txA3OutputstageANumberOfEntries, 
                txA3OutputstageALogbookClear, txA3OstALogbookEntryNbr, txA3OstALogbookType, txA3OstALogbookSlope, txA3OstALogbookMessage, 
                txA3OstALogbookDateTime, txA4OutputstageANumberOfEntries, txA4OutputstageALogbookClear, txA4OstALogbookEntryNbr, txA4OstALogbookType, 
                txA4OstALogbookSlope, txA4OstALogbookMessage, txA4OstALogbookDateTime, txA5OutputstageANumberOfEntries, txA5OutputstageALogbookClear, 
                txA5OstALogbookEntryNbr, txA5OstALogbookType, txA5OstALogbookSlope, txA5OstALogbookMessage, txA5OstALogbookDateTime, 
                txA6OutputstageANumberOfEntries, txA6OutputstageALogbookClear, txA6OstALogbookEntryNbr, txA6OstALogbookType, txA6OstALogbookSlope, 
                txA6OstALogbookMessage, txA6OstALogbookDateTime, txA7OutputstageANumberOfEntries, txA7OutputstageALogbookClear, txA7OstALogbookEntryNbr, 
                txA7OstALogbookType, txA7OstALogbookSlope, txA7OstALogbookMessage, txA7OstALogbookDateTime, txA8OutputstageANumberOfEntries, 
                txA8OutputstageALogbookClear, txA8OstALogbookEntryNbr, txA8OstALogbookType, txA8OstALogbookSlope, txA8OstALogbookMessage, 
                txA8OstALogbookDateTime }
            STATUS current
            DESCRIPTION 
                "Group for objects of logbooks of outputstages A."
            ::= { rsXx8000DvbNTxGroups 32 }

        
        groupTxObjsLogbookExcB OBJECT-GROUP
            OBJECTS { txA1ExciterBNumberOfEntries, txA1ExciterBLogbookClear, txA1ExcBLogbookEntryNbr, txA1ExcBLogbookType, txA1ExcBLogbookSlope, 
                txA1ExcBLogbookMessage, txA1ExcBLogbookDateTime, txA2ExciterBNumberOfEntries, txA2ExciterBLogbookClear, txA2ExcBLogbookEntryNbr, 
                txA2ExcBLogbookType, txA2ExcBLogbookSlope, txA2ExcBLogbookMessage, txA2ExcBLogbookDateTime, txA3ExciterBNumberOfEntries, 
                txA3ExciterBLogbookClear, txA3ExcBLogbookEntryNbr, txA3ExcBLogbookType, txA3ExcBLogbookSlope, txA3ExcBLogbookMessage, 
                txA3ExcBLogbookDateTime, txA4ExciterBNumberOfEntries, txA4ExciterBLogbookClear, txA4ExcBLogbookEntryNbr, txA4ExcBLogbookType, 
                txA4ExcBLogbookSlope, txA4ExcBLogbookMessage, txA4ExcBLogbookDateTime, txA5ExciterBNumberOfEntries, txA5ExciterBLogbookClear, 
                txA5ExcBLogbookEntryNbr, txA5ExcBLogbookType, txA5ExcBLogbookSlope, txA5ExcBLogbookMessage, txA5ExcBLogbookDateTime, 
                txA6ExciterBNumberOfEntries, txA6ExciterBLogbookClear, txA6ExcBLogbookEntryNbr, txA6ExcBLogbookType, txA6ExcBLogbookSlope, 
                txA6ExcBLogbookMessage, txA6ExcBLogbookDateTime, txA7ExciterBNumberOfEntries, txA7ExciterBLogbookClear, txA7ExcBLogbookEntryNbr, 
                txA7ExcBLogbookType, txA7ExcBLogbookSlope, txA7ExcBLogbookMessage, txA7ExcBLogbookDateTime, txA8ExciterBNumberOfEntries, 
                txA8ExciterBLogbookClear, txA8ExcBLogbookEntryNbr, txA8ExcBLogbookType, txA8ExcBLogbookSlope, txA8ExcBLogbookMessage, 
                txA8ExcBLogbookDateTime }
            STATUS current
            DESCRIPTION 
                "Group for objects of logbooks of exciters B."
            ::= { rsXx8000DvbNTxGroups 33 }

        
        groupTxObjsOstARack OBJECT-GROUP
            OBJECTS { txA1OstARackInletTemperature, txA1OstARackOutletTemperature, txA1OstARackAuxPowerSupply, txA2OstARackInletTemperature, txA2OstARackOutletTemperature, 
                txA2OstARackAuxPowerSupply, txA3OstARackInletTemperature, txA3OstARackOutletTemperature, txA3OstARackAuxPowerSupply, txA4OstARackInletTemperature, 
                txA4OstARackOutletTemperature, txA4OstARackAuxPowerSupply, txA5OstARackInletTemperature, txA5OstARackOutletTemperature, txA5OstARackAuxPowerSupply, 
                txA6OstARackInletTemperature, txA6OstARackOutletTemperature, txA6OstARackAuxPowerSupply, txA7OstARackInletTemperature, txA7OstARackOutletTemperature, 
                txA7OstARackAuxPowerSupply, txA8OstARackInletTemperature, txA8OstARackOutletTemperature, txA8OstARackAuxPowerSupply, amplifiersPerRack, 
                rackRfEventSignalling, rackGeneralPurposeInput, rfProbePresent, rfProbeConfigurationNominalValue, rfProbeThresholdRfFailLimit, 
                rfProbeThresholdTimeoutRfFailCtr, rfProbeThresholdWarningLimit, rfProbeCalibrationGain, rfProbeCalibrationOffset, rfProbeCalibrationSetGain, 
                rfProbeCalibrationSetOffset, rfProbeMeasuredValue }
            STATUS current
            DESCRIPTION 
                "Group for objects of outputstage rack parameters."
            ::= { rsXx8000DvbNTxGroups 40 }

        
        groupTxObjsExcInput OBJECT-GROUP
            OBJECTS { txA1ExcInputChannelName, txA1ExcInputConnected, txA1ExcInputSeamless, txA1ExcInputPreselected, txA1ExcInputActive, 
                txA1ExcInputMipFail, txA1ExcInputBandwidth, txA1ExcInputFFTLength, txA1ExcInputGuardInterval, txA1ExcInputConstellation, 
                txA1ExcInputCellID, txA1ExcInputInterleaver, txA1ExcInputCodeRate, txA1ExcInputPacketLength, txA1ExcInputMeasuredDatarate, 
                txA1ExcInputRequiredDatarate, txA1ExcInputMaximumDelay, txA2ExcInputChannelName, txA2ExcInputConnected, txA2ExcInputSeamless, 
                txA2ExcInputPreselected, txA2ExcInputActive, txA2ExcInputMipFail, txA2ExcInputBandwidth, txA2ExcInputFFTLength, 
                txA2ExcInputGuardInterval, txA2ExcInputConstellation, txA2ExcInputCellID, txA2ExcInputInterleaver, txA2ExcInputCodeRate, 
                txA2ExcInputPacketLength, txA2ExcInputMeasuredDatarate, txA2ExcInputRequiredDatarate, txA2ExcInputMaximumDelay, txA3ExcInputChannelName, 
                txA3ExcInputConnected, txA3ExcInputSeamless, txA3ExcInputPreselected, txA3ExcInputActive, txA3ExcInputMipFail, 
                txA3ExcInputBandwidth, txA3ExcInputFFTLength, txA3ExcInputGuardInterval, txA3ExcInputConstellation, txA3ExcInputCellID, 
                txA3ExcInputInterleaver, txA3ExcInputCodeRate, txA3ExcInputPacketLength, txA3ExcInputMeasuredDatarate, txA3ExcInputRequiredDatarate, 
                txA3ExcInputMaximumDelay, txA4ExcInputChannelName, txA4ExcInputConnected, txA4ExcInputSeamless, txA4ExcInputPreselected, 
                txA4ExcInputActive, txA4ExcInputMipFail, txA4ExcInputBandwidth, txA4ExcInputFFTLength, txA4ExcInputGuardInterval, 
                txA4ExcInputConstellation, txA4ExcInputCellID, txA4ExcInputInterleaver, txA4ExcInputCodeRate, txA4ExcInputPacketLength, 
                txA4ExcInputMeasuredDatarate, txA4ExcInputRequiredDatarate, txA4ExcInputMaximumDelay, txA5ExcInputChannelName, txA5ExcInputConnected, 
                txA5ExcInputSeamless, txA5ExcInputPreselected, txA5ExcInputActive, txA5ExcInputMipFail, txA5ExcInputBandwidth, 
                txA5ExcInputFFTLength, txA5ExcInputGuardInterval, txA5ExcInputConstellation, txA5ExcInputCellID, txA5ExcInputInterleaver, 
                txA5ExcInputCodeRate, txA5ExcInputPacketLength, txA5ExcInputMeasuredDatarate, txA5ExcInputRequiredDatarate, txA5ExcInputMaximumDelay, 
                txA6ExcInputChannelName, txA6ExcInputConnected, txA6ExcInputSeamless, txA6ExcInputPreselected, txA6ExcInputActive, 
                txA6ExcInputMipFail, txA6ExcInputBandwidth, txA6ExcInputFFTLength, txA6ExcInputGuardInterval, txA6ExcInputConstellation, 
                txA6ExcInputCellID, txA6ExcInputInterleaver, txA6ExcInputCodeRate, txA6ExcInputPacketLength, txA6ExcInputMeasuredDatarate, 
                txA6ExcInputRequiredDatarate, txA6ExcInputMaximumDelay, txA7ExcInputChannelName, txA7ExcInputConnected, txA7ExcInputSeamless, 
                txA7ExcInputPreselected, txA7ExcInputActive, txA7ExcInputMipFail, txA7ExcInputBandwidth, txA7ExcInputFFTLength, 
                txA7ExcInputGuardInterval, txA7ExcInputConstellation, txA7ExcInputCellID, txA7ExcInputInterleaver, txA7ExcInputCodeRate, 
                txA7ExcInputPacketLength, txA7ExcInputMeasuredDatarate, txA7ExcInputRequiredDatarate, txA7ExcInputMaximumDelay, txA8ExcInputChannelName, 
                txA8ExcInputConnected, txA8ExcInputSeamless, txA8ExcInputPreselected, txA8ExcInputActive, txA8ExcInputMipFail, 
                txA8ExcInputBandwidth, txA8ExcInputFFTLength, txA8ExcInputGuardInterval, txA8ExcInputConstellation, txA8ExcInputCellID, 
                txA8ExcInputInterleaver, txA8ExcInputCodeRate, txA8ExcInputPacketLength, txA8ExcInputMeasuredDatarate, txA8ExcInputRequiredDatarate, 
                txA8ExcInputMaximumDelay }
            STATUS current
            DESCRIPTION 
                "Group for InputTable of exciter."
            ::= { rsXx8000DvbNTxGroups 41 }

        
        groupIndependentRacks OBJECT-GROUP
            OBJECTS { rackReferenceVoltage, amplifiersPowerSupply, rackOnOff }
            STATUS current
            DESCRIPTION 
                "object types that are relevant for NX variants with independent racks only"
            ::= { rsXx8000DvbNTxGroups 42 }

        
        groupTxObjsProductInfo OBJECT-GROUP
            OBJECTS { prodInfoModuleName, prodInfoSerialNumber, prodInfoIdentNumberSW, prodInfoVersionNumberSW, prodInfoIdentNumberHW, 
                prodInfoVersionNumberHW, productInfoProductDateHW, ncuProdInfoModuleName, ncuProdInfoSerialNumber, ncuProdInfoIdentNumberSW, 
                ncuProdInfoVersionNumberSW, ncuProdInfoIdentNumberHW, ncuProdInfoVersionNumberHW, ncuProductInfoProductDateHW }
            STATUS current
            DESCRIPTION 
                "Group for ProductInfoTable of transmitters."
            ::= { rsXx8000DvbNTxGroups 50 }

        
        groupTxObjsDualDrive OBJECT-GROUP
            OBJECTS { cmdTxOperationModeReserve, cmdTxOpModeExcAutomatic, cmdTxPreselectExciter, cmdTxDelayTimeExcAutomatic, statusTxSummaryFaultExcB, 
                statusTxExciterAutomaticReady, statusTxExciterAutomaticChanged, statusTxExciterAutomaticFault, statusTxNoConnectionExcB, statusTxActiveExcA, 
                statusTxActiveExcB }
            STATUS current
            DESCRIPTION 
                "Group for objects of transmitters in case of DualDrive."
            ::= { rsXx8000DvbNTxGroups 60 }

        
        groupObjsObsoleted OBJECT-GROUP
            OBJECTS { cmdTxParametersetReSave, cmdExcInputAutoSwitch, cmdExcEnablePcrReset, cmdExcTimeForDailyPcrReset, cmdExcTPSManualAlpha, 
                txA1ExcInputAlpha, txA2ExcInputAlpha, txA3ExcInputAlpha, txA4ExcInputAlpha, txA5ExcInputAlpha, 
                txA6ExcInputAlpha, txA7ExcInputAlpha, txA8ExcInputAlpha }
            STATUS obsolete
            DESCRIPTION 
                "Group for obsoleted objects."
            ::= { rsXx8000DvbNTxGroups 99 }

        
        groupTxEventsMp NOTIFICATION-GROUP
            NOTIFICATIONS { txSummaryFault, txSummaryWarning, txLocal, txRfOn, txRfOk, 
                txParamSetValuesChanged, txRfLoopProgram, txRfWarning, txReflectionWarning, txNetCCUFanFault, 
                txNetCCUPowerSupply, txRfFail, txReflectionFault, txNetCCUNoConnectionToExcA, txNetCCUNoConnectionToOstA, 
                txOstSummaryFault, txOstSummaryWarning, txOstRfOn, txOstRfOk, txOstNoInput, 
                txOstRfWarning, txOstReflectionWarning, txOstRackWarning, txOstCoolingWarning, txOstRfFail, 
                txOstReflectionFault, txOstACFault, txOstCoolingFault, txOstCommFault, txRackSumFault, 
                txRackSumWarning, txRackOn, txRackGpiWarning, txRackFan1Fault, txRackFan2Fault, 
                txRackCoolingSumWarning, txRackAmplifierSumFault, txRackNoLink, txRackGpiFault, txRackTemperatureFault, 
                txRackACFault, txRackCoolingSumFault, txRackTempFaultAbs1, txRackTempFaultAbs2, txRackDCFault, 
                txAmpSumFault, txAmpSumWarning, txAmpPowerOn, txAmpDCOk, txAmpACOk, 
                txAmpRfInFail, txAmpRfFail, txAmpReflectionFault, txAmpTemperatureFault, txRackRfOk, 
                txRackRfOn, txRackTemperatureWarning, txRackOvervoltProtectWarning, txNoConnection, txAmpTransistorFault, 
                txNetCCUBoardTemperatureWarning, txRackRfWarning, txRackRfFault, txRackReflectionWarning, txRackReflectionFault, 
                txRackProbeNotCalibrated }
            STATUS current
            DESCRIPTION 
                "Group for events of transmitters in case of MediumPower."
            ::= { rsXx8000DvbNTxGroups 201 }

        
        groupTxEventsLpWithNetCCU NOTIFICATION-GROUP
            NOTIFICATIONS { txSummaryFault, txSummaryWarning, txLocal, txRfOn, txRfOk, 
                txParamSetValuesChanged, txRfLoopProgram, txNetCCUFanFault, txNetCCUPowerSupply, txRfFail, 
                txNetCCUNoConnectionToExcA, txNetCCUNoConnectionToOstA, txOstSummaryFault, txOstSummaryWarning, txExcInputReseveMissing, 
                txRfWarning, txNoConnection, txOstRfOn, txNetCCUBoardTemperatureWarning }
            STATUS current
            DESCRIPTION 
                "Group for events of transmitters in case of LowPower with NetCCU."
            ::= { rsXx8000DvbNTxGroups 202 }

        
        groupTxEventsLp NOTIFICATION-GROUP
            NOTIFICATIONS { txSummaryFault, txSummaryWarning, txLocal, txRfOn, txParamSetValuesChanged, 
                txRfFail, txExcSummaryFault, txExcSummaryWarning, txExcInputNoConnectHP1, txExcInputNoConnectLP1, 
                txExcInputNoConnectHP2, txExcInputNoConnectLP2, txExcInputActiveHP1, txExcInputActiveLP1, txExcInputActiveHP2, 
                txExcInputActiveLP2, txExcOn, txExcRfOn, txExcNoInput, txExcRfLoop, 
                txExcRfFail, txExcSelfTest, txExcOutputOpen, txExcBoardTemperatureWarning, txExcFanWarning, 
                txExcFanFault, txExcFifoWarning, txExcTestSignal, txExcSFNDelay, txExcWrongDatarate, 
                txExcMute, txExcPPSFail, txExcReferenceFail, txExcMIPFail, txExcInputAutomaticSwitchReady, 
                txExcInputAutomaticChangedOver, txOstSummaryFault, txOstSummaryWarning, txExcInputReseveMissing, txRfWarning, 
                txRfOk, txNoConnection, txOstRfOn, txExcRfOk }
            STATUS current
            DESCRIPTION 
                "Group for events of transmitters in case of LowPower."
            ::= { rsXx8000DvbNTxGroups 203 }

        
        groupTxEventsDualDrive NOTIFICATION-GROUP
            NOTIFICATIONS { txRfLoopReserve, txNetCCUNoConnectionToExcB, txAutomaticExcReady, txAutomaticExcChanged, txAutomaticExcFault
                 }
            STATUS current
            DESCRIPTION 
                "Group for events of transmitters in case of DualDrive."
            ::= { rsXx8000DvbNTxGroups 220 }

        
        groupTxEventsAddPowerSupply NOTIFICATION-GROUP
            NOTIFICATIONS { txInternalPowerSupplyWarning, txExternalPowerSupplyWarning }
            STATUS current
            DESCRIPTION 
                "Events that are available only when statusTxAdditionalPowerSupply is true."
            ::= { rsXx8000DvbNTxGroups 221 }

        
        groupTxObjsAddPowerSupply OBJECT-GROUP
            OBJECTS { statusTxInternalPowerSupply, statusTxExternalPowerSupply }
            STATUS current
            DESCRIPTION 
                "Objects that are available only when statusTxAdditionalPowerSupply is true."
            ::= { rsXx8000DvbNTxGroups 222 }

        
        groupEventTable OBJECT-GROUP
            OBJECTS { eventNcuName, eventNcuMask, eventNcuPriority, eventNcuEvent, eventTxName, 
                eventTxMask, eventTxPriority, eventTxEvent }
            STATUS current
            DESCRIPTION 
                "Group for all objects of event tables."
            ::= { rsXx8000DvbNTxGroups 400 }

        
        groupEventsObsoleted NOTIFICATION-GROUP
            NOTIFICATIONS { txNetCCUBoardTemperatureFault, txParamSetSubDeviceDiffers, ncuBoardTemperatureFault }
            STATUS obsolete
            DESCRIPTION 
                "Group for obsoleted or deprecated events."
            ::= { rsXx8000DvbNTxGroups 401 }

        
        groupSLx OBJECT-GROUP
            OBJECTS { cmdExcInput1Source, cmdExcInput2Source, cmdExcMonitoringOutput, excStatusNominalPower, excStatusVSWR, 
                cmdExcMuteCondition }
            STATUS current
            DESCRIPTION 
                "Group for objects of SLx transmitters."
            ::= { rsXx8000DvbNTxGroups 501 }

        
        groupRfProbes OBJECT-GROUP
            OBJECTS { rfProbesNetCCURfProbe1, rfProbesNetCCURfProbe2, rfProbesAntFwdNominal, rfProbesAntFwdWarningLimit, rfProbesAntFwdFailLimit, 
                rfProbesAntFwdDelayTimeRfFail, rfProbesAntFwdSetOffset, rfProbesAntFwdSetGain, rfProbesAntReflWarningLimit, rfProbesAntReflSetOffset, 
                rfProbesAntReflSetGain }
            STATUS current
            DESCRIPTION 
                "This group includes all OIDs regarding RF Probes."
            ::= { rsXx8000DvbNTxGroups 502 }

        
        groupAmpMeasureValues OBJECT-GROUP
            OBJECTS { ampI1A, ampI2A, ampI3A, ampI4A, ampI1B, 
                ampI2B, ampI3B, ampI4B, ampIDrv, ampUDc, 
                ampIDc, ampUDcControl, ampUReg, ampPowerA, ampPowerB, 
                ampPowerOut, ampPowerReflection, ampPowerReference, ampDeltaPhase, ampCmdDeltaPhase
                 }
            STATUS current
            DESCRIPTION 
                "Group for measured values of amplifiers."
            ::= { rsXx8000DvbNTxGroups 503 }

        
        groupDummyLoadRF OBJECT-GROUP
            OBJECTS { rfProbesDLFwdNominal, rfProbesDLFwdWarningLimit, rfProbesDLFwdFailLimit, rfProbesDLFwdDelayTimeRfFail, rfProbesDLFwdSetOffset, 
                rfProbesDLFwdSetGain, rfProbesDLReflWarningLimit, rfProbesDLReflSetOffset, rfProbesDLReflSetGain }
            STATUS current
            DESCRIPTION 
                "This group includes all object types regarding probes from dummy load.
                The object types in this group are defined only when a dummy load measure point exists.
                This can occur in reserve concept active reserve only.
                "
            ::= { rsXx8000DvbNTxGroups 504 }

        
        groupTxObjsOstB OBJECT-GROUP
            OBJECTS { txA1OstBRackInletTemperature, txA1OstBRackOutletTemperature, txA1OstBRackAuxPowerSupply, txA2OstBRackInletTemperature, txA2OstBRackOutletTemperature, 
                txA2OstBRackAuxPowerSupply, txA3OstBRackInletTemperature, txA3OstBRackOutletTemperature, txA3OstBRackAuxPowerSupply, txA4OstBRackInletTemperature, 
                txA4OstBRackOutletTemperature, txA4OstBRackAuxPowerSupply, txA5OstBRackInletTemperature, txA5OstBRackOutletTemperature, txA5OstBRackAuxPowerSupply, 
                txA6OstBRackInletTemperature, txA6OstBRackOutletTemperature, txA6OstBRackAuxPowerSupply, txA7OstBRackInletTemperature, txA7OstBRackOutletTemperature, 
                txA7OstBRackAuxPowerSupply, txA8OstBRackInletTemperature, txA8OstBRackOutletTemperature, txA8OstBRackAuxPowerSupply, ostBAmpI1A, 
                ostBAmpI2A, ostBAmpI3A, ostBAmpI4A, ostBAmpI1B, ostBAmpI2B, 
                ostBAmpI3B, ostBAmpI4B, ostBAmpIDrv, ostBAmpUDc, ostBAmpIDc, 
                ostBAmpUDcControl, ostBAmpUReg, ostBAmpPowerA, ostBAmpPowerB, ostBAmpPowerOut, 
                ostBAmpPowerReflection, ostBAmpPowerReference, ostBAmpDeltaPhase, statusTxActiveOstB, statusTxActiveOstA, 
                statusTxNoConnectionOstB, statusTxOstAutomaticFault, statusTxOstAutomaticChanged, statusTxOstAutomaticReady, statusTxSummaryFaultOstB, 
                cmdTxDelayTimeOstAutomatic, cmdTxPreselectOutputstage, cmdTxOpModeOstAutomatic, statusTxAbsorberFault, statusTxNoConnectionApaIf, 
                ostBAmpCmdDeltaPhase, txA1OutputstageBNumberOfEntries, txA1OutputstageBLogbookClear, txA1OstBLogbookEntryNbr, txA1OstBLogbookType, 
                txA1OstBLogbookSlope, txA1OstBLogbookMessage, txA1OstBLogbookDateTime, txA2OutputstageBNumberOfEntries, txA2OutputstageBLogbookClear, 
                txA2OstBLogbookEntryNbr, txA2OstBLogbookType, txA2OstBLogbookSlope, txA2OstBLogbookMessage, txA2OstBLogbookDateTime, 
                txA3OutputstageBNumberOfEntries, txA3OutputstageBLogbookClear, txA3OstBLogbookEntryNbr, txA3OstBLogbookType, txA3OstBLogbookSlope, 
                txA3OstBLogbookMessage, txA3OstBLogbookDateTime, txA4OutputstageBNumberOfEntries, txA4OutputstageBLogbookClear, txA4OstBLogbookEntryNbr, 
                txA4OstBLogbookType, txA4OstBLogbookSlope, txA4OstBLogbookMessage, txA4OstBLogbookDateTime, txA5OutputstageBNumberOfEntries, 
                txA5OutputstageBLogbookClear, txA5OstBLogbookEntryNbr, txA5OstBLogbookType, txA5OstBLogbookSlope, txA5OstBLogbookMessage, 
                txA5OstBLogbookDateTime, txA6OutputstageBNumberOfEntries, txA6OutputstageBLogbookClear, txA6OstBLogbookEntryNbr, txA6OstBLogbookType, 
                txA6OstBLogbookSlope, txA6OstBLogbookMessage, txA6OstBLogbookDateTime, txA7OutputstageBNumberOfEntries, txA7OutputstageBLogbookClear, 
                txA7OstBLogbookEntryNbr, txA7OstBLogbookType, txA7OstBLogbookSlope, txA7OstBLogbookMessage, txA7OstBLogbookDateTime, 
                txA8OutputstageBNumberOfEntries, txA8OutputstageBLogbookClear, txA8OstBLogbookEntryNbr, txA8OstBLogbookType, txA8OstBLogbookSlope, 
                txA8OstBLogbookMessage, txA8OstBLogbookDateTime }
            STATUS current
            DESCRIPTION 
                "Objects that ared implemented only when an output stage B exists."
            ::= { rsXx8000DvbNTxGroups 506 }

        
        groupTxEventsOstB NOTIFICATION-GROUP
            NOTIFICATIONS { txNetCCUNoConnectionToOstB, txAutomaticOstReady, txAutomaticOstChanged, txAutomaticOstFault, txNoConnectionApaIf, 
                txAbsorberFault }
            STATUS current
            DESCRIPTION 
                "Events that ared implemented only when an output stage B exists."
            ::= { rsXx8000DvbNTxGroups 507 }

        
        rsXx8000DvbNTxCompl OBJECT IDENTIFIER ::= { rsXx8000DvbNTxConf 2 }

        
        rsXx8000DVBNTxMP MODULE-COMPLIANCE
            STATUS current
            DESCRIPTION 
                "This reserve concept (Nplus1 MediumPower) consists of a switchover unit (NSU-MediumPower) and MediumPower transmitters."
            MODULE -- this module
                MANDATORY-GROUPS { groupTxObjsMp, groupTxObjsExc, groupTxObjsLogbookNetCCU, groupTxObjsLogbookExcA, groupTxObjsLogbookOstA, 
                    groupTxObjsOstARack, groupTxObjsExcInput, groupTxObjsProductInfo, groupTxEventsMp, groupEventTable, 
                    groupRfProbes, groupAmpMeasureValues, groupNcuObjs, groupNcuEvents }
                GROUP groupTxObjsDualDrive
                    DESCRIPTION 
                        "In case of DualDrive transmitters."
                GROUP groupTxObjsLogbookExcB
                    DESCRIPTION 
                        "In case of DualDrive transmitters."
                GROUP groupTxEventsDualDrive
                    DESCRIPTION 
                        "In case of DualDrive transmitters."
                GROUP groupIndependentRacks
                    DESCRIPTION 
                        "for variant with independent racks only"
                OBJECT cmdOstRefVoltageVision
                    MIN-ACCESS not-accessible
                    DESCRIPTION 
                        "not accessible in variant with independent racks"
                GROUP groupTxEventsAddPowerSupply
                    DESCRIPTION 
                        "only when statusTxAdditionalPowerSupply is true"
                GROUP groupNcuEventsAddPowerSupply
                    DESCRIPTION 
                        "only when additionalPowerSupply is true"
                GROUP groupNsuObjsAddPowerSupply
                    DESCRIPTION 
                        "only when additionalPowerSupply is true"
                GROUP groupTxObjsAddPowerSupply
                    DESCRIPTION 
                        "only when statusTxAdditionalPowerSupply is true"
                GROUP groupDummyLoadRF
                    DESCRIPTION 
                        "only when a dummy load measure point exists"
                GROUP groupTxObjsOstB
                    DESCRIPTION 
                        "only when an output stage B exists"
                GROUP groupTxEventsOstB
                    DESCRIPTION 
                        "only when an output stage B exists"
            ::= { rsXx8000DvbNTxCompl 2 }

        
        rsXx8000DVBNTxLpWithNetCCU MODULE-COMPLIANCE
            STATUS current
            DESCRIPTION 
                "This reserve concept (Nplus1 LowPower with NetCCU) consists of a switchover unit (NSU-LowPower) and LowPower transmitters with NetCCUs."
            MODULE -- this module
                MANDATORY-GROUPS { groupTxObjsExc, groupTxObjsLogbookNetCCU, groupTxObjsLogbookExcA, groupTxObjsExcInput, groupTxObjsProductInfo, 
                    groupTxEventsLpWithNetCCU, groupEventTable, groupRfProbes, groupAmpMeasureValues, groupNcuObjs, 
                    groupNcuEvents, groupTxObjsLp }
                GROUP groupTxObjsDualDrive
                    DESCRIPTION 
                        "In case of DualDrive transmitters."
                GROUP groupTxObjsLogbookExcB
                    DESCRIPTION 
                        "In case of DualDrive transmitters."
                GROUP groupTxEventsDualDrive
                    DESCRIPTION 
                        "In case of DualDrive transmitters."
                GROUP groupTxEventsAddPowerSupply
                    DESCRIPTION 
                        "only when statusTxAdditionalPowerSupply is true"
                GROUP groupNcuEventsAddPowerSupply
                    DESCRIPTION 
                        "only when additionalPowerSupply is true"
                GROUP groupNsuObjsAddPowerSupply
                    DESCRIPTION 
                        "only when additionalPowerSupply is true"
                GROUP groupTxObjsAddPowerSupply
                    DESCRIPTION 
                        "only when statusTxAdditionalPowerSupply is true"
                GROUP groupObjectsSx801Amplifier
                    DESCRIPTION 
                        "for Sx801 only"
            ::= { rsXx8000DvbNTxCompl 3 }

        
        rsXx8000DVBNTxLP MODULE-COMPLIANCE
            STATUS current
            DESCRIPTION 
                "This system consists of a control unit (NCU) and LowPower transmitters."
            MODULE -- this module
                MANDATORY-GROUPS { groupNcuObjs, groupNcuEvents, groupTxObjsLp, groupTxObjsExc, groupTxObjsExcInput, 
                    groupTxObjsProductInfo, groupTxEventsLp, groupSLx, groupEventTable, groupTxObjsLogbookExcA
                     }
                GROUP groupNcuEventsAddPowerSupply
                    DESCRIPTION 
                        "only when additionalPowerSupply is true"
                GROUP groupNsuObjsAddPowerSupply
                    DESCRIPTION 
                        "only when additionalPowerSupply is true"
                GROUP groupObjectsSx801Amplifier
                    DESCRIPTION 
                        "for Sx801 only"
            ::= { rsXx8000DvbNTxCompl 4 }

        
    
    END
