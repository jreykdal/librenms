--
-- RS-XX8000-ISDBT-EXC-MIB.mi2
-- MIB generated by MG-SOFT Visual MIB Builder 2010 Version 8.0  Build 410
-- Wednesday, November 27, 2013 at 09:10:17
--

-- *****************************************************************************
-- *****************************************************************************
-- **
-- **  COPYRIGHT      (c) 2012 Rohde & Schwarz GmbH & Co. KG
-- **                          Muehldorfstrasse 15
-- **    R & S                 D-81671 Muenchen
-- **
-- *****************************************************************************
-- **
-- **  MODULE         RS-XX8000-ISDBT-EXC-MIB
-- **  
-- **  DESCRIPTION    Rohde & Schwarz SNMP
-- **
-- *****************************************************************************
-- *****************************************************************************

    RS-XX8000-ISDBT-EXC-MIB DEFINITIONS ::= BEGIN
 
        IMPORTS
            rsXx8000, eventAlarmClass, rsXx8000MibModule, EventClass, EventMask, 
            EventMaxEntryNumber, EventPriority, EventState, IndexTransmitter, IndexAB, 
            SwitchOnOff, FloatingPoint, FailDelayMode, FailDelayStatus, LogbookMaxEntryNumber, 
            Trigger, LogbookEntrySlope, LogbookEntryMessagesExcTv, ProdInfoModuleNameTv, ReadableString            
                FROM RS-XX8000-COMMON-MIB            
            OBJECT-GROUP, MODULE-COMPLIANCE, NOTIFICATION-GROUP            
                FROM SNMPv2-CONF            
            Integer32, Unsigned32, OBJECT-TYPE, MODULE-IDENTITY, OBJECT-IDENTITY, 
            NOTIFICATION-TYPE            
                FROM SNMPv2-SMI            
            TruthValue, DateAndTime, TEXTUAL-CONVENTION            
                FROM SNMPv2-TC;
    
    
        rsXx8000IsdbtExcMibModule MODULE-IDENTITY 
            LAST-UPDATED "201205161000Z"		-- May 16, 2012 at 10:00 GMT
            ORGANIZATION 
                "Rohde&Schwarz GmbH & Co. KG"
            CONTACT-INFO 
                "Rohde & Schwarz GmbH & Co. KG
                Broadcasting Division
                
                Muehldorfstrasse 15
                81671 Munich
                Germany
                
                customersupport@rohde-schwarz.com"
            DESCRIPTION 
                "This MIB defines transmitting systems from Rohde & Schwarz.
                
                Use this MIB if your system meets the following requirements:
                - series XX8000 (NetCCU800),
                - ISDB-T,
                - transmitter reserve concept NTx or N+1.
                
                The following MIBs are related to this:
                - RS-COMMON-MIB         - mandatory for this MIB
                - RS-XX8000-COMMON-MIB  - mandatory for this MIB"
            REVISION "201205161000Z"		-- May 16, 2012 at 10:00 GMT
            DESCRIPTION 
                "Preliminary release."
            ::= { rsXx8000MibModule 213 }

        
    
--
-- Textual conventions
--
    
        ISDBtMode ::= TEXTUAL-CONVENTION
            STATUS current
            DESCRIPTION 
                "ISDB-T mode:
                mode1(1) - 2K
                mode2(2) - 4K
                mode3(3) - 8K"
            SYNTAX INTEGER
                {
                mode1(1),
                mode2(2),
                mode3(3)
                }

        GuardInterval ::= TEXTUAL-CONVENTION
            STATUS current
            DESCRIPTION 
                "Guard interval"
            SYNTAX INTEGER
                {
                oneDiv4(1),
                oneDiv8(2),
                oneDiv16(3),
                oneDiv32(4)
                }

        ValueTypeIndex ::= TEXTUAL-CONVENTION
            STATUS current
            DESCRIPTION 
                "This textual convention is for distinguishing two instances
                of a configuration object:
                granted(1)
                - The instance shows the currently active value.
                  This instance is read-only.
                customerSpecified(2)
                - The instance is for changing the value."
            SYNTAX INTEGER
                {
                granted(1),
                customerSpecified(2)
                }

        NitSource ::= TEXTUAL-CONVENTION
            STATUS current
            DESCRIPTION 
                "Description."
            SYNTAX INTEGER
                {
                manual(1),
                bts(2)
                }

    
--
-- Node definitions
--
    
        rsXx8000IsdbtExc OBJECT-IDENTITY
            STATUS current
            DESCRIPTION 
                "Xx8000 ISDBT exciter."
            ::= { rsXx8000 213 }

        
        rsXx8000IsdbtExcObjs OBJECT IDENTIFIER ::= { rsXx8000IsdbtExc 1 }

        
        rsXx8000IsdbtExcCommandsTable OBJECT-TYPE
            SYNTAX SEQUENCE OF RsXx8000IsdbtExcCommandsEntry
            MAX-ACCESS not-accessible
            STATUS current
            DESCRIPTION
                "This table contains important commands for the exciter."
            ::= { rsXx8000IsdbtExcObjs 1 }

        
        rsXx8000IsdbtExcCommandsEntry OBJECT-TYPE
            SYNTAX RsXx8000IsdbtExcCommandsEntry
            MAX-ACCESS not-accessible
            STATUS current
            DESCRIPTION
                "An entry in the rsXx8000IsdbtExcCommandsTable."
            INDEX { cmdTxIdx, cmdExcIdx }
            ::= { rsXx8000IsdbtExcCommandsTable 1 }

        
        RsXx8000IsdbtExcCommandsEntry ::=
            SEQUENCE { 
                cmdTxIdx
                    IndexTransmitter,
                cmdExcIdx
                    IndexAB,
                cmdExcOpModeInputAutomatic
                    SwitchOnOff,
                cmdExcPreselectInput
                    INTEGER,
                cmdExcSfnMode
                    INTEGER,
                cmdExcNetworkMode
                    INTEGER,
                cmdExcCoderSettingsSource
                    INTEGER,
                cmdExcTmccNextControl
                    INTEGER,
                cmdExcTxAutomatic
                    SwitchOnOff,
                cmdExcStaticUserDelay
                    FloatingPoint,
                cmdExcInputPriority
                    INTEGER,
                cmdExcInputCheckTimeForward
                    Integer32,
                cmdExcInputCheckTimeSwitchback
                    Integer32,
                cmdExcInputMuteOnFail
                    INTEGER,
                cmdExcPartialReception
                    SwitchOnOff,
                cmdExcISDBtMode
                    ISDBtMode,
                cmdExcTPSManualGuardInterval
                    GuardInterval,
                cmdExcTestMode
                    INTEGER,
                cmdExcSFNStaticDelay
                    FloatingPoint,
                cmdExcSFNDeviationTime
                    Integer32,
                cmdExcFrequency
                    Integer32,
                cmdExcReferenceSource
                    INTEGER,
                cmdExcMuteOnPPSFail
                    INTEGER,
                cmdExcMuteOnReferenceFail
                    INTEGER,
                cmdExcRefFailDelayTime
                    Integer32,
                cmdExcTypeLossOfInput
                    INTEGER,
                cmdExcRfOutput
                    SwitchOnOff,
                cmdExcRfOutputRegulation
                    SwitchOnOff,
                cmdExcRfOutputManualRfLevel
                    FloatingPoint,
                cmdExcRfOutputAttenuation
                    Integer32,
                cmdExcRfOutputRfSlope
                    FloatingPoint,
                cmdExcRfOutputModulationSlope
                    FloatingPoint,
                cmdExcRfIqAdjustStart
                    INTEGER,
                cmdExcRfIqAdjustTestsignal
                    SwitchOnOff,
                cmdExcRfIqAdjustBiasCoarseI
                    Integer32,
                cmdExcRfIqAdjustBiasCoarseQ
                    Integer32,
                cmdExcRfIqAdjustBiasFineI
                    Integer32,
                cmdExcRfIqAdjustBiasFineQ
                    Integer32,
                cmdExcRfIqAdjustGainI
                    Integer32,
                cmdExcRfIqAdjustGainQ
                    Integer32,
                cmdExcRfIqAdjustPhase
                    FloatingPoint,
                cmdExcInputFailDelayTime
                    Integer32,
                cmdExcOcxoAdjust
                    Integer32,
                cmdExcFailDelayMode
                    FailDelayMode
             }

        cmdTxIdx OBJECT-TYPE
            SYNTAX IndexTransmitter
            MAX-ACCESS not-accessible
            STATUS current
            DESCRIPTION
                "The transmitter index."
            ::= { rsXx8000IsdbtExcCommandsEntry 1 }

        
        cmdExcIdx OBJECT-TYPE
            SYNTAX IndexAB
            MAX-ACCESS not-accessible
            STATUS current
            DESCRIPTION
                "This index distinguishes the exiters.
                Necessary if you have dual drive transmitters."
            ::= { rsXx8000IsdbtExcCommandsEntry 2 }

        
        cmdExcOpModeInputAutomatic OBJECT-TYPE
            SYNTAX SwitchOnOff
            MAX-ACCESS read-write
            STATUS current
            DESCRIPTION
                "This switches the automatic switching of the exciters input on or off."
            ::= { rsXx8000IsdbtExcCommandsEntry 31 }

        
        cmdExcPreselectInput OBJECT-TYPE
            SYNTAX INTEGER
                {
                input1(1),
                input2(2)
                }
            MAX-ACCESS read-write
            STATUS current
            DESCRIPTION
                "This sets the preselection of a transmitters input."
            ::= { rsXx8000IsdbtExcCommandsEntry 32 }

        
        cmdExcSfnMode OBJECT-TYPE
            SYNTAX INTEGER
                {
                dynamic(1),
                static(2),
                signalledInIIP(3)
                }
            MAX-ACCESS read-write
            STATUS current
            DESCRIPTION
                "Select the SFN mode:
                dynamic(1)        - dynamic SFN
                static(2)         - static SFN
                signalledInIIP(3) - automatic setup through IIP."
            ::= { rsXx8000IsdbtExcCommandsEntry 33 }

        
        cmdExcNetworkMode OBJECT-TYPE
            SYNTAX INTEGER
                {
                mfn(1),
                sfn(2)
                }
            MAX-ACCESS read-write
            STATUS current
            DESCRIPTION
                "Switch between Single Frequency Networks (SFN) and 
                Multiple Frequency Networks (MFN)."
            ::= { rsXx8000IsdbtExcCommandsEntry 34 }

        
        cmdExcCoderSettingsSource OBJECT-TYPE
            SYNTAX INTEGER
                {
                iip(1),
                manual(2)
                }
            MAX-ACCESS read-write
            STATUS current
            DESCRIPTION
                "Coder settings parameters can be adjusted manually inside 
                the exciter or automatically via IIP (ISDB-T Information Packet)."
            ::= { rsXx8000IsdbtExcCommandsEntry 35 }

        
        cmdExcTmccNextControl OBJECT-TYPE
            SYNTAX INTEGER
                {
                off(1),
                active(2),
                automatic(3)
                }
            MAX-ACCESS read-write
            STATUS current
            DESCRIPTION
                "Control of TMCC NEXT information:
                off(1)
                - Signalling is switched off.
                active(2)
                - Signalling as TMCC.
                automatic(3)
                - If cmdExcCoderSettingsSource is manual(2) signalling as TMCC,
                  if it is iip(1) then signalling as given in IIP (ISDB-T Information Packet)."
            ::= { rsXx8000IsdbtExcCommandsEntry 36 }

        
        cmdExcTxAutomatic OBJECT-TYPE
            SYNTAX SwitchOnOff
            MAX-ACCESS read-write
            STATUS current
            DESCRIPTION
                "This enables Tx specific parameters from the 
                MIP data caroussel (e.g. time offset, frequency offset)."
            ::= { rsXx8000IsdbtExcCommandsEntry 38 }

        
        cmdExcStaticUserDelay OBJECT-TYPE
            SYNTAX FloatingPoint
            UNITS "Microseconds"
            MAX-ACCESS read-write
            STATUS current
            DESCRIPTION
                "The total value of the static delay during Static Manual SFN Mode.
                It is unused in every other mode."
            ::= { rsXx8000IsdbtExcCommandsEntry 39 }

        
        cmdExcInputPriority OBJECT-TYPE
            SYNTAX INTEGER
                {
                equal(1),
                prior(2)
                }
            MAX-ACCESS read-write
            STATUS current
            DESCRIPTION
                "Equal: There are no differences between both inputs. 
                If a failure on the current input is detected it will be switched to the reserve input. 
                It stays there until the reserve shows a failure. 
                Prior: Whenever possible a certain input shall be used. 
                If a failure is detected the reserve will be used as short as possible."
            ::= { rsXx8000IsdbtExcCommandsEntry 41 }

        
        cmdExcInputCheckTimeForward OBJECT-TYPE
            SYNTAX Integer32 (0..600)
            UNITS "seconds"
            MAX-ACCESS read-write
            STATUS current
            DESCRIPTION
                "This time has to elapse before the current input switches 
                to the reserve input."
            ::= { rsXx8000IsdbtExcCommandsEntry 42 }

        
        cmdExcInputCheckTimeSwitchback OBJECT-TYPE
            SYNTAX Integer32 (0..600)
            UNITS "seconds"
            MAX-ACCESS read-write
            STATUS current
            DESCRIPTION
                "This time has to elapse before the automatic switches back 
                from the reserve to a preselected input. 
                This value has no effect if the priority is set to equal."
            ::= { rsXx8000IsdbtExcCommandsEntry 43 }

        
        cmdExcInputMuteOnFail OBJECT-TYPE
            SYNTAX INTEGER
                {
                mute(1),
                noMute(2)
                }
            MAX-ACCESS read-write
            STATUS current
            DESCRIPTION
                "If a loss of input signal is detected, the exciter mutes."
            ::= { rsXx8000IsdbtExcCommandsEntry 44 }

        
        cmdExcPartialReception OBJECT-TYPE
            SYNTAX SwitchOnOff
            MAX-ACCESS read-write
            STATUS current
            DESCRIPTION
                "indicator for receiver"
            ::= { rsXx8000IsdbtExcCommandsEntry 49 }

        
        cmdExcISDBtMode OBJECT-TYPE
            SYNTAX ISDBtMode
            MAX-ACCESS read-write
            STATUS current
            DESCRIPTION
                "see textual convention"
            ::= { rsXx8000IsdbtExcCommandsEntry 50 }

        
        cmdExcTPSManualGuardInterval OBJECT-TYPE
            SYNTAX GuardInterval
            MAX-ACCESS read-write
            STATUS current
            DESCRIPTION
                "The Guard interval affects the error correction in multipath receiving situations.
                A long Guard Interval reduces the amount of payload data."
            ::= { rsXx8000IsdbtExcCommandsEntry 51 }

        
        cmdExcTestMode OBJECT-TYPE
            SYNTAX INTEGER
                {
                off(1),
                coderMode0(2),
                coderMode1(3),
                ifftLeftCarrier(4),
                ifftRightCarrier(5),
                ifftLowerBand(6),
                ifftUpperBand(7),
                ifftPRBS(8)
                }
            MAX-ACCESS read-write
            STATUS current
            DESCRIPTION
                "Enable the test mode and allow to filter some sub carriers."
            ::= { rsXx8000IsdbtExcCommandsEntry 61 }

        
        cmdExcSFNStaticDelay OBJECT-TYPE
            SYNTAX FloatingPoint
            UNITS "Microseconds"
            MAX-ACCESS read-write
            STATUS current
            DESCRIPTION
                "The offset in time of transmission set manually for the individual transmitter site,
                relative to the regular time of transmission specified by the maximum delay.
                The static delay can be used to compensate for manufacturing differences
                between transmitter systems. If static delay and Tx offset delay are both present
                at the same time their effects combines."
            ::= { rsXx8000IsdbtExcCommandsEntry 62 }

        
        cmdExcSFNDeviationTime OBJECT-TYPE
            SYNTAX Integer32 (1..100)
            UNITS "Microseconds"
            MAX-ACCESS read-write
            STATUS current
            DESCRIPTION
                "In relation to the computed time of transmission, this is the maximum
                deviation time that can be corrected without a break in transmission."
            ::= { rsXx8000IsdbtExcCommandsEntry 63 }

        
        cmdExcFrequency OBJECT-TYPE
            SYNTAX Integer32 (47000000..1500000000)
            UNITS "Hertz"
            MAX-ACCESS read-write
            STATUS current
            DESCRIPTION
                "This is the RF frequency."
            ::= { rsXx8000IsdbtExcCommandsEntry 64 }

        
        cmdExcReferenceSource OBJECT-TYPE
            SYNTAX INTEGER
                {
                intern(1),
                extern5Mhz(2),
                extern10Mhz(3),
                extern1PPS(4),
                internGPS(5)
                }
            MAX-ACCESS read-write
            STATUS current
            DESCRIPTION
                "The Source of the reference signal.
                The value internGPS is not valid for SX800."
            ::= { rsXx8000IsdbtExcCommandsEntry 65 }

        
        cmdExcMuteOnPPSFail OBJECT-TYPE
            SYNTAX INTEGER
                {
                off(1),
                onlyAtStartup(2),
                afterFailDelayTime(3)
                }
            MAX-ACCESS read-write
            STATUS current
            DESCRIPTION
                "Select the behaviour if the external second pulse is not available."
            ::= { rsXx8000IsdbtExcCommandsEntry 66 }

        
        cmdExcMuteOnReferenceFail OBJECT-TYPE
            SYNTAX INTEGER
                {
                off(1),
                onlyAtStartup(2),
                afterFailDelayTime(3)
                }
            MAX-ACCESS read-write
            STATUS current
            DESCRIPTION
                "Select the behaviour if the external reference is not available."
            ::= { rsXx8000IsdbtExcCommandsEntry 67 }

        
        cmdExcRefFailDelayTime OBJECT-TYPE
            SYNTAX Integer32 (0..24)
            UNITS "Hours"
            MAX-ACCESS read-write
            STATUS current
            DESCRIPTION
                "Adjusts the time after the RF will be muted in case of a reference problem.
                Zero hours means react immediately."
            ::= { rsXx8000IsdbtExcCommandsEntry 68 }

        
        cmdExcTypeLossOfInput OBJECT-TYPE
            SYNTAX INTEGER
                {
                warning(1),
                fault(2)
                }
            MAX-ACCESS read-write
            STATUS current
            DESCRIPTION
                "If the input signal is lost, either a warning or a fault can be generated.
                If you select fault here, a switchover to the reserve exciter will be executed 
                when input signal is lost."
            ::= { rsXx8000IsdbtExcCommandsEntry 69 }

        
        cmdExcRfOutput OBJECT-TYPE
            SYNTAX SwitchOnOff
            MAX-ACCESS read-write
            STATUS current
            DESCRIPTION
                "Turns on/switches off the output signal. This switch takes the same effect as the switch on the frontpanel of the exciter."
            ::= { rsXx8000IsdbtExcCommandsEntry 70 }

        
        cmdExcRfOutputRegulation OBJECT-TYPE
            SYNTAX SwitchOnOff
            MAX-ACCESS read-write
            STATUS current
            DESCRIPTION
                "Turns on/switches off the automatic output level regulation."
            ::= { rsXx8000IsdbtExcCommandsEntry 71 }

        
        cmdExcRfOutputManualRfLevel OBJECT-TYPE
            SYNTAX FloatingPoint
            UNITS "Percent"
            MAX-ACCESS read-write
            STATUS current
            DESCRIPTION
                "Adjusts the RF level (0.0 ... 100.0). The value relates to an attenuation of 0 dB."
            ::= { rsXx8000IsdbtExcCommandsEntry 72 }

        
        cmdExcRfOutputAttenuation OBJECT-TYPE
            SYNTAX Integer32 (0..9)
            UNITS "dB"
            MAX-ACCESS read-write
            STATUS current
            DESCRIPTION
                "Activates internal attenuators to reduce the output level of the exciter.
                Adjustable in steps of 3 dB only."
            ::= { rsXx8000IsdbtExcCommandsEntry 73 }

        
        cmdExcRfOutputRfSlope OBJECT-TYPE
            SYNTAX FloatingPoint
            UNITS "Percent"
            MAX-ACCESS read-write
            STATUS current
            DESCRIPTION
                "Adjusts a slope in the RF signal (-50.0 ... 50.0)."
            ::= { rsXx8000IsdbtExcCommandsEntry 74 }

        
        cmdExcRfOutputModulationSlope OBJECT-TYPE
            SYNTAX FloatingPoint
            UNITS "Percent"
            MAX-ACCESS read-write
            STATUS current
            DESCRIPTION
                "Modulation slope (-50.0 ... 50.0)."
            ::= { rsXx8000IsdbtExcCommandsEntry 75 }

        
        cmdExcRfIqAdjustStart OBJECT-TYPE
            SYNTAX INTEGER
                {
                break(1),
                start(2)
                }
            MAX-ACCESS read-write
            STATUS current
            DESCRIPTION
                "Starts the automatic IQ adjustment. It works for the current used local 1 frequency and lasts up to 5 minutes. In this time the output will be muted. During the adjustment no transmitter parameter shall be changed. Break will stop the automatic immediately. The IQ modulator looses its adjustment!
                Read values mean idle(1) and started(2)."
            ::= { rsXx8000IsdbtExcCommandsEntry 77 }

        
        cmdExcRfIqAdjustTestsignal OBJECT-TYPE
            SYNTAX SwitchOnOff
            MAX-ACCESS read-write
            STATUS current
            DESCRIPTION
                "Generates a test signal to adjust the IQ modulation. It is necessary to disconnect the rf-cable to the output stages."
            ::= { rsXx8000IsdbtExcCommandsEntry 78 }

        
        cmdExcRfIqAdjustBiasCoarseI OBJECT-TYPE
            SYNTAX Integer32 (-1023..1023)
            MAX-ACCESS read-write
            STATUS current
            DESCRIPTION
                "Adjusts the offset for I in huge steps."
            ::= { rsXx8000IsdbtExcCommandsEntry 79 }

        
        cmdExcRfIqAdjustBiasCoarseQ OBJECT-TYPE
            SYNTAX Integer32 (-1023..1023)
            MAX-ACCESS read-write
            STATUS current
            DESCRIPTION
                "Adjusts the offset for Q in huge steps."
            ::= { rsXx8000IsdbtExcCommandsEntry 80 }

        
        cmdExcRfIqAdjustBiasFineI OBJECT-TYPE
            SYNTAX Integer32 (-32767..32767)
            MAX-ACCESS read-write
            STATUS current
            DESCRIPTION
                "Adjusts the offset for I in small steps."
            ::= { rsXx8000IsdbtExcCommandsEntry 81 }

        
        cmdExcRfIqAdjustBiasFineQ OBJECT-TYPE
            SYNTAX Integer32 (-32767..32767)
            MAX-ACCESS read-write
            STATUS current
            DESCRIPTION
                "Adjusts the offset for Q in small steps."
            ::= { rsXx8000IsdbtExcCommandsEntry 82 }

        
        cmdExcRfIqAdjustGainI OBJECT-TYPE
            SYNTAX Integer32 (0..255)
            MAX-ACCESS read-write
            STATUS current
            DESCRIPTION
                "Adjusts the gain for I in small steps."
            ::= { rsXx8000IsdbtExcCommandsEntry 83 }

        
        cmdExcRfIqAdjustGainQ OBJECT-TYPE
            SYNTAX Integer32 (0..255)
            MAX-ACCESS read-write
            STATUS current
            DESCRIPTION
                "Adjusts the gain for Q in small steps."
            ::= { rsXx8000IsdbtExcCommandsEntry 84 }

        
        cmdExcRfIqAdjustPhase OBJECT-TYPE
            SYNTAX FloatingPoint
            MAX-ACCESS read-write
            STATUS current
            DESCRIPTION
                "Adjusts the phase between I and Q (-14.000 ... 14.000)."
            ::= { rsXx8000IsdbtExcCommandsEntry 85 }

        
        cmdExcInputFailDelayTime OBJECT-TYPE
            SYNTAX Integer32 (0..600)
            UNITS "Seconds"
            MAX-ACCESS read-write
            STATUS current
            DESCRIPTION
                "The time between detecting a loss of input signal and displaying a failure."
            ::= { rsXx8000IsdbtExcCommandsEntry 89 }

        
        cmdExcOcxoAdjust OBJECT-TYPE
            SYNTAX Integer32 (0..65535)
            MAX-ACCESS read-write
            STATUS current
            DESCRIPTION
                "Adjusts the frequency of the internal 10 MHz reference.
                This value only takes effect if the reference source 'internal' is selected."
            ::= { rsXx8000IsdbtExcCommandsEntry 111 }

        
        cmdExcFailDelayMode OBJECT-TYPE
            SYNTAX FailDelayMode
            MAX-ACCESS read-write
            STATUS current
            DESCRIPTION
                "Condition when the fail delay time is used."
            ::= { rsXx8000IsdbtExcCommandsEntry 115 }

        
        rsXx8000IsdbtExcInputTable OBJECT-TYPE
            SYNTAX SEQUENCE OF RsXx8000IsdbtExcInputEntry
            MAX-ACCESS not-accessible
            STATUS current
            DESCRIPTION
                "Exciter input values."
            ::= { rsXx8000IsdbtExcObjs 2 }

        
        rsXx8000IsdbtExcInputEntry OBJECT-TYPE
            SYNTAX RsXx8000IsdbtExcInputEntry
            MAX-ACCESS not-accessible
            STATUS current
            DESCRIPTION
                "An entry in the rsXx8000IsdbtExcInputTable."
            INDEX { cmdTxIdx, cmdExcIdx, excInputChannelIdx }
            ::= { rsXx8000IsdbtExcInputTable 1 }

        
        RsXx8000IsdbtExcInputEntry ::=
            SEQUENCE { 
                excInputChannelIdx
                    Unsigned32,
                excInputChannelName
                    INTEGER,
                excInputConnected
                    TruthValue,
                excInputPreselected
                    TruthValue,
                excInputActive
                    TruthValue,
                excInputPacketLength
                    Integer32,
                excInputMeasuredDatarate
                    Integer32,
                excInputRequiredDatarate
                    Integer32
             }

        excInputChannelIdx OBJECT-TYPE
            SYNTAX Unsigned32 (1..2)
            MAX-ACCESS not-accessible
            STATUS current
            DESCRIPTION
                "The index for the different input channels."
            ::= { rsXx8000IsdbtExcInputEntry 2 }

        
        excInputChannelName OBJECT-TYPE
            SYNTAX INTEGER
                {
                input1(1),
                input2(2)
                }
            MAX-ACCESS read-only
            STATUS current
            DESCRIPTION
                "This is the logical name for the index for the different input channels."
            ::= { rsXx8000IsdbtExcInputEntry 3 }

        
        excInputConnected OBJECT-TYPE
            SYNTAX TruthValue
            MAX-ACCESS read-only
            STATUS current
            DESCRIPTION
                "The input channel is connected."
            ::= { rsXx8000IsdbtExcInputEntry 4 }

        
        excInputPreselected OBJECT-TYPE
            SYNTAX TruthValue
            MAX-ACCESS read-only
            STATUS current
            DESCRIPTION
                "The input channel is the preselected."
            ::= { rsXx8000IsdbtExcInputEntry 5 }

        
        excInputActive OBJECT-TYPE
            SYNTAX TruthValue
            MAX-ACCESS read-only
            STATUS current
            DESCRIPTION
                "The input channel is active."
            ::= { rsXx8000IsdbtExcInputEntry 6 }

        
        excInputPacketLength OBJECT-TYPE
            SYNTAX Integer32
            MAX-ACCESS read-only
            STATUS current
            DESCRIPTION
                "The Packet length for the channel."
            ::= { rsXx8000IsdbtExcInputEntry 17 }

        
        excInputMeasuredDatarate OBJECT-TYPE
            SYNTAX Integer32
            UNITS "Bit/s"
            MAX-ACCESS read-only
            STATUS current
            DESCRIPTION
                "The measured datarate of the input."
            ::= { rsXx8000IsdbtExcInputEntry 18 }

        
        excInputRequiredDatarate OBJECT-TYPE
            SYNTAX Integer32
            UNITS "Bit/s"
            MAX-ACCESS read-only
            STATUS current
            DESCRIPTION
                "The required datarate of the input."
            ::= { rsXx8000IsdbtExcInputEntry 19 }

        
        rsXx8000IsdbtExcStatusTable OBJECT-TYPE
            SYNTAX SEQUENCE OF RsXx8000IsdbtExcStatusEntry
            MAX-ACCESS not-accessible
            STATUS current
            DESCRIPTION
                "Exciter status values."
            ::= { rsXx8000IsdbtExcObjs 20 }

        
        rsXx8000IsdbtExcStatusEntry OBJECT-TYPE
            SYNTAX RsXx8000IsdbtExcStatusEntry
            MAX-ACCESS not-accessible
            STATUS current
            DESCRIPTION
                "An entry in the rsXx8000IsdbtExcStatusTable."
            AUGMENTS { rsXx8000IsdbtExcCommandsEntry }
            ::= { rsXx8000IsdbtExcStatusTable 1 }

        
        RsXx8000IsdbtExcStatusEntry ::=
            SEQUENCE { 
                excStatusRfOutputAgcRegulation
                    FloatingPoint,
                excStatusRfIqAdjustAuto
                    INTEGER,
                excStatusRfIqAdjustLO1Frequency
                    FloatingPoint,
                excStatusISDBtMode
                    ISDBtMode,
                excStatusGuardInterval
                    GuardInterval,
                excStatusPartialReception
                    TruthValue,
                excStatusSfnDelayProcessing
                    FloatingPoint,
                excStatusSfnDelayDynamic
                    FloatingPoint,
                excStatusSfnDelayNetwork
                    FloatingPoint,
                excStatusSfnDelayTxOffset
                    FloatingPoint,
                excStatusSfnDelayMaximum
                    FloatingPoint,
                excStatusSfnDelayTotal
                    FloatingPoint,
                excStatusSfnMode
                    INTEGER,
                excStatusFailDelay
                    FailDelayStatus
             }

        excStatusRfOutputAgcRegulation OBJECT-TYPE
            SYNTAX FloatingPoint
            UNITS "Percent"
            MAX-ACCESS read-only
            STATUS current
            DESCRIPTION
                "Shows the operating point of the RF regulator.
                The shown value should be around 50 per cent."
            ::= { rsXx8000IsdbtExcStatusEntry 4 }

        
        excStatusRfIqAdjustAuto OBJECT-TYPE
            SYNTAX INTEGER
                {
                notAdjusted(1),
                inProgress(2),
                adjusted(3)
                }
            UNITS "Percent"
            MAX-ACCESS read-only
            STATUS current
            DESCRIPTION
                "Automatic I/Q-Adjust."
            ::= { rsXx8000IsdbtExcStatusEntry 5 }

        
        excStatusRfIqAdjustLO1Frequency OBJECT-TYPE
            SYNTAX FloatingPoint
            UNITS "MHz"
            MAX-ACCESS read-only
            STATUS current
            DESCRIPTION
                "Modulator LO1."
            ::= { rsXx8000IsdbtExcStatusEntry 6 }

        
        excStatusISDBtMode OBJECT-TYPE
            SYNTAX ISDBtMode
            MAX-ACCESS read-only
            STATUS current
            DESCRIPTION
                "The currently active ISDB-T mode.
                see textual convention"
            ::= { rsXx8000IsdbtExcStatusEntry 10 }

        
        excStatusGuardInterval OBJECT-TYPE
            SYNTAX GuardInterval
            MAX-ACCESS read-only
            STATUS current
            DESCRIPTION
                "The currently active guard interval."
            ::= { rsXx8000IsdbtExcStatusEntry 11 }

        
        excStatusPartialReception OBJECT-TYPE
            SYNTAX TruthValue
            MAX-ACCESS read-only
            STATUS current
            DESCRIPTION
                "The current state of partial reception."
            ::= { rsXx8000IsdbtExcStatusEntry 12 }

        
        excStatusSfnDelayProcessing OBJECT-TYPE
            SYNTAX FloatingPoint
            UNITS "Microseconds"
            MAX-ACCESS read-only
            STATUS current
            DESCRIPTION
                "The minimum signal transmit time through the exciter.
                This delay depends on the transmission parameters."
            ::= { rsXx8000IsdbtExcStatusEntry 13 }

        
        excStatusSfnDelayDynamic OBJECT-TYPE
            SYNTAX FloatingPoint
            UNITS "Microseconds"
            MAX-ACCESS read-only
            STATUS current
            DESCRIPTION
                "The period of time by which signal processing is artificially delayed
                so that the desired time of transmission is obtained."
            ::= { rsXx8000IsdbtExcStatusEntry 14 }

        
        excStatusSfnDelayNetwork OBJECT-TYPE
            SYNTAX FloatingPoint
            UNITS "Microseconds"
            MAX-ACCESS read-only
            STATUS current
            DESCRIPTION
                "The signal propagation time between the play-out center
                (MIP inserter) and the exciter input. This delay depends
                on the transmission path used."
            ::= { rsXx8000IsdbtExcStatusEntry 15 }

        
        excStatusSfnDelayTxOffset OBJECT-TYPE
            SYNTAX FloatingPoint
            UNITS "Microseconds"
            MAX-ACCESS read-only
            STATUS current
            DESCRIPTION
                "An individual transmitter specific delay. It can be adjusted
                via data carousel of the SFN adapter. It is true for a
                specific transmitter address."
            ::= { rsXx8000IsdbtExcStatusEntry 16 }

        
        excStatusSfnDelayMaximum OBJECT-TYPE
            SYNTAX FloatingPoint
            UNITS "Microseconds"
            MAX-ACCESS read-only
            STATUS current
            DESCRIPTION
                "The period of time between the signal leaving the play-out center
                (MIP inserter) and its regular transmission at the antenna.
                This delay is set in the MIP inserter and serves as a basis for
                all the transmitters in the SFN."
            ::= { rsXx8000IsdbtExcStatusEntry 17 }

        
        excStatusSfnDelayTotal OBJECT-TYPE
            SYNTAX FloatingPoint
            UNITS "Microseconds"
            MAX-ACCESS read-only
            STATUS current
            DESCRIPTION
                "The actual signal transit time through the exciter.
                This is derived from the sum of static-, dynamic-, 
                offset- and processing delay."
            ::= { rsXx8000IsdbtExcStatusEntry 18 }

        
        excStatusSfnMode OBJECT-TYPE
            SYNTAX INTEGER
                {
                off(1),
                dynamic(2),
                staticIIP(3),
                staticManual(4)
                }
            MAX-ACCESS read-write
            STATUS current
            DESCRIPTION
                "Shows the currently active SFN mode."
            ::= { rsXx8000IsdbtExcStatusEntry 19 }

        
        excStatusFailDelay OBJECT-TYPE
            SYNTAX FailDelayStatus
            MAX-ACCESS read-only
            STATUS current
            DESCRIPTION
                "Shows whether the fail delay time is qualified."
            ::= { rsXx8000IsdbtExcStatusEntry 40 }

        
        rsXx8000IsdbtExcPrecorrectionTable OBJECT-TYPE
            SYNTAX SEQUENCE OF RsXx8000IsdbtExcPrecorrectionEntry
            MAX-ACCESS not-accessible
            STATUS current
            DESCRIPTION
                "Exciter precorrection commands and values."
            ::= { rsXx8000IsdbtExcObjs 21 }

        
        rsXx8000IsdbtExcPrecorrectionEntry OBJECT-TYPE
            SYNTAX RsXx8000IsdbtExcPrecorrectionEntry
            MAX-ACCESS not-accessible
            STATUS current
            DESCRIPTION
                "An entry in the rsXx8000IsdbtExcPrecorrectionTable."
            AUGMENTS { rsXx8000IsdbtExcCommandsEntry }
            ::= { rsXx8000IsdbtExcPrecorrectionTable 1 }

        
        RsXx8000IsdbtExcPrecorrectionEntry ::=
            SEQUENCE { 
                excPrecLinCorrection
                    SwitchOnOff,
                excPrecLinAutomaticADE
                    INTEGER,
                excPrecLinMaxAmplitudeRipple
                    FloatingPoint,
                excPrecLinMaxGroupDelayRipple
                    Integer32,
                excPrecLinAmplitudeRipple
                    FloatingPoint,
                excPrecLinGroupDelayRipple
                    Integer32,
                excPrecLinInputLevel
                    INTEGER,
                excPrecLinAutomatic
                    INTEGER,
                excPrecNonlinCorrection
                    SwitchOnOff,
                excPrecNonlinAutomaticADE
                    INTEGER,
                excPrecNonlinThresholdShoulders
                    FloatingPoint,
                excPrecNonlinShoulderLeft
                    FloatingPoint,
                excPrecNonlinShoulderRight
                    FloatingPoint,
                excPrecNonlinInputLevel
                    INTEGER,
                excPrecNonlinAutomatic
                    INTEGER,
                excPrecExtendedGroupDelay
                    SwitchOnOff
             }

        excPrecLinCorrection OBJECT-TYPE
            SYNTAX SwitchOnOff
            MAX-ACCESS read-write
            STATUS current
            DESCRIPTION
                "Switches on/turns off the linear precorrector."
            ::= { rsXx8000IsdbtExcPrecorrectionEntry 4 }

        
        excPrecLinAutomaticADE OBJECT-TYPE
            SYNTAX INTEGER
                {
                manual(1),
                automatic(2),
                adaptive(3)
                }
            MAX-ACCESS read-write
            STATUS current
            DESCRIPTION
                "Enables /disables the automatic precorrector. To get the ADE in work linear precorrection has to be switched on."
            ::= { rsXx8000IsdbtExcPrecorrectionEntry 5 }

        
        excPrecLinMaxAmplitudeRipple OBJECT-TYPE
            SYNTAX FloatingPoint
            UNITS "dB"
            MAX-ACCESS read-write
            STATUS current
            DESCRIPTION
                "Sets te maximum ripple for automatic amplitude correction (0.0 ... 2.0)."
            ::= { rsXx8000IsdbtExcPrecorrectionEntry 6 }

        
        excPrecLinMaxGroupDelayRipple OBJECT-TYPE
            SYNTAX Integer32 (0..500)
            UNITS "Nanoseconds"
            MAX-ACCESS read-write
            STATUS current
            DESCRIPTION
                "Sets the maximum ripple for automatic group delay correction."
            ::= { rsXx8000IsdbtExcPrecorrectionEntry 7 }

        
        excPrecLinAmplitudeRipple OBJECT-TYPE
            SYNTAX FloatingPoint
            UNITS "dB"
            MAX-ACCESS read-only
            STATUS current
            DESCRIPTION
                "Shows the current amplitude ripple."
            ::= { rsXx8000IsdbtExcPrecorrectionEntry 8 }

        
        excPrecLinGroupDelayRipple OBJECT-TYPE
            SYNTAX Integer32
            UNITS "Nanoseconds"
            MAX-ACCESS read-only
            STATUS current
            DESCRIPTION
                "Shows the current group delay ripple."
            ::= { rsXx8000IsdbtExcPrecorrectionEntry 9 }

        
        excPrecLinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { rsXx8000IsdbtExcPrecorrectionEntry 10 }

        
        excPrecLinAutomatic OBJECT-TYPE
            SYNTAX INTEGER
                {
                disabled(1),
                active(2),
                calculate(3),
                measure(4)
                }
            MAX-ACCESS read-only
            STATUS current
            DESCRIPTION
                "Shows if the automatic precorrector works properly."
            ::= { rsXx8000IsdbtExcPrecorrectionEntry 11 }

        
        excPrecNonlinCorrection OBJECT-TYPE
            SYNTAX SwitchOnOff
            MAX-ACCESS read-write
            STATUS current
            DESCRIPTION
                "Switches on/turns off the nonlinear precorrector."
            ::= { rsXx8000IsdbtExcPrecorrectionEntry 12 }

        
        excPrecNonlinAutomaticADE OBJECT-TYPE
            SYNTAX INTEGER
                {
                manual(1),
                automatic(2),
                adaptive(3)
                }
            MAX-ACCESS read-write
            STATUS current
            DESCRIPTION
                "Enables /disables the automatic precorrector. To get the ADE in work nonlinear precorrection has to be switched on."
            ::= { rsXx8000IsdbtExcPrecorrectionEntry 13 }

        
        excPrecNonlinThresholdShoulders OBJECT-TYPE
            SYNTAX FloatingPoint
            UNITS "dB"
            MAX-ACCESS read-write
            STATUS current
            DESCRIPTION
                "The target shoulder distance for ADE (0.0 ... 40.0)."
            ::= { rsXx8000IsdbtExcPrecorrectionEntry 14 }

        
        excPrecNonlinShoulderLeft OBJECT-TYPE
            SYNTAX FloatingPoint
            UNITS "dB"
            MAX-ACCESS read-only
            STATUS current
            DESCRIPTION
                "Displays the current measurement for the left handed shoulder distance."
            ::= { rsXx8000IsdbtExcPrecorrectionEntry 15 }

        
        excPrecNonlinShoulderRight OBJECT-TYPE
            SYNTAX FloatingPoint
            UNITS "dB"
            MAX-ACCESS read-only
            STATUS current
            DESCRIPTION
                "Displays the current measurement of the right handed shoulder."
            ::= { rsXx8000IsdbtExcPrecorrectionEntry 16 }

        
        excPrecNonlinInputLevel OBJECT-TYPE
            SYNTAX INTEGER
                {
                tooHigh(1),
                ok(2),
                tooLow(3),
                failure(4)
                }
            MAX-ACCESS read-only
            STATUS current
            DESCRIPTION
                "Shows the state of the feedback signal from the measurement point between output stage and antenna."
            ::= { rsXx8000IsdbtExcPrecorrectionEntry 17 }

        
        excPrecNonlinAutomatic OBJECT-TYPE
            SYNTAX INTEGER
                {
                disabled(1),
                active(2),
                calculate(3),
                measure(4)
                }
            MAX-ACCESS read-only
            STATUS current
            DESCRIPTION
                "Shows if the automatic precorrector works properly."
            ::= { rsXx8000IsdbtExcPrecorrectionEntry 18 }

        
        excPrecExtendedGroupDelay OBJECT-TYPE
            SYNTAX SwitchOnOff
            MAX-ACCESS read-write
            STATUS current
            DESCRIPTION
                "Switch extended group delay on or off.
                Switching on is possible only when the corresponding option key is active."
            ::= { rsXx8000IsdbtExcPrecorrectionEntry 30 }

        
        rsXx8000IsdbtExcTmmcTable OBJECT-TYPE
            SYNTAX SEQUENCE OF RsXx8000IsdbtExcTmmcEntry
            MAX-ACCESS not-accessible
            STATUS current
            DESCRIPTION
                "Transmission and Multiplexing Configuration Control table."
            ::= { rsXx8000IsdbtExcObjs 22 }

        
        rsXx8000IsdbtExcTmmcEntry OBJECT-TYPE
            SYNTAX RsXx8000IsdbtExcTmmcEntry
            MAX-ACCESS not-accessible
            STATUS current
            DESCRIPTION
                "An entry in the rsXx8000IsdbtExcTmmcTable."
            INDEX { cmdTxIdx, cmdExcIdx, tmccLayerIdx, tmccValueTypeIdx }
            ::= { rsXx8000IsdbtExcTmmcTable 1 }

        
        RsXx8000IsdbtExcTmmcEntry ::=
            SEQUENCE { 
                tmccLayerIdx
                    INTEGER,
                tmccValueTypeIdx
                    ValueTypeIndex,
                tmccSegments
                    Integer32,
                tmccConstellation
                    INTEGER,
                tmccCodeRate
                    INTEGER,
                tmccTimeInterleaver
                    INTEGER
             }

        tmccLayerIdx OBJECT-TYPE
            SYNTAX INTEGER
                {
                layerA(1),
                layerB(2),
                layerC(3)
                }
            MAX-ACCESS not-accessible
            STATUS current
            DESCRIPTION
                "index for hierarchical layer"
            ::= { rsXx8000IsdbtExcTmmcEntry 1 }

        
        tmccValueTypeIdx OBJECT-TYPE
            SYNTAX ValueTypeIndex
            MAX-ACCESS not-accessible
            STATUS current
            DESCRIPTION
                "see description of textual convention"
            ::= { rsXx8000IsdbtExcTmmcEntry 2 }

        
        tmccSegments OBJECT-TYPE
            SYNTAX Integer32 (0..13)
            MAX-ACCESS read-write
            STATUS current
            DESCRIPTION
                "number of segments used in (resp. set for) layer"
            ::= { rsXx8000IsdbtExcTmmcEntry 3 }

        
        tmccConstellation OBJECT-TYPE
            SYNTAX INTEGER
                {
                dqpsk(1),
                qpsk(2),
                qam16(3),
                qam64(4)
                }
            MAX-ACCESS read-write
            STATUS current
            DESCRIPTION
                "constellation used in (resp. set for) layer"
            ::= { rsXx8000IsdbtExcTmmcEntry 4 }

        
        tmccCodeRate OBJECT-TYPE
            SYNTAX INTEGER
                {
                oneHalf(1),
                twoThird(2),
                threeQuarters(3),
                fiveSixth(4),
                sevenEighth(5)
                }
            MAX-ACCESS read-write
            STATUS current
            DESCRIPTION
                "code rate used in (resp. set for) layer"
            ::= { rsXx8000IsdbtExcTmmcEntry 5 }

        
        tmccTimeInterleaver OBJECT-TYPE
            SYNTAX INTEGER
                {
                i0(1),
                i1(2),
                i2(3),
                i4(4),
                i8(5),
                i16(6),
                i32(7)
                }
            MAX-ACCESS read-write
            STATUS current
            DESCRIPTION
                "time interleaver used in (resp. set for) layer"
            ::= { rsXx8000IsdbtExcTmmcEntry 6 }

        
        rsXx8000IsdbtExcNitLocalizationTable OBJECT-TYPE
            SYNTAX SEQUENCE OF RsXx8000IsdbtExcNitLocalizationEntry
            MAX-ACCESS not-accessible
            STATUS current
            DESCRIPTION
                "NIT (network information tabel) configuration"
            ::= { rsXx8000IsdbtExcObjs 23 }

        
        rsXx8000IsdbtExcNitLocalizationEntry OBJECT-TYPE
            SYNTAX RsXx8000IsdbtExcNitLocalizationEntry
            MAX-ACCESS not-accessible
            STATUS current
            DESCRIPTION
                "An entry in the rsXx8000IsdbtExcNitLocalizationTable."
            AUGMENTS { rsXx8000IsdbtExcCommandsEntry }
            ::= { rsXx8000IsdbtExcNitLocalizationTable 1 }

        
        RsXx8000IsdbtExcNitLocalizationEntry ::=
            SEQUENCE { 
                nitNetworkIdSource
                    NitSource,
                nitNetworkId
                    Unsigned32,
                nitTransportStreamIdSource
                    NitSource,
                nitTransportStreamId
                    Unsigned32,
                nitAreaCodeSource
                    NitSource,
                nitAreaCode
                    Unsigned32,
                nitFrequencySource
                    NitSource,
                nitFrequency
                    Unsigned32,
                nitRemoteControlKeyIdSource
                    NitSource,
                nitRemoteControlKeyId
                    Unsigned32
             }

        nitNetworkIdSource OBJECT-TYPE
            SYNTAX NitSource
            MAX-ACCESS read-write
            STATUS current
            DESCRIPTION
                "Source for nitNetworkId."
            ::= { rsXx8000IsdbtExcNitLocalizationEntry 1 }

        
        nitNetworkId OBJECT-TYPE
            SYNTAX Unsigned32 (0..65535)
            MAX-ACCESS read-write
            STATUS current
            DESCRIPTION
                "This is a label to identify the network.
                Localization is done within each NIT."
            ::= { rsXx8000IsdbtExcNitLocalizationEntry 2 }

        
        nitTransportStreamIdSource OBJECT-TYPE
            SYNTAX NitSource
            MAX-ACCESS read-write
            STATUS current
            DESCRIPTION
                "Source for nitTransportStreamId."
            ::= { rsXx8000IsdbtExcNitLocalizationEntry 3 }

        
        nitTransportStreamId OBJECT-TYPE
            SYNTAX Unsigned32 (0..65535)
            MAX-ACCESS read-write
            STATUS current
            DESCRIPTION
                "This is a label to identify the transport stream
                from any other multiplex within the delivery system.
                Localization is done within each NIT, PAT, SDT, EIT, RST, PCAT and LDT."
            ::= { rsXx8000IsdbtExcNitLocalizationEntry 4 }

        
        nitAreaCodeSource OBJECT-TYPE
            SYNTAX NitSource
            MAX-ACCESS read-write
            STATUS current
            DESCRIPTION
                "Source for nitAreaCode."
            ::= { rsXx8000IsdbtExcNitLocalizationEntry 5 }

        
        nitAreaCode OBJECT-TYPE
            SYNTAX Unsigned32 (0..4095)
            MAX-ACCESS read-write
            STATUS current
            DESCRIPTION
                "This is the service area code from terrestrial delivery system descriptor.
                Localization is done within each NIT."
            ::= { rsXx8000IsdbtExcNitLocalizationEntry 6 }

        
        nitFrequencySource OBJECT-TYPE
            SYNTAX NitSource
            MAX-ACCESS read-write
            STATUS current
            DESCRIPTION
                "Source for nitFrequency."
            ::= { rsXx8000IsdbtExcNitLocalizationEntry 7 }

        
        nitFrequency OBJECT-TYPE
            SYNTAX Unsigned32 (0..65535)
            MAX-ACCESS read-write
            STATUS current
            DESCRIPTION
                "This is the first frequency within the list of frequencies
                from terrestrial delivery system descriptor.
                Localization is done within each NIT."
            ::= { rsXx8000IsdbtExcNitLocalizationEntry 8 }

        
        nitRemoteControlKeyIdSource OBJECT-TYPE
            SYNTAX NitSource
            MAX-ACCESS read-write
            STATUS current
            DESCRIPTION
                "Source for nitRemoteControlKeyId."
            ::= { rsXx8000IsdbtExcNitLocalizationEntry 9 }

        
        nitRemoteControlKeyId OBJECT-TYPE
            SYNTAX Unsigned32 (0..255)
            MAX-ACCESS read-write
            STATUS current
            DESCRIPTION
                "This indicates the recommended remote control key number
                to which the TS shall be assigned.
                This is also known as 'virtual channel'.
                Localization is done within each NIT."
            ::= { rsXx8000IsdbtExcNitLocalizationEntry 10 }

        
        rsXx8000IsdbtExcLogbook OBJECT IDENTIFIER ::= { rsXx8000IsdbtExcObjs 90 }

        
        logbookConfigTable OBJECT-TYPE
            SYNTAX SEQUENCE OF LogbookConfigEntry
            MAX-ACCESS not-accessible
            STATUS current
            DESCRIPTION
                "Configuration for exciter logbook table."
            ::= { rsXx8000IsdbtExcLogbook 1 }

        
        logbookConfigEntry OBJECT-TYPE
            SYNTAX LogbookConfigEntry
            MAX-ACCESS not-accessible
            STATUS current
            DESCRIPTION
                "An entry (conceptual row) in the logbookConfigTable."
            AUGMENTS { rsXx8000IsdbtExcCommandsEntry }
            ::= { logbookConfigTable 1 }

        
        LogbookConfigEntry ::=
            SEQUENCE { 
                lbCfgNumberOfEntries
                    LogbookMaxEntryNumber,
                lbCfgClear
                    Trigger
             }

        lbCfgNumberOfEntries OBJECT-TYPE
            SYNTAX LogbookMaxEntryNumber
            MAX-ACCESS read-only
            STATUS current
            DESCRIPTION
                "The number of entries in logbook."
            ::= { logbookConfigEntry 1 }

        
        lbCfgClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookConfigEntry 2 }

        
        logbookTable OBJECT-TYPE
            SYNTAX SEQUENCE OF LogbookEntry
            MAX-ACCESS not-accessible
            STATUS current
            DESCRIPTION
                "Exciter logbook table."
            ::= { rsXx8000IsdbtExcLogbook 2 }

        
        logbookEntry OBJECT-TYPE
            SYNTAX LogbookEntry
            MAX-ACCESS not-accessible
            STATUS current
            DESCRIPTION
                "An entry in the logbookTable."
            INDEX { cmdTxIdx, cmdExcIdx, logbookEntryIdx }
            ::= { logbookTable 1 }

        
        LogbookEntry ::=
            SEQUENCE { 
                logbookEntryIdx
                    LogbookMaxEntryNumber,
                logbookEntryNbr
                    LogbookMaxEntryNumber,
                logbookType
                    EventClass,
                logbookSlope
                    LogbookEntrySlope,
                logbookMessage
                    LogbookEntryMessagesExcTv,
                logbookDateTime
                    DateAndTime
             }

        logbookEntryIdx OBJECT-TYPE
            SYNTAX LogbookMaxEntryNumber
            MAX-ACCESS not-accessible
            STATUS current
            DESCRIPTION
                "This is an increasing number from 1 to 128. It is used as an index column for SNMP."
            ::= { logbookEntry 1 }

        
        logbookEntryNbr OBJECT-TYPE
            SYNTAX LogbookMaxEntryNumber
            MAX-ACCESS read-only
            STATUS current
            DESCRIPTION
                "This is the number of the logbook entry. It is an decreasing number from max 128 down to 1."
            ::= { logbookEntry 2 }

        
        logbookType OBJECT-TYPE
            SYNTAX EventClass
            MAX-ACCESS read-only
            STATUS current
            DESCRIPTION
                "Can either be Fault, Warning or State."
            ::= { logbookEntry 3 }

        
        logbookSlope OBJECT-TYPE
            SYNTAX LogbookEntrySlope
            MAX-ACCESS read-only
            STATUS current
            DESCRIPTION
                "Either set (event raises) or reset (event disappears)"
            ::= { logbookEntry 4 }

        
        logbookMessage OBJECT-TYPE
            SYNTAX LogbookEntryMessagesExcTv
            MAX-ACCESS read-only
            STATUS current
            DESCRIPTION
                "See RS-XX8000-COMMON-MIB - TextualConvention - LogbookEntryMessagesExcTv for details."
            ::= { logbookEntry 5 }

        
        logbookDateTime OBJECT-TYPE
            SYNTAX DateAndTime
            MAX-ACCESS read-only
            STATUS current
            DESCRIPTION
                "The time of the logbook entry."
            ::= { logbookEntry 6 }

        
        rsXx8000IsdbtExcProductInfoTable OBJECT-TYPE
            SYNTAX SEQUENCE OF RsXx8000IsdbtExcProductInfoEntry
            MAX-ACCESS not-accessible
            STATUS current
            DESCRIPTION
                "The table for product typeplates."
            ::= { rsXx8000IsdbtExcObjs 100 }

        
        rsXx8000IsdbtExcProductInfoEntry OBJECT-TYPE
            SYNTAX RsXx8000IsdbtExcProductInfoEntry
            MAX-ACCESS not-accessible
            STATUS current
            DESCRIPTION
                "An entry in the rsXx8000IsdbtExcProductInfoTable."
            INDEX { prodInfoModuleIdx, cmdTxIdx, cmdExcIdx }
            ::= { rsXx8000IsdbtExcProductInfoTable 1 }

        
        RsXx8000IsdbtExcProductInfoEntry ::=
            SEQUENCE { 
                prodInfoModuleIdx
                    ProdInfoModuleNameTv,
                prodInfoModuleName
                    ProdInfoModuleNameTv,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime
             }

        prodInfoModuleIdx OBJECT-TYPE
            SYNTAX ProdInfoModuleNameTv
            MAX-ACCESS not-accessible
            STATUS current
            DESCRIPTION
                "The module index."
            ::= { rsXx8000IsdbtExcProductInfoEntry 1 }

        
        prodInfoModuleName OBJECT-TYPE
            SYNTAX ProdInfoModuleNameTv
            MAX-ACCESS read-only
            STATUS current
            DESCRIPTION
                "The readable module type."
            ::= { rsXx8000IsdbtExcProductInfoEntry 6 }

        
        prodInfoSerialNumber OBJECT-TYPE
            SYNTAX ReadableString
            MAX-ACCESS read-only
            STATUS current
            DESCRIPTION
                "The serial number of the subdevice."
            ::= { rsXx8000IsdbtExcProductInfoEntry 7 }

        
        prodInfoIdentNumberSW OBJECT-TYPE
            SYNTAX ReadableString
            MAX-ACCESS read-only
            STATUS current
            DESCRIPTION
                "The Rohde&Schwarz identification number of the software, for example 
                2094.2090.02."
            ::= { rsXx8000IsdbtExcProductInfoEntry 8 }

        
        prodInfoVersionNumberSW OBJECT-TYPE
            SYNTAX ReadableString
            MAX-ACCESS read-only
            STATUS current
            DESCRIPTION
                "The Rohde&Schwarz revision number of the software, for example 1.2.1."
            ::= { rsXx8000IsdbtExcProductInfoEntry 9 }

        
        prodInfoIdentNumberHW OBJECT-TYPE
            SYNTAX ReadableString
            MAX-ACCESS read-only
            STATUS current
            DESCRIPTION
                "The Rohde&Schwarz identification number of the hardware, for example 
                2095.8007.02 (NetCCU)."
            ::= { rsXx8000IsdbtExcProductInfoEntry 10 }

        
        prodInfoVersionNumberHW OBJECT-TYPE
            SYNTAX ReadableString
            MAX-ACCESS read-only
            STATUS current
            DESCRIPTION
                "The Rohde&Schwarz revision number (product index) of the hardware, for example 
                03.03."
            ::= { rsXx8000IsdbtExcProductInfoEntry 11 }

        
        productInfoProductDateHW OBJECT-TYPE
            SYNTAX DateAndTime
            MAX-ACCESS read-only
            STATUS current
            DESCRIPTION
                "The Rohde&Schwarz production date of the hardware,"
            ::= { rsXx8000IsdbtExcProductInfoEntry 12 }

        
        rsXx8000IsdbtExcEvents OBJECT IDENTIFIER ::= { rsXx8000IsdbtExc 3 }

        
        rsXx8000IsdbtExcEventsV2 OBJECT IDENTIFIER ::= { rsXx8000IsdbtExcEvents 0 }

        
        txExcSummaryFault NOTIFICATION-TYPE
            OBJECTS { eventAlarmClass, rsXx8000IsdbtExcEvtPriority, rsXx8000IsdbtExcEvent }
            STATUS current
            DESCRIPTION 
                "Exciter Summary Fault."
            ::= { rsXx8000IsdbtExcEventsV2 100 }

        
        txExcSummaryWarning NOTIFICATION-TYPE
            OBJECTS { eventAlarmClass, rsXx8000IsdbtExcEvtPriority, rsXx8000IsdbtExcEvent }
            STATUS current
            DESCRIPTION 
                "Exciter Summary Warning."
            ::= { rsXx8000IsdbtExcEventsV2 101 }

        
        txExcLocal NOTIFICATION-TYPE
            OBJECTS { eventAlarmClass, rsXx8000IsdbtExcEvtPriority, rsXx8000IsdbtExcEvent }
            STATUS current
            DESCRIPTION 
                "Exciter Local/Remote"
            ::= { rsXx8000IsdbtExcEventsV2 102 }

        
        txExcInputNoConnectTS1 NOTIFICATION-TYPE
            OBJECTS { eventAlarmClass, rsXx8000IsdbtExcEvtPriority, rsXx8000IsdbtExcEvent }
            STATUS current
            DESCRIPTION 
                "Exciter Input 1 has no connected input signal"
            ::= { rsXx8000IsdbtExcEventsV2 105 }

        
        txExcInputNoConnectTS2 NOTIFICATION-TYPE
            OBJECTS { eventAlarmClass, rsXx8000IsdbtExcEvtPriority, rsXx8000IsdbtExcEvent }
            STATUS current
            DESCRIPTION 
                "Exciter Input 2 has no connected input signal"
            ::= { rsXx8000IsdbtExcEventsV2 107 }

        
        txExcInputActiveTS1 NOTIFICATION-TYPE
            OBJECTS { eventAlarmClass, rsXx8000IsdbtExcEvtPriority, rsXx8000IsdbtExcEvent }
            STATUS current
            DESCRIPTION 
                "Exciter Input 1 is active"
            ::= { rsXx8000IsdbtExcEventsV2 109 }

        
        txExcInputActiveTS2 NOTIFICATION-TYPE
            OBJECTS { eventAlarmClass, rsXx8000IsdbtExcEvtPriority, rsXx8000IsdbtExcEvent }
            STATUS current
            DESCRIPTION 
                "Exciter Input 2 is active"
            ::= { rsXx8000IsdbtExcEventsV2 111 }

        
        txExcOn NOTIFICATION-TYPE
            OBJECTS { eventAlarmClass, rsXx8000IsdbtExcEvtPriority, rsXx8000IsdbtExcEvent }
            STATUS current
            DESCRIPTION 
                "Exciter On"
            ::= { rsXx8000IsdbtExcEventsV2 113 }

        
        txExcRfOn NOTIFICATION-TYPE
            OBJECTS { eventAlarmClass, rsXx8000IsdbtExcEvtPriority, rsXx8000IsdbtExcEvent }
            STATUS current
            DESCRIPTION 
                "Exciter RF On"
            ::= { rsXx8000IsdbtExcEventsV2 114 }

        
        txExcNoInput NOTIFICATION-TYPE
            OBJECTS { eventAlarmClass, rsXx8000IsdbtExcEvtPriority, rsXx8000IsdbtExcEvent }
            STATUS current
            DESCRIPTION 
                "Exciter has no valid input signal."
            ::= { rsXx8000IsdbtExcEventsV2 115 }

        
        txExcRfLoop NOTIFICATION-TYPE
            OBJECTS { eventAlarmClass, rsXx8000IsdbtExcEvtPriority, rsXx8000IsdbtExcEvent }
            STATUS current
            DESCRIPTION 
                "Exciter RF loop"
            ::= { rsXx8000IsdbtExcEventsV2 116 }

        
        txExcRfFail NOTIFICATION-TYPE
            OBJECTS { eventAlarmClass, rsXx8000IsdbtExcEvtPriority, rsXx8000IsdbtExcEvent }
            STATUS current
            DESCRIPTION 
                "Exciter RF Fail"
            ::= { rsXx8000IsdbtExcEventsV2 117 }

        
        txExcSelfTest NOTIFICATION-TYPE
            OBJECTS { eventAlarmClass, rsXx8000IsdbtExcEvtPriority, rsXx8000IsdbtExcEvent }
            STATUS current
            DESCRIPTION 
                "Exciter hardware self test"
            ::= { rsXx8000IsdbtExcEventsV2 118 }

        
        txExcOutputOpen NOTIFICATION-TYPE
            OBJECTS { eventAlarmClass, rsXx8000IsdbtExcEvtPriority, rsXx8000IsdbtExcEvent }
            STATUS current
            DESCRIPTION 
                "Exciter output open"
            ::= { rsXx8000IsdbtExcEventsV2 119 }

        
        txExcBoardTemperatureWarning NOTIFICATION-TYPE
            OBJECTS { eventAlarmClass, rsXx8000IsdbtExcEvtPriority, rsXx8000IsdbtExcEvent }
            STATUS current
            DESCRIPTION 
                "Exciter Board Temperature"
            ::= { rsXx8000IsdbtExcEventsV2 120 }

        
        txExcFanWarning NOTIFICATION-TYPE
            OBJECTS { eventAlarmClass, rsXx8000IsdbtExcEvtPriority, rsXx8000IsdbtExcEvent }
            STATUS current
            DESCRIPTION 
                "Exciter has one faulty fan"
            ::= { rsXx8000IsdbtExcEventsV2 121 }

        
        txExcFanFault NOTIFICATION-TYPE
            OBJECTS { eventAlarmClass, rsXx8000IsdbtExcEvtPriority, rsXx8000IsdbtExcEvent }
            STATUS current
            DESCRIPTION 
                "Both exciter fans are faulty."
            ::= { rsXx8000IsdbtExcEventsV2 122 }

        
        txExcFifoWarning NOTIFICATION-TYPE
            OBJECTS { eventAlarmClass, rsXx8000IsdbtExcEvtPriority, rsXx8000IsdbtExcEvent }
            STATUS current
            DESCRIPTION 
                "Exciter Fifo"
            ::= { rsXx8000IsdbtExcEventsV2 123 }

        
        txExcTestSignal NOTIFICATION-TYPE
            OBJECTS { eventAlarmClass, rsXx8000IsdbtExcEvtPriority, rsXx8000IsdbtExcEvent }
            STATUS current
            DESCRIPTION 
                "Exciter Testsignal Active"
            ::= { rsXx8000IsdbtExcEventsV2 124 }

        
        txExcSFNDelay NOTIFICATION-TYPE
            OBJECTS { eventAlarmClass, rsXx8000IsdbtExcEvtPriority, rsXx8000IsdbtExcEvent }
            STATUS current
            DESCRIPTION 
                "Exciter SFN Delay Fault"
            ::= { rsXx8000IsdbtExcEventsV2 125 }

        
        txExcWrongDatarate NOTIFICATION-TYPE
            OBJECTS { eventAlarmClass, rsXx8000IsdbtExcEvtPriority, rsXx8000IsdbtExcEvent }
            STATUS current
            DESCRIPTION 
                "Exciter Wrong Datarate"
            ::= { rsXx8000IsdbtExcEventsV2 126 }

        
        txExcMute NOTIFICATION-TYPE
            OBJECTS { eventAlarmClass, rsXx8000IsdbtExcEvtPriority, rsXx8000IsdbtExcEvent }
            STATUS current
            DESCRIPTION 
                "Exciter Mute"
            ::= { rsXx8000IsdbtExcEventsV2 127 }

        
        txExcPPSFail NOTIFICATION-TYPE
            OBJECTS { eventAlarmClass, rsXx8000IsdbtExcEvtPriority, rsXx8000IsdbtExcEvent }
            STATUS current
            DESCRIPTION 
                "Exciter PPS Fail"
            ::= { rsXx8000IsdbtExcEventsV2 128 }

        
        txExcReferenceFail NOTIFICATION-TYPE
            OBJECTS { eventAlarmClass, rsXx8000IsdbtExcEvtPriority, rsXx8000IsdbtExcEvent }
            STATUS current
            DESCRIPTION 
                "Exciter Reference Fail"
            ::= { rsXx8000IsdbtExcEventsV2 129 }

        
        txExcIIPFail NOTIFICATION-TYPE
            OBJECTS { eventAlarmClass, rsXx8000IsdbtExcEvtPriority, rsXx8000IsdbtExcEvent }
            STATUS current
            DESCRIPTION 
                "Exciter IIP Fail"
            ::= { rsXx8000IsdbtExcEventsV2 130 }

        
        rsXx8000IsdbtExcEventsTable OBJECT-TYPE
            SYNTAX SEQUENCE OF RsXx8000IsdbtExcEventsEntry
            MAX-ACCESS not-accessible
            STATUS current
            DESCRIPTION
                "This table contains necessary information for handling alarms.
                For each alarm you have the following information:
                - name (get),
                - mask to enable/disable sending out (set/get),
                - priority (set/get) and
                - the current state (get only)."
            ::= { rsXx8000IsdbtExcEvents 1 }

        
        rsXx8000IsdbtExcEventsEntry OBJECT-TYPE
            SYNTAX RsXx8000IsdbtExcEventsEntry
            MAX-ACCESS not-accessible
            STATUS current
            DESCRIPTION
                "An entry in the rsXx8000IsdbtExcEventsTable."
            INDEX { cmdTxIdx, cmdExcIdx, rsXx8000IsdbtExcEvtNameIdx }
            ::= { rsXx8000IsdbtExcEventsTable 1 }

        
        RsXx8000IsdbtExcEventsEntry ::=
            SEQUENCE { 
                rsXx8000IsdbtExcEvtNameIdx
                    EventMaxEntryNumber,
                rsXx8000IsdbtExcEvtName
                    INTEGER,
                rsXx8000IsdbtExcEvtMask
                    EventMask,
                rsXx8000IsdbtExcEvtPriority
                    EventPriority,
                rsXx8000IsdbtExcEvent
                    EventState
             }

        rsXx8000IsdbtExcEvtNameIdx OBJECT-TYPE
            SYNTAX EventMaxEntryNumber
            MAX-ACCESS not-accessible
            STATUS current
            DESCRIPTION
                "The event number as integer.
                This is a helper column and therefore not-accessible."
            ::= { rsXx8000IsdbtExcEventsEntry 3 }

        
        rsXx8000IsdbtExcEvtName OBJECT-TYPE
            SYNTAX INTEGER
                {
                txExcSummaryFault(100),
                txExcSummaryWarning(101),
                txExcLocal(102),
                txExcInputNoConnectTS1(105),
                txExcInputNoConnectTS2(107),
                txExcInputActiveTS1(109),
                txExcInputActiveTS2(111),
                txExcOn(113),
                txExcRfOn(114),
                txExcNoInput(115),
                txExcRfLoop(116),
                txExcRfFail(117),
                txExcSelfTest(118),
                txExcOutputOpen(119),
                txExcBoardTemperatureWarning(120),
                txExcFanWarning(121),
                txExcFanFault(122),
                txExcFifoWarning(123),
                txExcTestSignal(124),
                txExcSFNDelay(125),
                txExcWrongDatarate(126),
                txExcMute(127),
                txExcPPSFail(128),
                txExcReferenceFail(129),
                txExcIIPFail(130)
                }
            MAX-ACCESS read-only
            STATUS current
            DESCRIPTION
                "The event name as readable integer.
                The enumeration correlates with the notifications
                below rsXx8000IsdbtExcEventsV2."
            ::= { rsXx8000IsdbtExcEventsEntry 4 }

        
        rsXx8000IsdbtExcEvtMask OBJECT-TYPE
            SYNTAX EventMask
            MAX-ACCESS read-write
            STATUS current
            DESCRIPTION
                "See textual convention for details."
            ::= { rsXx8000IsdbtExcEventsEntry 5 }

        
        rsXx8000IsdbtExcEvtPriority OBJECT-TYPE
            SYNTAX EventPriority
            MAX-ACCESS read-write
            STATUS current
            DESCRIPTION
                "See textual convention for details."
            ::= { rsXx8000IsdbtExcEventsEntry 6 }

        
        rsXx8000IsdbtExcEvent OBJECT-TYPE
            SYNTAX EventState
            MAX-ACCESS read-only
            STATUS current
            DESCRIPTION
                "See textual convention for details."
            ::= { rsXx8000IsdbtExcEventsEntry 7 }

        
        rsXx8000IsdbtExcConf OBJECT IDENTIFIER ::= { rsXx8000IsdbtExc 5 }

        
        rsXx8000IsdbtExcGroups OBJECT IDENTIFIER ::= { rsXx8000IsdbtExcConf 1 }

        
        rsXx8000IsdbtExcObjjGeneral OBJECT-GROUP
            OBJECTS { cmdExcOpModeInputAutomatic, cmdExcPreselectInput, cmdExcSfnMode, cmdExcNetworkMode, cmdExcCoderSettingsSource, 
                cmdExcTmccNextControl, cmdExcTxAutomatic, cmdExcStaticUserDelay, cmdExcInputPriority, cmdExcInputCheckTimeForward, 
                cmdExcInputCheckTimeSwitchback, cmdExcInputMuteOnFail, cmdExcPartialReception, cmdExcISDBtMode, cmdExcTPSManualGuardInterval, 
                cmdExcTestMode, cmdExcSFNStaticDelay, cmdExcSFNDeviationTime, cmdExcFrequency, cmdExcReferenceSource, 
                cmdExcMuteOnPPSFail, cmdExcMuteOnReferenceFail, cmdExcRefFailDelayTime, cmdExcTypeLossOfInput, cmdExcRfOutput, 
                cmdExcRfOutputRegulation, cmdExcRfOutputManualRfLevel, cmdExcRfOutputAttenuation, cmdExcRfOutputRfSlope, cmdExcRfOutputModulationSlope, 
                cmdExcRfIqAdjustStart, cmdExcRfIqAdjustTestsignal, cmdExcRfIqAdjustBiasCoarseI, cmdExcRfIqAdjustBiasCoarseQ, cmdExcRfIqAdjustBiasFineI, 
                cmdExcRfIqAdjustBiasFineQ, cmdExcRfIqAdjustGainI, cmdExcRfIqAdjustGainQ, cmdExcRfIqAdjustPhase, cmdExcInputFailDelayTime, 
                cmdExcOcxoAdjust, cmdExcFailDelayMode, excInputChannelName, excInputConnected, excInputPreselected, 
                excInputActive, excInputPacketLength, excInputMeasuredDatarate, excInputRequiredDatarate, excStatusRfOutputAgcRegulation, 
                excStatusRfIqAdjustAuto, excStatusRfIqAdjustLO1Frequency, excStatusISDBtMode, excStatusGuardInterval, excStatusPartialReception, 
                excStatusSfnDelayProcessing, excStatusSfnDelayDynamic, excStatusSfnDelayNetwork, excStatusSfnDelayTxOffset, excStatusSfnDelayMaximum, 
                excStatusSfnDelayTotal, excStatusSfnMode, excStatusFailDelay, excPrecLinCorrection, excPrecLinAutomaticADE, 
                excPrecLinMaxAmplitudeRipple, excPrecLinMaxGroupDelayRipple, excPrecLinAmplitudeRipple, excPrecLinGroupDelayRipple, excPrecLinInputLevel, 
                excPrecLinAutomatic, excPrecNonlinCorrection, excPrecNonlinAutomaticADE, excPrecNonlinThresholdShoulders, excPrecNonlinShoulderLeft, 
                excPrecNonlinShoulderRight, excPrecNonlinInputLevel, excPrecNonlinAutomatic, excPrecExtendedGroupDelay, tmccSegments, 
                tmccConstellation, tmccCodeRate, tmccTimeInterleaver, nitNetworkIdSource, nitNetworkId, 
                nitTransportStreamIdSource, nitTransportStreamId, nitAreaCodeSource, nitAreaCode, nitFrequencySource, 
                nitFrequency, nitRemoteControlKeyIdSource, nitRemoteControlKeyId }
            STATUS current
            DESCRIPTION 
                "Group for common objects of ISDB-T exciters."
            ::= { rsXx8000IsdbtExcGroups 1 }

        
        rsXx8000IsdbtExcObjLogbook OBJECT-GROUP
            OBJECTS { lbCfgNumberOfEntries, lbCfgClear, logbookEntryNbr, logbookType, logbookSlope, 
                logbookMessage, logbookDateTime }
            STATUS current
            DESCRIPTION 
                "Group for objects of the logbook."
            ::= { rsXx8000IsdbtExcGroups 2 }

        
        rsXx8000IsdbtExcObjProductInfo OBJECT-GROUP
            OBJECTS { prodInfoModuleName, prodInfoSerialNumber, prodInfoIdentNumberSW, prodInfoVersionNumberSW, prodInfoIdentNumberHW, 
                prodInfoVersionNumberHW, productInfoProductDateHW }
            STATUS current
            DESCRIPTION 
                "Group for objects of the rsXx8000IsdbtExcProductInfoTable."
            ::= { rsXx8000IsdbtExcGroups 3 }

        
        rsXx8000IsdbtExcObjEventsTable OBJECT-GROUP
            OBJECTS { rsXx8000IsdbtExcEvtName, rsXx8000IsdbtExcEvtMask, rsXx8000IsdbtExcEvtPriority, rsXx8000IsdbtExcEvent }
            STATUS current
            DESCRIPTION 
                "Group for all objects of the rsXx8000IsdbtExcEventsTable."
            ::= { rsXx8000IsdbtExcGroups 4 }

        
        rsXx8000IsdbtExcNotifyGeneral NOTIFICATION-GROUP
            NOTIFICATIONS { txExcSummaryFault, txExcSummaryWarning, txExcLocal, txExcInputNoConnectTS1, txExcInputNoConnectTS2, 
                txExcInputActiveTS1, txExcInputActiveTS2, txExcOn, txExcRfOn, txExcNoInput, 
                txExcRfLoop, txExcRfFail, txExcSelfTest, txExcOutputOpen, txExcBoardTemperatureWarning, 
                txExcFanWarning, txExcFanFault, txExcFifoWarning, txExcTestSignal, txExcSFNDelay, 
                txExcWrongDatarate, txExcMute, txExcPPSFail, txExcReferenceFail, txExcIIPFail
                 }
            STATUS current
            DESCRIPTION 
                "Group for common notifications of ISDB-T exciters."
            ::= { rsXx8000IsdbtExcGroups 5 }

        
        rsXx8000IsdbtExcCompls OBJECT IDENTIFIER ::= { rsXx8000IsdbtExcConf 2 }

        
        rsXx8000IsdbtExciter MODULE-COMPLIANCE
            STATUS current
            DESCRIPTION 
                "ISDB-T exciters."
            MODULE -- this module
                MANDATORY-GROUPS { rsXx8000IsdbtExcObjjGeneral, rsXx8000IsdbtExcNotifyGeneral }
            ::= { rsXx8000IsdbtExcCompls 1 }

        
    
    END

--
-- RS-XX8000-ISDBT-EXC-MIB.mi2
--
