-- *****************************************************************************
-- *****************************************************************************
-- **
-- **  COPYRIGHT      (c) 2007 Rohde & Schwarz GmbH & Co. KG
-- **                          Muehldorfstrasse 15
-- **    R & S                 D-81671 Muenchen
-- **
-- *****************************************************************************
-- **
-- **  MODULE         RS-XX8000-ATV-TX-MIB
-- **  
-- **  DESCRIPTION    Rohde & Schwarz SNMP
-- **
-- **  HISTORY        
-- **  2007-12-17 sr - preliminary version
-- **  2008-02-29 hu - initial version
-- **  2008-03-31 sr - change range of cmdTxDelayTimeExcAutomatic and
-- **                  cmdTxDelayTimeOstAutomatic to 1..60
-- **  2008-05-08 sr - cmdExcReferenceSource with value internGPS
-- **  2008-07-24 sr - new SLx parameters: cmdExcTimeScheduler, configurationTable and
-- **                                      timeSchedulerTable
-- **                - use TC 'AtvStandard'
-- **  2008-08-26 ks - rfProbesNetCCURfProbe1, rfProbesNetCCURfProbe2 read-only
-- **                - cmdTxParametersetReSave obsolete
-- **  2008-08-29 hu - changed TC for LogbookMessages imported
-- **                  from RS-XX8000-COMMON-MIB
-- **  2008-09-15 sr - new rackTable
-- **                - new txRackRfWarning, txRackRfFault, txRackReflectionWarning,
-- **                      txRackReflectionFault
-- **                - new groupIndependentRacks
-- **  2008-10-08 sr - cmdExcFrequency and configFrequency range up to 1500 MHz
-- **  2008-11-04 ks - new cmdExcTypeLossOfInput
-- **  2008-12-12 sr - rfProbeConfigurationLabel obsolete
-- **                - txRackExtCoolingWarning renamed to txRackGpiWarning
-- **                - txRackExtCoolingFault renamed to txRackGpiFault
-- **  2009-01-07 sr - rfProbeCalibrationSetGain, rfProbeCalibrationSetOffset
-- **  2009-03-30 ks - txRackProbeNotCalibrated added
-- **                - txParamSetSubDeviceDiffers obsoleted
-- **  2009-05-28 ks - information for additional (external) power supply added
-- **                - txRackRfOn, txRackRfOk, txRackTemperatureWarning  added
-- **  2009-06-26 ks - consideration of face-lift configuration in module compliances
-- **                - measured values for power supply added
-- **                - conditional groupDummyLoadRF added
-- **  2009-07-16 ks - additional values for reserve concept 'backup exciter'
-- **  2009-09-10 ks - cmdTxSystemMode added
-- **                - traps for TX mode switch over added
-- **  2009-10-08 ks - txRackOvervoltProtectWarning added
-- **  2009-11-13 ks - ostRackAmpDeltaPhase, ostRackAmpCmdDeltaPhase added
-- **  2009-12-02 ks - configRxFrequency, configInputSource added
-- **  2009-12-04 ks - configuration2Table added
-- **  2009-12-07 ks - excStatusNominalPower added
-- **  2010-01-12 ks - excStatusVSWR added
-- **  2010-01-29 ks - txNetCCUBoardTemperatureFault deprecated,
-- **                  txNetCCUBoardTemperatureWarning added
-- **  2010-05-21 ks - cmdTxRfSwitch added
-- **  2011-03-01 ks - Amplifier status for Sx801 added.
-- **  2011-05-12 ks - cmdExcFailDelayMode, excStatusFailDelay added
-- **  2012-08-21 ks - sx801AmplifierTable measured values added
-- **
-- *****************************************************************************
-- *****************************************************************************

    RS-XX8000-ATV-TX-MIB DEFINITIONS ::= BEGIN
 
        IMPORTS
            rsXx8000, eventAlarmPriority, eventAlarmClass, eventEvent, indexAB, 
            indexRack, indexAmplifier, rsXx8000MibModule, EventPriority, EventClass, 
            EventState, IndexAB, IndexRack, IndexAmplifier, Trigger, 
            SwitchOnOff, TvStandard, LockState, AtvStandard, FloatingPoint, 
            EqualizerCalibrationState, ProdInfoModuleNameTv, ReadableString, LogbookMaxEntryNumber, LogbookEntrySlope, 
            LogbookEntryMessagesNetCCU, LogbookEntryMessagesExcTv, LogbookEntryMessagesOST, EventMaxEntryNumber, EventMask, 
            InputSource, Sx801AmplifierState, FailDelayMode, FailDelayStatus            
                FROM RS-XX8000-COMMON-MIB            
            OBJECT-GROUP, MODULE-COMPLIANCE, NOTIFICATION-GROUP            
                FROM SNMPv2-CONF            
            Integer32, OBJECT-TYPE, MODULE-IDENTITY, OBJECT-IDENTITY, NOTIFICATION-TYPE            
                FROM SNMPv2-SMI            
            TruthValue, DateAndTime, RowStatus            
                FROM SNMPv2-TC;
    
    
        rsXx8000AtvTxMibModule MODULE-IDENTITY 
            LAST-UPDATED "201208210800Z"		-- August 21, 2012 at 08:00 GMT
            ORGANIZATION 
                "Rohde&Schwarz GmbH & Co. KG"
            CONTACT-INFO 
                "Torsten Huebscher
                Department 7TS2
                Broadcasting Division
                Muehldorfstrasse 15
                81671 Munich, Germany
                torsten.huebscher@rohde-schwarz.com"
            DESCRIPTION 
                "This MIB defines transmitting systems from Rohde & Schwarz.
                
                Use this MIB if your system meets the following requirements:
                - series XX8000 (NetCCU800),
                - ATV (analog TV),
                - transmitter reserve concept SingleTx, DualDrive,
                  Active Reserve or Passive Reserve.
                
                The following MIBs are related to this:
                - RS-COMMON-MIB         - mandatory for this MIB
                - RS-XX8000-COMMON-MIB  - mandatory for this MIB"
            REVISION "201208210800Z"		-- August 21, 2012 at 08:00 GMT
            DESCRIPTION 
                "sx801AmplifierTable measured values added"
            REVISION "201105120800Z"		-- May 12, 2011 at 08:00 GMT
            DESCRIPTION 
                "cmdExcFailDelayMode, excStatusFailDelay added"
            REVISION "201103010800Z"		-- March 01, 2011 at 08:00 GMT
            DESCRIPTION 
                "Amplifier status for Sx801 added."
            REVISION "201005210800Z"		-- May 21, 2010 at 08:00 GMT
            DESCRIPTION 
                "cmdTxRfSwitch added"
            REVISION "201001290800Z"		-- January 29, 2010 at 08:00 GMT
            DESCRIPTION 
                "txNetCCUBoardTemperatureFault deprecated,
                txNetCCUBoardTemperatureWarning added"
            REVISION "201001120800Z"		-- January 12, 2010 at 08:00 GMT
            DESCRIPTION 
                "excStatusVSWR added"
            REVISION "200912020800Z"		-- December 02, 2009 at 08:00 GMT
            DESCRIPTION 
                "configRxFrequency,
                configInputSource, configuration2Table,
                excStatusNominalPower added"
            REVISION "200911130800Z"		-- November 13, 2009 at 08:00 GMT
            DESCRIPTION 
                "ostRackAmpDeltaPhase, ostRackAmpCmdDeltaPhase added"
            REVISION "200910080800Z"		-- October 08, 2009 at 08:00 GMT
            DESCRIPTION 
                "txRackOvervoltProtectWarning added"
            REVISION "200909100800Z"		-- September 10, 2009 at 08:00 GMT
            DESCRIPTION 
                "cmdTxSystemMode added
                traps for TX mode switch over added"
            REVISION "200907160800Z"		-- July 16, 2009 at 08:00 GMT
            DESCRIPTION 
                "additional values for reserve concept 'backup exciter'"
            REVISION "200906260800Z"		-- June 26, 2009 at 08:00 GMT
            DESCRIPTION 
                "consideration of face-lift configuration in module compliances,
                measured values for power supply added,
                conditional groupDummyLoadRF added"
            REVISION "200905280900Z"		-- May 28, 2009 at 09:00 GMT
            DESCRIPTION 
                "information for additional (external) power supply added
                txRackRfOn, txRackRfOk, txRackTemperatureWarning  added"
            REVISION "200903300900Z"		-- March 30, 2009 at 09:00 GMT
            DESCRIPTION 
                "txRackProbeNotCalibrated added
                txParamSetSubDeviceDiffers obsoleted"
            REVISION "200901071030Z"		-- January 07, 2009 at 10:30 GMT
            DESCRIPTION 
                "rfProbeCalibrationSetGain, rfProbeCalibrationSetOffset"
            REVISION "200812121430Z"		-- December 12, 2008 at 14:30 GMT
            DESCRIPTION 
                "rfProbeConfigurationLabel obsolete
                xRackExtCoolingWarning renamed to txRackGpiWarning
                txRackExtCoolingFault renamed to txRackGpiFault"
            REVISION "200811041000Z"		-- November 04, 2008 at 10:00 GMT
            DESCRIPTION 
                "new cmdExcTypeLossOfInput"
            REVISION "200810081000Z"		-- October 08, 2008 at 10:00 GMT
            DESCRIPTION 
                "cmdExcFrequency and configFrequency range up to 1500 MHz"
            REVISION "200809151200Z"		-- September 15, 2008 at 12:00 GMT
            DESCRIPTION 
                "new rackTable
                new txRackRfWarning, txRackRfFault, txRackReflectionWarning,
                    txRackReflectionFault
                new groupIndependentRacks"
            REVISION "200808291000Z"		-- August 29, 2008 at 10:00 GMT
            DESCRIPTION 
                "changed TC for LogbookMessages"
            REVISION "200808260900Z"		-- August 26, 2008 at 09:00 GMT
            DESCRIPTION 
                "- rfProbesNetCCURfProbe1, rfProbesNetCCURfProbe2 read-only
                - cmdTxParametersetReSave obsolete"
            REVISION "200807240730Z"		-- July 24, 2008 at 07:30 GMT
            DESCRIPTION 
                "- new SLx parameters: cmdExcTimeScheduler, configurationTable and
                timeSchedulerTable
                - use TC 'AtvStandard'"
            REVISION "200805080730Z"		-- May 08, 2008 at 07:30 GMT
            DESCRIPTION 
                "- cmdExcReferenceSource with value internGPS"
            REVISION "200804031455Z"		-- April 03, 2008 at 14:55 GMT
            DESCRIPTION 
                "- change range of cmdTxDelayTimeExcAutomatic and
                cmdTxDelayTimeOstAutomatic to 1..60
                - adds cmdExcConfNICAM, cmdExcTransmitterType, cmdExcOutputPower
                excPrecUserState, excPrecFactoryState, excPrecRestoreCurrentSettings, excPrecRestoreAllSettings"
            REVISION "200802291200Z"		-- February 29, 2008 at 12:00 GMT
            DESCRIPTION 
                "initial version"
            ::= { rsXx8000MibModule 34 }

        
    
    
--
-- Node definitions
--
    
        rsXx8000AtvTx OBJECT-IDENTITY
            STATUS current
            DESCRIPTION 
                "Xx8000 ATV transmitter."
            ::= { rsXx8000 34 }

        
-- *****************************************************************************
-- **          object definitions
-- *****************************************************************************
        rsXx8000AtvTxObjs OBJECT IDENTIFIER ::= { rsXx8000AtvTx 1 }

        
        commandsTxTable OBJECT-TYPE
            SYNTAX SEQUENCE OF CommandsTxEntry
            MAX-ACCESS not-accessible
            STATUS current
            DESCRIPTION
                "This table contains important commands for the transmitter."
            ::= { rsXx8000AtvTxObjs 1 }

        
        commandsTxEntry OBJECT-TYPE
            SYNTAX CommandsTxEntry
            MAX-ACCESS not-accessible
            STATUS current
            DESCRIPTION
                "An entry for a designated transmitter and device."
            INDEX { cmdDeviceIdx }
            ::= { commandsTxTable 1 }

        
        CommandsTxEntry ::=
            SEQUENCE { 
                cmdTxResetSumFault
                    Trigger,
                cmdTxParametersetLoad
                    Integer32,
                cmdTxParametersetSave
                    Integer32,
                cmdTxParametersetReSave
                    Trigger,
                cmdTxOperationModeProgram
                    SwitchOnOff,
                cmdTxOperationModeReserve
                    SwitchOnOff,
                cmdTxOpModeExcAutomatic
                    SwitchOnOff,
                cmdTxOpModeOstAutomatic
                    SwitchOnOff,
                cmdTxPreselectExciter
                    INTEGER,
                cmdTxPreselectOutputstage
                    INTEGER,
                cmdTxDelayTimeExcAutomatic
                    Integer32,
                cmdTxDelayTimeOstAutomatic
                    Integer32,
                cmdTxRfSwitch
                    INTEGER,
                cmdTxSystemMode
                    TvStandard,
                cmdTxProgramExciterPrio
                    SwitchOnOff,
                cmdTxChangeOver
                    Trigger,
                cmdTxSwitchPosition
                    INTEGER,
                cmdDeviceIdx
                    IndexAB,
                cmdExcCarrier
                    LockState,
                cmdExcConfNICAM
                    SwitchOnOff,
                cmdExcTvStandard
                    AtvStandard,
                cmdExcAfMode
                    INTEGER,
                cmdExcNicamMode
                    INTEGER,
                cmdExcNicamRolloff
                    INTEGER,
                cmdExcSoundSelect
                    INTEGER,
                cmdExcFmInput
                    INTEGER,
                cmdExcVideoInput
                    INTEGER,
                cmdExcVideoInputNominalLevel
                    INTEGER,
                cmdExcVideoInputLimiter
                    SwitchOnOff,
                cmdExcWhiteCtrlAutomatic
                    SwitchOnOff,
                cmdExcWhiteCtrlTestLine
                    Integer32,
                cmdExcWhiteCtrlGainSource
                    INTEGER,
                cmdExcWhiteCtrlManualGain
                    FloatingPoint,
                cmdExcWhiteLimiter
                    SwitchOnOff,
                cmdExcWhiteLimiterThreshold
                    FloatingPoint,
                cmdExcSyncRegeneration
                    SwitchOnOff,
                cmdExcSyncAmplitude
                    Integer32,
                cmdExcDiplexer
                    SwitchOnOff,
                cmdExcDiplexerPeaking
                    FloatingPoint,
                cmdExcDiplexerPreEqualization
                    SwitchOnOff,
                cmdExcAudioNominalLevelAF1
                    FloatingPoint,
                cmdExcAudioNominalLevelAF2
                    FloatingPoint,
                cmdExcAudioNominalLevelAF3
                    FloatingPoint,
                cmdExcAudioNominalLevelBTSC
                    FloatingPoint,
                cmdExcAudioInputLowpass
                    SwitchOnOff,
                cmdExcAudioInputPreemphasis
                    SwitchOnOff,
                cmdExcNicamInputPreemphasis
                    SwitchOnOff,
                cmdExcNicamGainAdjustAF1
                    FloatingPoint,
                cmdExcNicamGainAdjustAF2
                    FloatingPoint,
                cmdExcFmAudioMode
                    INTEGER,
                cmdExcFmAudioDataLine
                    Integer32,
                cmdExcFmAudioPilot
                    SwitchOnOff,
                cmdExcFmAudioPilotGain
                    FloatingPoint,
                cmdExcFmSubCarrier1
                    INTEGER,
                cmdExcFmSubCarrier2
                    INTEGER,
                cmdExcFmAf1Deviation
                    Integer32,
                cmdExcFmAf2Deviation
                    Integer32,
                cmdExcFmDeviationLimiter
                    SwitchOnOff,
                cmdExcFmDeviationLimiterThrshold
                    Integer32,
                cmdExcFmDeviationLimiterWrnThrsh
                    Integer32,
                cmdExcFmPrecorrChn1
                    SwitchOnOff,
                cmdExcFmPrecorrChn1Point1
                    FloatingPoint,
                cmdExcFmPrecorrChn1Slope1
                    FloatingPoint,
                cmdExcFmPrecorrChn1Point2
                    FloatingPoint,
                cmdExcFmPrecorrChn1Slope2
                    FloatingPoint,
                cmdExcFmPrecorrChn2
                    SwitchOnOff,
                cmdExcFmPrecorrChn2Point1
                    FloatingPoint,
                cmdExcFmPrecorrChn2Slope1
                    FloatingPoint,
                cmdExcFmPrecorrChn2Point2
                    FloatingPoint,
                cmdExcFmPrecorrChn2Slope2
                    FloatingPoint,
                cmdExcNicamAudioMode
                    INTEGER,
                cmdExcNicamAudioReserveSound
                    SwitchOnOff,
                cmdExcNicamPrecorrection
                    SwitchOnOff,
                cmdExcNicamInsertPrbs
                    SwitchOnOff,
                cmdExcFrequency
                    Integer32,
                cmdExcFrequencyOffset
                    Integer32,
                cmdExcReferenceSource
                    INTEGER,
                cmdExcOcxoAdjust
                    Integer32,
                cmdExcRfOutput
                    SwitchOnOff,
                cmdExcRfOutputRegulation
                    SwitchOnOff,
                cmdExcRfOutputManualRfLevel
                    FloatingPoint,
                cmdExcRfOutputAttenuation
                    Integer32,
                cmdExcRfOutputRfSlope
                    FloatingPoint,
                cmdExcRfOutputModulationSlope
                    FloatingPoint,
                cmdExcRfOutputCarrier1
                    FloatingPoint,
                cmdExcRfOutputCarrier2
                    FloatingPoint,
                cmdExcRfOutputResidualCarrier
                    FloatingPoint,
                cmdExcRfMonitorCommon
                    FloatingPoint,
                cmdExcRfMonitorSound1
                    FloatingPoint,
                cmdExcRfMonitorSound2
                    FloatingPoint,
                cmdExcLevelVsVisionAntennaSound1
                    FloatingPoint,
                cmdExcLevelVsVisionAntennaSound2
                    FloatingPoint,
                cmdExcRfIqAdjustStart
                    INTEGER,
                cmdExcRfIqAdjustTestsignal
                    SwitchOnOff,
                cmdExcRfIqAdjustBiasCoarseI
                    Integer32,
                cmdExcRfIqAdjustBiasCoarseQ
                    Integer32,
                cmdExcRfIqAdjustBiasFineI
                    Integer32,
                cmdExcRfIqAdjustBiasFineQ
                    Integer32,
                cmdExcRfIqAdjustGainI
                    Integer32,
                cmdExcRfIqAdjustGainQ
                    Integer32,
                cmdExcRfIqAdjustPhase
                    FloatingPoint,
                cmdExcTypeLossOfInput
                    INTEGER,
                cmdExcTransmitterType
                    INTEGER,
                cmdExcTimeScheduler
                    SwitchOnOff,
                cmdExcOutputPower
                    FloatingPoint,
                cmdOstRefVoltageVision
                    FloatingPoint,
                cmdOstMaxOutletTempThreshold
                    Integer32,
                cmdExcFailDelayMode
                    FailDelayMode
             }

        cmdTxResetSumFault OBJECT-TYPE
            SYNTAX Trigger
            MAX-ACCESS read-write
            STATUS current
            DESCRIPTION
                "Reset all faults (in all modules) of the transmitter.
                
                You reset a designated transmitter (NetCCU, Exciters, Outputstages).
                An equivalent would be pressing RESET at this transmitters frontpanel.
                
                A GET will always return idle(1). A SET idle(1) will return NO_ERROR without doing anything."
            ::= { commandsTxEntry 1 }

        
        cmdTxParametersetLoad OBJECT-TYPE
            SYNTAX Integer32 (1..8)
            MAX-ACCESS read-write
            STATUS current
            DESCRIPTION
                "This loads the desired parameter set."
            ::= { commandsTxEntry 2 }

        
        cmdTxParametersetSave OBJECT-TYPE
            SYNTAX Integer32 (1..8)
            MAX-ACCESS read-write
            STATUS current
            DESCRIPTION
                "This saves the current settings to a designated parameter set."
            ::= { commandsTxEntry 3 }

        
        cmdTxParametersetReSave OBJECT-TYPE
            SYNTAX Trigger
            MAX-ACCESS read-write
            STATUS obsolete
            DESCRIPTION
                "This saves the changes to the current parameter set."
            ::= { commandsTxEntry 4 }

        
        cmdTxOperationModeProgram OBJECT-TYPE
            SYNTAX SwitchOnOff
            MAX-ACCESS read-write
            STATUS current
            DESCRIPTION
                "This switches the program path of the transmitter on/off."
            ::= { commandsTxEntry 5 }

        
        cmdTxOperationModeReserve OBJECT-TYPE
            SYNTAX SwitchOnOff
            MAX-ACCESS read-write
            STATUS current
            DESCRIPTION
                "This switches the reserve path of the transmitter on/off."
            ::= { commandsTxEntry 6 }

        
        cmdTxOpModeExcAutomatic OBJECT-TYPE
            SYNTAX SwitchOnOff
            MAX-ACCESS read-write
            STATUS current
            DESCRIPTION
                "This switches the exciter automatic on/off."
            ::= { commandsTxEntry 7 }

        
        cmdTxOpModeOstAutomatic OBJECT-TYPE
            SYNTAX SwitchOnOff
            MAX-ACCESS read-write
            STATUS current
            DESCRIPTION
                "This switches the outputstage automatic on/off.
                
                This paramter is only available for systems with an automatic output switch."
            ::= { commandsTxEntry 8 }

        
        cmdTxPreselectExciter OBJECT-TYPE
            SYNTAX INTEGER
                {
                exciterA(1),
                exciterB(2)
                }
            MAX-ACCESS read-write
            STATUS current
            DESCRIPTION
                "This sets exciterA or exciterB to program path (antenna) of the transmitter."
            ::= { commandsTxEntry 9 }

        
        cmdTxPreselectOutputstage OBJECT-TYPE
            SYNTAX INTEGER
                {
                outputstageA(1),
                outputstageB(2),
                bothToAntenna(3),
                bothToDummyLoad(4)
                }
            MAX-ACCESS read-write
            STATUS current
            DESCRIPTION
                "This sets 
                - outputstageA or 
                - outputstageB or
                - both
                to program path (antenna) of the transmitter,
                or it sets both to dummyload.
                
                The settings bothToAntenna(3) and bothToDummyLoad(4) are only settable 
                for ActiveReserve systems.
                
                This paramter is only available for systems with an automatic output switch."
            ::= { commandsTxEntry 10 }

        
        cmdTxDelayTimeExcAutomatic OBJECT-TYPE
            SYNTAX Integer32 (1..60)
            UNITS "seconds"
            MAX-ACCESS read-write
            STATUS current
            DESCRIPTION
                "This sets the exciter automatic delay time."
            ::= { commandsTxEntry 11 }

        
        cmdTxDelayTimeOstAutomatic OBJECT-TYPE
            SYNTAX Integer32 (1..60)
            UNITS "seconds"
            MAX-ACCESS read-write
            STATUS current
            DESCRIPTION
                "This sets the outputstage automatic delay time.
                
                This paramter is only available for systems with an automatic output switch."
            ::= { commandsTxEntry 12 }

        
        cmdTxRfSwitch OBJECT-TYPE
            SYNTAX INTEGER
                {
                antenna(1),
                dummyLoad(2)
                }
            MAX-ACCESS read-write
            STATUS current
            DESCRIPTION
                "RF switch for single-ended systems."
            ::= { commandsTxEntry 13 }

        
        cmdTxSystemMode OBJECT-TYPE
            SYNTAX TvStandard
            MAX-ACCESS read-write
            STATUS current
            DESCRIPTION
                "This object gives you the possibility of switching the TV standard
                of a whole system with NetCCU with only one command.
                Not applicable for N+1 or NTx systems.
                The value 'test' cannot be written."
            ::= { commandsTxEntry 15 }

        
        cmdTxProgramExciterPrio OBJECT-TYPE
            SYNTAX SwitchOnOff
            MAX-ACCESS read-write
            STATUS current
            DESCRIPTION
                "Enables/Disables priority usage of program exciter"
            ::= { commandsTxEntry 20 }

        
        cmdTxChangeOver OBJECT-TYPE
            SYNTAX Trigger
            MAX-ACCESS read-write
            STATUS current
            DESCRIPTION
                "Performs a change over"
            ::= { commandsTxEntry 21 }

        
        cmdTxSwitchPosition OBJECT-TYPE
            SYNTAX INTEGER
                {
                undefined(1),
                controlExcOnAmp(2),
                programExcOnAmp(3)
                }
            MAX-ACCESS read-only
            STATUS current
            DESCRIPTION
                "Shows the actual switch position.
                The program exciter is connected to input 1 (RF IN 1),
                the control exciter is connected to input 2 (RF IN 2) of the base amplifier."
            ::= { commandsTxEntry 22 }

        
        cmdDeviceIdx OBJECT-TYPE
            SYNTAX IndexAB
            MAX-ACCESS not-accessible
            STATUS current
            DESCRIPTION
                "This column is used to show parameters for both exiters, if you have 
                dualdrive transmitters."
            ::= { commandsTxEntry 30 }

        
        cmdExcCarrier OBJECT-TYPE
            SYNTAX LockState
            MAX-ACCESS read-write
            STATUS current
            DESCRIPTION
                "In case of damage it might be useful to manually switch from carrier lock to unlock.
                Usually this command will be set from the Net CCU."
            ::= { commandsTxEntry 31 }

        
        cmdExcConfNICAM OBJECT-TYPE
            SYNTAX SwitchOnOff
            MAX-ACCESS read-write
            STATUS current
            DESCRIPTION
                "Switch between IRT and NICAM."
            ::= { commandsTxEntry 32 }

        
        cmdExcTvStandard OBJECT-TYPE
            SYNTAX AtvStandard
            MAX-ACCESS read-write
            STATUS current
            DESCRIPTION
                "Selection of the TV standard"
            ::= { commandsTxEntry 33 }

        
        cmdExcAfMode OBJECT-TYPE
            SYNTAX INTEGER
                {
                tone2(1),
                tone3(2)
                }
            MAX-ACCESS read-write
            STATUS current
            DESCRIPTION
                "Selection between dual-sound and triple-sound mode.
                This selection is available only if the second sound subcarrier
                is transmitted in accordance with NICAM and the coder mode
                is set under the Nicam mode."
            ::= { commandsTxEntry 34 }

        
        cmdExcNicamMode OBJECT-TYPE
            SYNTAX INTEGER
                {
                coder(1),
                modulator(2),
                extern(3)
                }
            MAX-ACCESS read-write
            STATUS current
            DESCRIPTION
                "Selection of the NICAM mode:
                - Coder: AF signal supply of AF1 and AF2 via the AUDIO input with encoding and modulation in the exciter
                - Modulator: Signal supply as a NICAM728 data stream via the NICAM DATA IN digital input
                - External: Signal supply of a modulated NICAM sound subcarrier via the NICAM SC IN input"
            ::= { commandsTxEntry 35 }

        
        cmdExcNicamRolloff OBJECT-TYPE
            SYNTAX INTEGER
                {
                auto(1),
                percent40(2),
                percent100(3)
                }
            MAX-ACCESS read-write
            STATUS current
            DESCRIPTION
                "Setting of the NICAM rolloff:
                - Auto: The NICAM rolloff is set automatically as the function of the selected TV standard and in compliance with the NICAM specifications (recommended setting!).
                - 40% / 100%: Manual setting of the NICAM rolloff"
            ::= { commandsTxEntry 36 }

        
        cmdExcSoundSelect OBJECT-TYPE
            SYNTAX INTEGER
                {
                singleCarrier(1),
                dualCarrier(2)
                }
            MAX-ACCESS read-write
            STATUS current
            DESCRIPTION
                "Selection of the number of sound subcarriers:
                - Single Carrier: One sound subcarrier
                - Dual Carrier: Two sound subcarriers"
            ::= { commandsTxEntry 37 }

        
        cmdExcFmInput OBJECT-TYPE
            SYNTAX INTEGER
                {
                af(1),
                btsc(2)
                }
            MAX-ACCESS read-write
            STATUS current
            DESCRIPTION
                "Selection of the audio input mode in standard M"
            ::= { commandsTxEntry 38 }

        
        cmdExcVideoInput OBJECT-TYPE
            SYNTAX INTEGER
                {
                vf1(1),
                vf2(2)
                }
            MAX-ACCESS read-write
            STATUS current
            DESCRIPTION
                "Selects the Video input connector.
                Note: Only VF1 can be monitored"
            ::= { commandsTxEntry 39 }

        
        cmdExcVideoInputNominalLevel OBJECT-TYPE
            SYNTAX INTEGER
                {
                v0p7(1),
                v1p0(2)
                }
            MAX-ACCESS read-write
            STATUS current
            DESCRIPTION
                "Selects the nominal video input level:
                0.7V or 1.0V"
            ::= { commandsTxEntry 40 }

        
        cmdExcVideoInputLimiter OBJECT-TYPE
            SYNTAX SwitchOnOff
            MAX-ACCESS read-write
            STATUS current
            DESCRIPTION
                "Limitation of input signal changes"
            ::= { commandsTxEntry 41 }

        
        cmdExcWhiteCtrlAutomatic OBJECT-TYPE
            SYNTAX SwitchOnOff
            MAX-ACCESS read-write
            STATUS current
            DESCRIPTION
                "enables/disables the automatic white pulse regulation"
            ::= { commandsTxEntry 42 }

        
        cmdExcWhiteCtrlTestLine OBJECT-TYPE
            SYNTAX Integer32 (16..22 | 48..54)
            MAX-ACCESS read-write
            STATUS current
            DESCRIPTION
                "Selects the test line for the white pulse.
                The test line can be in the first or second field
                for first half frame: 16-22
                for second half frame: 48-54 (==> 16-22 [+32])"
            ::= { commandsTxEntry 43 }

        
        cmdExcWhiteCtrlGainSource OBJECT-TYPE
            SYNTAX INTEGER
                {
                memory(1),
                manual(2)
                }
            MAX-ACCESS read-write
            STATUS current
            DESCRIPTION
                "Selects the source for fixed video gain in case of failure of the white pulse
                with white control simultaneously switched on.
                Only effective when white controller is OFF."
            ::= { commandsTxEntry 44 }

        
        cmdExcWhiteCtrlManualGain OBJECT-TYPE
            SYNTAX FloatingPoint
            UNITS "Percent"
            MAX-ACCESS read-write
            STATUS current
            DESCRIPTION
                "allows to set a manual value for the gain"
            ::= { commandsTxEntry 45 }

        
        cmdExcWhiteLimiter OBJECT-TYPE
            SYNTAX SwitchOnOff
            MAX-ACCESS read-write
            STATUS current
            DESCRIPTION
                "When the limiter is switched on all low frequency signal components
                that lie above a set threshold are filtered out."
            ::= { commandsTxEntry 46 }

        
        cmdExcWhiteLimiterThreshold OBJECT-TYPE
            SYNTAX FloatingPoint
            UNITS "Percent"
            MAX-ACCESS read-write
            STATUS current
            DESCRIPTION
                "Sets a threshold for the limiter."
            ::= { commandsTxEntry 47 }

        
        cmdExcSyncRegeneration OBJECT-TYPE
            SYNTAX SwitchOnOff
            MAX-ACCESS read-write
            STATUS current
            DESCRIPTION
                "If the sync impulse shall be regenerated manually this switch has to be set to 'on'.
                In case of an automatic sync control this parameter is disabled."
            ::= { commandsTxEntry 48 }

        
        cmdExcSyncAmplitude OBJECT-TYPE
            SYNTAX Integer32 (200..500)
            UNITS "mV"
            MAX-ACCESS read-write
            STATUS current
            DESCRIPTION
                "Adjust the amplitude for sync regeneration.
                This parameter is disabled if the automatic sync control is active."
            ::= { commandsTxEntry 49 }

        
        cmdExcDiplexer OBJECT-TYPE
            SYNTAX SwitchOnOff
            MAX-ACCESS read-write
            STATUS current
            DESCRIPTION
                "To equalize the frequency response of the diplexer,
                you can activate a frequency response emphasis function.
                Although the shape of the curve is fixed, you can set the
                magnitude of the emphasis at the band limit of the upper sideband."
            ::= { commandsTxEntry 50 }

        
        cmdExcDiplexerPeaking OBJECT-TYPE
            SYNTAX FloatingPoint
            UNITS "dB"
            MAX-ACCESS read-write
            STATUS current
            DESCRIPTION
                "Sets the diplexer peaking in the range from 0.1 dBm to 2.5 dBm
                at the band limit of the upper sideband."
            ::= { commandsTxEntry 51 }

        
        cmdExcDiplexerPreEqualization OBJECT-TYPE
            SYNTAX SwitchOnOff
            MAX-ACCESS read-write
            STATUS current
            DESCRIPTION
                "After the video signal processing, it is possible to perform receiver pre-equalization.
                When receiver pre-equalization is switched on,
                the fixed group delay curve required for the relevant standard is activated."
            ::= { commandsTxEntry 52 }

        
        cmdExcAudioNominalLevelAF1 OBJECT-TYPE
            SYNTAX FloatingPoint
            UNITS "dBu"
            MAX-ACCESS read-write
            STATUS current
            DESCRIPTION
                "Adjustment of audio level input VF 1 when it is used as IRT signal"
            ::= { commandsTxEntry 53 }

        
        cmdExcAudioNominalLevelAF2 OBJECT-TYPE
            SYNTAX FloatingPoint
            UNITS "dBu"
            MAX-ACCESS read-write
            STATUS current
            DESCRIPTION
                "Combined adjustment of audio level for input AF 2 and VF 3
                when it is used a IRT signal"
            ::= { commandsTxEntry 54 }

        
        cmdExcAudioNominalLevelAF3 OBJECT-TYPE
            SYNTAX FloatingPoint
            UNITS "dBu"
            MAX-ACCESS read-write
            STATUS current
            DESCRIPTION
                "Nominal Level AF3 (FM)"
            ::= { commandsTxEntry 55 }

        
        cmdExcAudioNominalLevelBTSC OBJECT-TYPE
            SYNTAX FloatingPoint
            UNITS "Vrms"
            MAX-ACCESS read-write
            STATUS current
            DESCRIPTION
                "Adjustment of audio level input VF 1 when it is used as IRT signal"
            ::= { commandsTxEntry 56 }

        
        cmdExcAudioInputLowpass OBJECT-TYPE
            SYNTAX SwitchOnOff
            MAX-ACCESS read-write
            STATUS current
            DESCRIPTION
                "enables/disables the lowpass filter"
            ::= { commandsTxEntry 57 }

        
        cmdExcAudioInputPreemphasis OBJECT-TYPE
            SYNTAX SwitchOnOff
            MAX-ACCESS read-write
            STATUS current
            DESCRIPTION
                "Preemphase"
            ::= { commandsTxEntry 58 }

        
        cmdExcNicamInputPreemphasis OBJECT-TYPE
            SYNTAX SwitchOnOff
            MAX-ACCESS read-write
            STATUS current
            DESCRIPTION
                "Preemphase NICAM"
            ::= { commandsTxEntry 59 }

        
        cmdExcNicamGainAdjustAF1 OBJECT-TYPE
            SYNTAX FloatingPoint
            UNITS "dB"
            MAX-ACCESS read-write
            STATUS current
            DESCRIPTION
                "Adjusts the nominal input level for the AF signal AF1
                which is fed to the integrated NICAM coder."
            ::= { commandsTxEntry 60 }

        
        cmdExcNicamGainAdjustAF2 OBJECT-TYPE
            SYNTAX FloatingPoint
            UNITS "dB"
            MAX-ACCESS read-write
            STATUS current
            DESCRIPTION
                "Adjusts the nominal input level for the AF signal AF2
                which is fed to the integrated NICAM coder."
            ::= { commandsTxEntry 61 }

        
        cmdExcFmAudioMode OBJECT-TYPE
            SYNTAX INTEGER
                {
                off(1),
                mono(2),
                stereo(3),
                dual(4),
                auto(5)
                }
            MAX-ACCESS read-write
            STATUS current
            DESCRIPTION
                "Selects the sound mode of both audio carriers.
                When set to 'auto' the information is automatically picked from the
                selected dataline if it contains the appropriate information."
            ::= { commandsTxEntry 62 }

        
        cmdExcFmAudioDataLine OBJECT-TYPE
            SYNTAX Integer32 (10..22)
            MAX-ACCESS read-write
            STATUS current
            DESCRIPTION
                "Selects the dataline of the first video frame which includes
                information about the current sound mode."
            ::= { commandsTxEntry 63 }

        
        cmdExcFmAudioPilot OBJECT-TYPE
            SYNTAX SwitchOnOff
            MAX-ACCESS read-write
            STATUS current
            DESCRIPTION
                "selects if the pilot shall be on or off"
            ::= { commandsTxEntry 64 }

        
        cmdExcFmAudioPilotGain OBJECT-TYPE
            SYNTAX FloatingPoint
            UNITS "dB"
            MAX-ACCESS read-write
            STATUS current
            DESCRIPTION
                "Adjust the level of the pilot signal"
            ::= { commandsTxEntry 65 }

        
        cmdExcFmSubCarrier1 OBJECT-TYPE
            SYNTAX INTEGER
                {
                off(1),
                modOff(2),
                on(3)
                }
            MAX-ACCESS read-write
            STATUS current
            DESCRIPTION
                "Selects the behaviour of audio carrier 1.
                The choosable items depends on the video and audio standards"
            ::= { commandsTxEntry 66 }

        
        cmdExcFmSubCarrier2 OBJECT-TYPE
            SYNTAX INTEGER
                {
                off(1),
                modOff(2),
                on(3)
                }
            MAX-ACCESS read-write
            STATUS current
            DESCRIPTION
                "Selects the behaviour of audio carrier 2.
                The choosable items depends on the video and audio.
                With this switch it is possible to activate NICAM audio standard."
            ::= { commandsTxEntry 67 }

        
        cmdExcFmAf1Deviation OBJECT-TYPE
            SYNTAX Integer32 (20000..75000)
            UNITS "Hz"
            MAX-ACCESS read-write
            STATUS current
            DESCRIPTION
                "AF1 Deviation"
            ::= { commandsTxEntry 68 }

        
        cmdExcFmAf2Deviation OBJECT-TYPE
            SYNTAX Integer32 (20000..75000)
            UNITS "Hz"
            MAX-ACCESS read-write
            STATUS current
            DESCRIPTION
                "AF2 Deviation"
            ::= { commandsTxEntry 69 }

        
        cmdExcFmDeviationLimiter OBJECT-TYPE
            SYNTAX SwitchOnOff
            MAX-ACCESS read-write
            STATUS current
            DESCRIPTION
                "Selects if the deviation limiter shall work or not."
            ::= { commandsTxEntry 70 }

        
        cmdExcFmDeviationLimiterThrshold OBJECT-TYPE
            SYNTAX Integer32 (50000..120000)
            UNITS "Hz"
            MAX-ACCESS read-write
            STATUS current
            DESCRIPTION
                "Sets a maximum threshold for frequency deviation."
            ::= { commandsTxEntry 71 }

        
        cmdExcFmDeviationLimiterWrnThrsh OBJECT-TYPE
            SYNTAX Integer32 (50000..250000)
            UNITS "Hz"
            MAX-ACCESS read-write
            STATUS current
            DESCRIPTION
                "Sets a level to generate a warning if the frequency deviation
                rises above this warning limit."
            ::= { commandsTxEntry 72 }

        
        cmdExcFmPrecorrChn1 OBJECT-TYPE
            SYNTAX SwitchOnOff
            MAX-ACCESS read-write
            STATUS current
            DESCRIPTION
                "Selects if the phase shifter for channel 1 shall work or not."
            ::= { commandsTxEntry 73 }

        
        cmdExcFmPrecorrChn1Point1 OBJECT-TYPE
            SYNTAX FloatingPoint
            UNITS "Percent"
            MAX-ACCESS read-write
            STATUS current
            DESCRIPTION
                "Sets the first sampling point for audio channel 1."
            ::= { commandsTxEntry 74 }

        
        cmdExcFmPrecorrChn1Slope1 OBJECT-TYPE
            SYNTAX FloatingPoint
            UNITS "Percent"
            MAX-ACCESS read-write
            STATUS current
            DESCRIPTION
                "Sets a slope for the first inset point audio carrier 1."
            ::= { commandsTxEntry 75 }

        
        cmdExcFmPrecorrChn1Point2 OBJECT-TYPE
            SYNTAX FloatingPoint
            UNITS "Percent"
            MAX-ACCESS read-write
            STATUS current
            DESCRIPTION
                "Sets the second sampling point for audio channel 1."
            ::= { commandsTxEntry 76 }

        
        cmdExcFmPrecorrChn1Slope2 OBJECT-TYPE
            SYNTAX FloatingPoint
            UNITS "Percent"
            MAX-ACCESS read-write
            STATUS current
            DESCRIPTION
                "Sets a slope for the second inset point audio carrier 1."
            ::= { commandsTxEntry 77 }

        
        cmdExcFmPrecorrChn2 OBJECT-TYPE
            SYNTAX SwitchOnOff
            MAX-ACCESS read-write
            STATUS current
            DESCRIPTION
                "Selects if the phase shifter for channel 2 shall work or not."
            ::= { commandsTxEntry 78 }

        
        cmdExcFmPrecorrChn2Point1 OBJECT-TYPE
            SYNTAX FloatingPoint
            UNITS "Percent"
            MAX-ACCESS read-write
            STATUS current
            DESCRIPTION
                "Sets the first sampling point for audio channel 2."
            ::= { commandsTxEntry 79 }

        
        cmdExcFmPrecorrChn2Slope1 OBJECT-TYPE
            SYNTAX FloatingPoint
            UNITS "Percent"
            MAX-ACCESS read-write
            STATUS current
            DESCRIPTION
                "Sets a slope for the first inset point audio carrier 2."
            ::= { commandsTxEntry 80 }

        
        cmdExcFmPrecorrChn2Point2 OBJECT-TYPE
            SYNTAX FloatingPoint
            UNITS "Percent"
            MAX-ACCESS read-write
            STATUS current
            DESCRIPTION
                "Sets the second sampling point for audio channel 2."
            ::= { commandsTxEntry 81 }

        
        cmdExcFmPrecorrChn2Slope2 OBJECT-TYPE
            SYNTAX FloatingPoint
            UNITS "Percent"
            MAX-ACCESS read-write
            STATUS current
            DESCRIPTION
                "Sets a slope for the second inset point audio carrier 2."
            ::= { commandsTxEntry 82 }

        
        cmdExcNicamAudioMode OBJECT-TYPE
            SYNTAX INTEGER
                {
                tonecoder(1),
                monoData(2),
                stereo(3),
                dual(4)
                }
            MAX-ACCESS read-write
            STATUS current
            DESCRIPTION
                "Determines the NICAM audio mode (possible only in the NICAM coder mode):
                - Equal FM Audio Mode: The NICAM audio mode is oriented towards the FM audio mode.
                - Mono/Data, Stereo and Dual Sound:
                  These settings determine the NICAM audio mode regardless of the FM channel;
                  the encoding takes place in accordance with the NICAM specifications."
            ::= { commandsTxEntry 83 }

        
        cmdExcNicamAudioReserveSound OBJECT-TYPE
            SYNTAX SwitchOnOff
            MAX-ACCESS read-write
            STATUS current
            DESCRIPTION
                "Reserve Sound switching Flag"
            ::= { commandsTxEntry 84 }

        
        cmdExcNicamPrecorrection OBJECT-TYPE
            SYNTAX SwitchOnOff
            MAX-ACCESS read-write
            STATUS current
            DESCRIPTION
                "Enables the NICAM precorrector"
            ::= { commandsTxEntry 85 }

        
        cmdExcNicamInsertPrbs OBJECT-TYPE
            SYNTAX SwitchOnOff
            MAX-ACCESS read-write
            STATUS current
            DESCRIPTION
                "generates a PRBS signal on the NICAM carrier for test purposes"
            ::= { commandsTxEntry 86 }

        
        cmdExcFrequency OBJECT-TYPE
            SYNTAX Integer32 (47000000..1500000000)
            UNITS "Hz"
            MAX-ACCESS read-write
            STATUS current
            DESCRIPTION
                "This is the RF frequency."
            ::= { commandsTxEntry 87 }

        
        cmdExcFrequencyOffset OBJECT-TYPE
            SYNTAX Integer32 (-1024..1024)
            MAX-ACCESS read-write
            STATUS current
            DESCRIPTION
                "Frequency Offset"
            ::= { commandsTxEntry 88 }

        
        cmdExcReferenceSource OBJECT-TYPE
            SYNTAX INTEGER
                {
                intern(1),
                extern5Mhz(2),
                extern10Mhz(3),
                extern1PPS(4),
                internGPS(5)
                }
            MAX-ACCESS read-write
            STATUS current
            DESCRIPTION
                "The Source of the reference signal.
                - Intern: the reference will be generated internally using an OCXO.
                  Only use this setting in multi frequency networks with low requirements
                  in frequency stability.
                - Extern 5 and 10 MHz: The signal generation will be synchronized to an
                  external reference.
                - 1PPS: the reference will be generated using a PPS for synchronisation
                - GPS: The value internGPS is not valid for SX800."
            ::= { commandsTxEntry 89 }

        
        cmdExcOcxoAdjust OBJECT-TYPE
            SYNTAX Integer32 (0..65535)
            MAX-ACCESS read-write
            STATUS current
            DESCRIPTION
                "Adjusts the internal reference (0 ... 65535)."
            ::= { commandsTxEntry 90 }

        
        cmdExcRfOutput OBJECT-TYPE
            SYNTAX SwitchOnOff
            MAX-ACCESS read-write
            STATUS current
            DESCRIPTION
                "Turns on/switches off the output signal.
                This switch takes the same effect as the switch on the frontpanel of the exciter."
            ::= { commandsTxEntry 91 }

        
        cmdExcRfOutputRegulation OBJECT-TYPE
            SYNTAX SwitchOnOff
            MAX-ACCESS read-write
            STATUS current
            DESCRIPTION
                "Turns on/switches off the automatic output level regulation."
            ::= { commandsTxEntry 92 }

        
        cmdExcRfOutputManualRfLevel OBJECT-TYPE
            SYNTAX FloatingPoint
            UNITS "Percent"
            MAX-ACCESS read-write
            STATUS current
            DESCRIPTION
                "Adjusts the RF level (0.0 ... 100.0).
                The value relates to an attenuation of 0 dB."
            ::= { commandsTxEntry 93 }

        
        cmdExcRfOutputAttenuation OBJECT-TYPE
            SYNTAX Integer32 (0..9)
            UNITS "dB"
            MAX-ACCESS read-write
            STATUS current
            DESCRIPTION
                "Activates internal attenuators to reduce the output level of the exciter.
                Adjustable in steps of 3 dB only."
            ::= { commandsTxEntry 94 }

        
        cmdExcRfOutputRfSlope OBJECT-TYPE
            SYNTAX FloatingPoint
            UNITS "Percent"
            MAX-ACCESS read-write
            STATUS current
            DESCRIPTION
                "Adjusts a slope in the RF signal (-50.0 ... 50.0)."
            ::= { commandsTxEntry 95 }

        
        cmdExcRfOutputModulationSlope OBJECT-TYPE
            SYNTAX FloatingPoint
            UNITS "Percent"
            MAX-ACCESS read-write
            STATUS current
            DESCRIPTION
                "Modulation slope (-50.0 ... 50.0)."
            ::= { commandsTxEntry 96 }

        
        cmdExcRfOutputCarrier1 OBJECT-TYPE
            SYNTAX FloatingPoint
            UNITS "dB"
            MAX-ACCESS read-write
            STATUS current
            DESCRIPTION
                "Vision/Sound Carrier 1"
            ::= { commandsTxEntry 97 }

        
        cmdExcRfOutputCarrier2 OBJECT-TYPE
            SYNTAX FloatingPoint
            UNITS "dB"
            MAX-ACCESS read-write
            STATUS current
            DESCRIPTION
                "Vision/Sound Carrier 2"
            ::= { commandsTxEntry 98 }

        
        cmdExcRfOutputResidualCarrier OBJECT-TYPE
            SYNTAX FloatingPoint
            UNITS "Percent"
            MAX-ACCESS read-write
            STATUS current
            DESCRIPTION
                "Residual"
            ::= { commandsTxEntry 99 }

        
        cmdExcRfMonitorCommon OBJECT-TYPE
            SYNTAX FloatingPoint
            UNITS "dB"
            MAX-ACCESS read-write
            STATUS current
            DESCRIPTION
                "Correction entry for fine adjustment of the entire coupling attenuation"
            ::= { commandsTxEntry 100 }

        
        cmdExcRfMonitorSound1 OBJECT-TYPE
            SYNTAX FloatingPoint
            UNITS "dB"
            MAX-ACCESS read-write
            STATUS current
            DESCRIPTION
                "Correction entry for fine adjustment of the coupling attenuation
                for sound carrier 1"
            ::= { commandsTxEntry 101 }

        
        cmdExcRfMonitorSound2 OBJECT-TYPE
            SYNTAX FloatingPoint
            UNITS "dB"
            MAX-ACCESS read-write
            STATUS current
            DESCRIPTION
                "Correction entry for fine adjustment of the coupling attenuation
                for sound carrier 2"
            ::= { commandsTxEntry 102 }

        
        cmdExcLevelVsVisionAntennaSound1 OBJECT-TYPE
            SYNTAX FloatingPoint
            UNITS "dB"
            MAX-ACCESS read-write
            STATUS current
            DESCRIPTION
                "Level versus Vision Antenna Sound 1"
            ::= { commandsTxEntry 103 }

        
        cmdExcLevelVsVisionAntennaSound2 OBJECT-TYPE
            SYNTAX FloatingPoint
            UNITS "dB"
            MAX-ACCESS read-write
            STATUS current
            DESCRIPTION
                "Level versus Vision Antenna Sound 2"
            ::= { commandsTxEntry 104 }

        
        cmdExcRfIqAdjustStart OBJECT-TYPE
            SYNTAX INTEGER
                {
                stop(1),
                start(2)
                }
            MAX-ACCESS read-write
            STATUS current
            DESCRIPTION
                "Starts the automatic IQ adjustment.
                It works for the current used local 1 frequency and lasts up to 5 minutes.
                In this time the output will be muted.
                During the adjustment no transmitter parameter shall be changed.
                Break will stop the automatic immediately.
                The IQ modulator looses its adjustment!
                Read values mean idle(1) and started(2)."
            ::= { commandsTxEntry 105 }

        
        cmdExcRfIqAdjustTestsignal OBJECT-TYPE
            SYNTAX SwitchOnOff
            MAX-ACCESS read-write
            STATUS current
            DESCRIPTION
                "Generates a test signal to adjust the IQ modulation.
                It is necessary to disconnect the RF-cable from the output stages."
            ::= { commandsTxEntry 106 }

        
        cmdExcRfIqAdjustBiasCoarseI OBJECT-TYPE
            SYNTAX Integer32 (-1023..1023)
            MAX-ACCESS read-write
            STATUS current
            DESCRIPTION
                "Adjusts the offset for I in huge steps."
            ::= { commandsTxEntry 107 }

        
        cmdExcRfIqAdjustBiasCoarseQ OBJECT-TYPE
            SYNTAX Integer32 (-1023..1023)
            MAX-ACCESS read-write
            STATUS current
            DESCRIPTION
                "Adjusts the offset for Q in huge steps."
            ::= { commandsTxEntry 108 }

        
        cmdExcRfIqAdjustBiasFineI OBJECT-TYPE
            SYNTAX Integer32 (-32767..32767)
            MAX-ACCESS read-write
            STATUS current
            DESCRIPTION
                "Adjusts the offset for I in small steps."
            ::= { commandsTxEntry 109 }

        
        cmdExcRfIqAdjustBiasFineQ OBJECT-TYPE
            SYNTAX Integer32 (-32767..32767)
            MAX-ACCESS read-write
            STATUS current
            DESCRIPTION
                "Adjusts the offset for Q in small steps."
            ::= { commandsTxEntry 110 }

        
        cmdExcRfIqAdjustGainI OBJECT-TYPE
            SYNTAX Integer32 (0..255)
            MAX-ACCESS read-write
            STATUS current
            DESCRIPTION
                "Adjusts the gain for I in small steps."
            ::= { commandsTxEntry 111 }

        
        cmdExcRfIqAdjustGainQ OBJECT-TYPE
            SYNTAX Integer32 (0..255)
            MAX-ACCESS read-write
            STATUS current
            DESCRIPTION
                "Adjusts the gain for Q in small steps."
            ::= { commandsTxEntry 112 }

        
        cmdExcRfIqAdjustPhase OBJECT-TYPE
            SYNTAX FloatingPoint
            MAX-ACCESS read-write
            STATUS current
            DESCRIPTION
                "Adjusts the phase between I and Q (-14.000 ... 14.000)."
            ::= { commandsTxEntry 113 }

        
        cmdExcTypeLossOfInput OBJECT-TYPE
            SYNTAX INTEGER
                {
                warning(1),
                fault(2)
                }
            MAX-ACCESS read-write
            STATUS current
            DESCRIPTION
                "If the input signal is lost, either a warning or a fault can be generated.
                If you select fault here and the input signal is lost, 
                the exciter is mute and a switchover to the reserve exciter (if existing) will be executed .
                "
            ::= { commandsTxEntry 120 }

        
        cmdExcTransmitterType OBJECT-TYPE
            SYNTAX INTEGER
                {
                atv(1),
                dvb(2),
                atsc(3)
                }
            MAX-ACCESS read-write
            STATUS current
            DESCRIPTION
                "the TV standard of the transmitter
                The transmitter is rebooted automatically when the TV standard is
                changed. Signal processing is also switched over."
            ::= { commandsTxEntry 150 }

        
        cmdExcTimeScheduler OBJECT-TYPE
            SYNTAX SwitchOnOff
            MAX-ACCESS read-write
            STATUS current
            DESCRIPTION
                "If on, the time scheduler controls the tx type. When switching on the scheduler 
                it may instantly set the correct TV standard and reboot the device."
            ::= { commandsTxEntry 151 }

        
        cmdExcOutputPower OBJECT-TYPE
            SYNTAX FloatingPoint
            UNITS "W"
            MAX-ACCESS read-write
            STATUS current
            DESCRIPTION
                "amplifier output power
                0 ... 400 W"
            ::= { commandsTxEntry 199 }

        
        cmdOstRefVoltageVision OBJECT-TYPE
            SYNTAX FloatingPoint
            UNITS "Percent"
            MAX-ACCESS read-write
            STATUS current
            DESCRIPTION
                "This adjusts the output power of the amplifier.
                This value is settable with maximal 1 position after point (example 11.2)."
            ::= { commandsTxEntry 200 }

        
        cmdOstMaxOutletTempThreshold OBJECT-TYPE
            SYNTAX Integer32 (45..65)
            UNITS "Degree Celsius"
            MAX-ACCESS read-write
            STATUS current
            DESCRIPTION
                "This sets the threshold for the outlet temperature."
            ::= { commandsTxEntry 201 }

        
        cmdExcFailDelayMode OBJECT-TYPE
            SYNTAX FailDelayMode
            MAX-ACCESS read-write
            STATUS current
            DESCRIPTION
                "Condition when the fail delay time is used."
            ::= { commandsTxEntry 202 }

        
        summaryInfo OBJECT IDENTIFIER ::= { rsXx8000AtvTxObjs 2 }

        
        summaryFaultTx OBJECT-TYPE
            SYNTAX TruthValue
            MAX-ACCESS read-only
            STATUS current
            DESCRIPTION
                "This indicates a summary fault of the transmitter.
                true(1)  --> summary fault
                false(2) --> no summary fault
                
                There is a fault of at least one module (e.g. Exciter) which causes this summary fault.
                
                An equivalent would be the LED Fault at the transmitters frontpanel."
            ::= { summaryInfo 1 }

        
        summaryWarningTx OBJECT-TYPE
            SYNTAX TruthValue
            MAX-ACCESS read-only
            STATUS current
            DESCRIPTION
                "This indicates a summary warning of the transmitter.
                true(1)  --> summary warning
                false(2) --> no summary warning
                
                There is a fault of at least one module (e.g. Exciter) which causes this summary warning.
                
                An equivalent would be the LED Warning at the transmitters frontpanel."
            ::= { summaryInfo 2 }

        
        localModeTx OBJECT-TYPE
            SYNTAX TruthValue
            MAX-ACCESS read-only
            STATUS current
            DESCRIPTION
                "This indicates the local/remote-mode of the transmitter.
                true(1)  --> local
                false(2) --> remote
                
                The transmitter is eigther in local-mode or in remote-mode. 
                For security reasons it is not possible to set this value!
                
                An equivalent would the LED Local at the transmitters frontpanel."
            ::= { summaryInfo 3 }

        
        rfOnTx OBJECT-TYPE
            SYNTAX TruthValue
            MAX-ACCESS read-only
            STATUS current
            DESCRIPTION
                "The RF is present for the corresponding transmitter."
            ::= { summaryInfo 4 }

        
        forwardPower OBJECT-TYPE
            SYNTAX FloatingPoint
            UNITS "Watt"
            MAX-ACCESS read-only
            STATUS current
            DESCRIPTION
                "The measured forwarded power [W] of the transmitter. 
                For Active Reserve systems it is the sum of both outputstages."
            ::= { summaryInfo 5 }

        
        reflectedPower OBJECT-TYPE
            SYNTAX FloatingPoint
            UNITS "Watt"
            MAX-ACCESS read-only
            STATUS current
            DESCRIPTION
                "The measured reflected power [W] of the transmitter. 
                For Active Reserve systems it is the sum of both outputstages.
                
                Not available for lowpower systems."
            ::= { summaryInfo 6 }

        
        summaryFaultExcA OBJECT-TYPE
            SYNTAX TruthValue
            MAX-ACCESS read-only
            STATUS current
            DESCRIPTION
                "This indicates a summary fault of exciterA."
            ::= { summaryInfo 7 }

        
        summaryFaultOstA OBJECT-TYPE
            SYNTAX TruthValue
            MAX-ACCESS read-only
            STATUS current
            DESCRIPTION
                "This indicates a summary fault of outputstageA."
            ::= { summaryInfo 8 }

        
        summaryFaultExcB OBJECT-TYPE
            SYNTAX TruthValue
            MAX-ACCESS read-only
            STATUS current
            DESCRIPTION
                "This indicates a summary fault of exciterA."
            ::= { summaryInfo 9 }

        
        summaryFaultOstB OBJECT-TYPE
            SYNTAX TruthValue
            MAX-ACCESS read-only
            STATUS current
            DESCRIPTION
                "This indicates a summary fault of outputstageB."
            ::= { summaryInfo 10 }

        
        exciterAutomaticReady OBJECT-TYPE
            SYNTAX TruthValue
            MAX-ACCESS read-only
            STATUS current
            DESCRIPTION
                "The Exciter Automatic is Ready. 
                In case of any fault on one exciter, there will be a switchover to the other exciter."
            ::= { summaryInfo 11 }

        
        exciterAutomaticChanged OBJECT-TYPE
            SYNTAX TruthValue
            MAX-ACCESS read-only
            STATUS current
            DESCRIPTION
                "The Exciter Automatic has changed. 
                There was a fault on one exciter which lead to this changeover."
            ::= { summaryInfo 12 }

        
        exciterAutomaticFault OBJECT-TYPE
            SYNTAX TruthValue
            MAX-ACCESS read-only
            STATUS current
            DESCRIPTION
                "The Exciter Automatic is faulty. 
                In case of any fault on one exciter, there will be no switchover to the other exciter,
                because of this fault."
            ::= { summaryInfo 13 }

        
        outputstageAutomaticReady OBJECT-TYPE
            SYNTAX TruthValue
            MAX-ACCESS read-only
            STATUS current
            DESCRIPTION
                "The Outputstage Automatic is Ready. 
                In case of any fault on one outputstage, there will be a switchover to the other outputstage.
                
                This paramter is only available for systems with an automatic output switch."
            ::= { summaryInfo 14 }

        
        outputstageAutomaticChanged OBJECT-TYPE
            SYNTAX TruthValue
            MAX-ACCESS read-only
            STATUS current
            DESCRIPTION
                "The Outputstage Automatic has changed. 
                There was a fault on one outputstage which lead to this changeover.
                
                This paramter is only available for systems with an automatic output switch."
            ::= { summaryInfo 15 }

        
        outputstageAutomaticFault OBJECT-TYPE
            SYNTAX TruthValue
            MAX-ACCESS read-only
            STATUS current
            DESCRIPTION
                "The Outputstage Automatic is faulty. 
                In case of any fault on one outputstage, there will be no switchover to the other outputstage,
                because of this fault.
                
                This paramter is only available for systems with an automatic output switch."
            ::= { summaryInfo 16 }

        
        noConnectionExcA OBJECT-TYPE
            SYNTAX TruthValue
            MAX-ACCESS read-only
            STATUS current
            DESCRIPTION
                "No Connection between NetCCU and ExciterA."
            ::= { summaryInfo 17 }

        
        noConnectionOstA OBJECT-TYPE
            SYNTAX TruthValue
            MAX-ACCESS read-only
            STATUS current
            DESCRIPTION
                "No Connection between NetCCU and OutputstageA."
            ::= { summaryInfo 18 }

        
        noConnectionExcB OBJECT-TYPE
            SYNTAX TruthValue
            MAX-ACCESS read-only
            STATUS current
            DESCRIPTION
                "No Connection between NetCCU and ExciterB."
            ::= { summaryInfo 19 }

        
        noConnectionOstB OBJECT-TYPE
            SYNTAX TruthValue
            MAX-ACCESS read-only
            STATUS current
            DESCRIPTION
                "No Connection between NetCCU and OutputstageB."
            ::= { summaryInfo 20 }

        
        activeExcA OBJECT-TYPE
            SYNTAX TruthValue
            MAX-ACCESS read-only
            STATUS current
            DESCRIPTION
                "ExciterA is currently active."
            ::= { summaryInfo 21 }

        
        activeOstA OBJECT-TYPE
            SYNTAX TruthValue
            MAX-ACCESS read-only
            STATUS current
            DESCRIPTION
                "OutputstageA is currently active."
            ::= { summaryInfo 22 }

        
        activeExcB OBJECT-TYPE
            SYNTAX TruthValue
            MAX-ACCESS read-only
            STATUS current
            DESCRIPTION
                "ExciterB is currently active."
            ::= { summaryInfo 23 }

        
        activeOstB OBJECT-TYPE
            SYNTAX TruthValue
            MAX-ACCESS read-only
            STATUS current
            DESCRIPTION
                "OutputstageB is currently active."
            ::= { summaryInfo 24 }

        
        forwardPowerOstA OBJECT-TYPE
            SYNTAX FloatingPoint
            UNITS "Watt"
            MAX-ACCESS read-only
            STATUS current
            DESCRIPTION
                "The measured forwarded power [W] of the OutputstageA."
            ::= { summaryInfo 25 }

        
        reflectedPowerOstA OBJECT-TYPE
            SYNTAX FloatingPoint
            UNITS "Watt"
            MAX-ACCESS read-only
            STATUS current
            DESCRIPTION
                "The measured reflected power [W] of the OutputstageA.
                
                Not available for lowpower systems."
            ::= { summaryInfo 26 }

        
        forwardPowerOstB OBJECT-TYPE
            SYNTAX FloatingPoint
            UNITS "Watt"
            MAX-ACCESS read-only
            STATUS current
            DESCRIPTION
                "The measured forwarded power [W] of the OutputstageB."
            ::= { summaryInfo 27 }

        
        reflectedPowerOstB OBJECT-TYPE
            SYNTAX FloatingPoint
            UNITS "Watt"
            MAX-ACCESS read-only
            STATUS current
            DESCRIPTION
                "The measured reflected power [W] of the OutputstageB.
                
                Not available for lowpower systems."
            ::= { summaryInfo 28 }

        
        powerSupply OBJECT-TYPE
            SYNTAX FloatingPoint
            UNITS "volt"
            MAX-ACCESS read-only
            STATUS current
            DESCRIPTION
                "Monitoring value of the output voltages of the power supply."
            ::= { summaryInfo 29 }

        
        additionalPowerSupply OBJECT-TYPE
            SYNTAX TruthValue
            MAX-ACCESS read-only
            STATUS current
            DESCRIPTION
                "Shows whether the NetCCU has an additional (external) power supply."
            ::= { summaryInfo 30 }

        
        internalPowerSupply OBJECT-TYPE
            SYNTAX FloatingPoint
            UNITS "volt"
            MAX-ACCESS read-only
            STATUS current
            DESCRIPTION
                "Monitoring value of the output voltages of the internal power supply."
            ::= { summaryInfo 31 }

        
        externalPowerSupply OBJECT-TYPE
            SYNTAX FloatingPoint
            UNITS "volt"
            MAX-ACCESS read-only
            STATUS current
            DESCRIPTION
                "Monitoring value of the output voltages of the external power supply."
            ::= { summaryInfo 32 }

        
        detailedInfo OBJECT IDENTIFIER ::= { rsXx8000AtvTxObjs 3 }

        
        ostTable OBJECT-TYPE
            SYNTAX SEQUENCE OF OstEntry
            MAX-ACCESS not-accessible
            STATUS current
            DESCRIPTION
                "The table of racks."
            ::= { detailedInfo 3 }

        
        ostEntry OBJECT-TYPE
            SYNTAX OstEntry
            MAX-ACCESS not-accessible
            STATUS current
            DESCRIPTION
                "A row (an entry) for one rack."
            INDEX { ostIdx, ostRackIdx, ostRackAmpIdx }
            ::= { ostTable 1 }

        
        OstEntry ::=
            SEQUENCE { 
                ostIdx
                    IndexAB,
                ostRackIdx
                    IndexRack,
                ostRackInletTemperature
                    FloatingPoint,
                ostRackOutletTemperature
                    FloatingPoint,
                ostRackAuxPowerSupply
                    FloatingPoint,
                ostRackAmpIdx
                    IndexAmplifier,
                ostRackAmpI1A
                    FloatingPoint,
                ostRackAmpI2A
                    FloatingPoint,
                ostRackAmpI3A
                    FloatingPoint,
                ostRackAmpI4A
                    FloatingPoint,
                ostRackAmpI1B
                    FloatingPoint,
                ostRackAmpI2B
                    FloatingPoint,
                ostRackAmpI3B
                    FloatingPoint,
                ostRackAmpI4B
                    FloatingPoint,
                ostRackAmpIDrv
                    FloatingPoint,
                ostRackAmpUDc
                    FloatingPoint,
                ostRackAmpIDc
                    FloatingPoint,
                ostRackAmpUDcControl
                    FloatingPoint,
                ostRackAmpUReg
                    FloatingPoint,
                ostRackAmpPowerA
                    FloatingPoint,
                ostRackAmpPowerB
                    FloatingPoint,
                ostRackAmpPowerOut
                    FloatingPoint,
                ostRackAmpPowerReflection
                    FloatingPoint,
                ostRackAmpPowerReference
                    FloatingPoint,
                ostRackAmpDeltaPhase
                    FloatingPoint,
                ostRackAmpCmdDeltaPhase
                    FloatingPoint
             }

        ostIdx OBJECT-TYPE
            SYNTAX IndexAB
            MAX-ACCESS not-accessible
            STATUS current
            DESCRIPTION
                "The dedicated outputstage (A/B)."
            ::= { ostEntry 1 }

        
        ostRackIdx OBJECT-TYPE
            SYNTAX IndexRack
            MAX-ACCESS not-accessible
            STATUS current
            DESCRIPTION
                "The rack number (1..10)."
            ::= { ostEntry 2 }

        
        ostRackInletTemperature OBJECT-TYPE
            SYNTAX FloatingPoint
            UNITS "Degree Celsius"
            MAX-ACCESS read-only
            STATUS current
            DESCRIPTION
                "The inlet temperature."
            ::= { ostEntry 3 }

        
        ostRackOutletTemperature OBJECT-TYPE
            SYNTAX FloatingPoint
            UNITS "Degree Celsius"
            MAX-ACCESS read-only
            STATUS current
            DESCRIPTION
                "The outlet temperature."
            ::= { ostEntry 4 }

        
        ostRackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { ostEntry 5 }

        
        ostRackAmpIdx OBJECT-TYPE
            SYNTAX IndexAmplifier
            MAX-ACCESS not-accessible
            STATUS current
            DESCRIPTION
                "Amplifier Index"
            ::= { ostEntry 400 }

        
        ostRackAmpI1A OBJECT-TYPE
            SYNTAX FloatingPoint
            UNITS "Ampere"
            MAX-ACCESS read-only
            STATUS current
            DESCRIPTION
                "The power amplifier module current (I_1A)."
            ::= { ostEntry 401 }

        
        ostRackAmpI2A OBJECT-TYPE
            SYNTAX FloatingPoint
            UNITS "Ampere"
            MAX-ACCESS read-only
            STATUS current
            DESCRIPTION
                "The power amplifier module current (I_2A)."
            ::= { ostEntry 402 }

        
        ostRackAmpI3A OBJECT-TYPE
            SYNTAX FloatingPoint
            UNITS "Ampere"
            MAX-ACCESS read-only
            STATUS current
            DESCRIPTION
                "The power amplifier module current (I_3A)."
            ::= { ostEntry 403 }

        
        ostRackAmpI4A OBJECT-TYPE
            SYNTAX FloatingPoint
            UNITS "Ampere"
            MAX-ACCESS read-only
            STATUS current
            DESCRIPTION
                "The power amplifier module current (I_4A)."
            ::= { ostEntry 404 }

        
        ostRackAmpI1B OBJECT-TYPE
            SYNTAX FloatingPoint
            UNITS "Ampere"
            MAX-ACCESS read-only
            STATUS current
            DESCRIPTION
                "The power amplifier module current (I_1B)."
            ::= { ostEntry 405 }

        
        ostRackAmpI2B OBJECT-TYPE
            SYNTAX FloatingPoint
            UNITS "Ampere"
            MAX-ACCESS read-only
            STATUS current
            DESCRIPTION
                "The power amplifier module current (I_2B)."
            ::= { ostEntry 406 }

        
        ostRackAmpI3B OBJECT-TYPE
            SYNTAX FloatingPoint
            UNITS "Ampere"
            MAX-ACCESS read-only
            STATUS current
            DESCRIPTION
                "The power amplifier module current (I_3B)."
            ::= { ostEntry 407 }

        
        ostRackAmpI4B OBJECT-TYPE
            SYNTAX FloatingPoint
            UNITS "Ampere"
            MAX-ACCESS read-only
            STATUS current
            DESCRIPTION
                "The power amplifier module current (I_4B)."
            ::= { ostEntry 408 }

        
        ostRackAmpIDrv OBJECT-TYPE
            SYNTAX FloatingPoint
            UNITS "Ampere"
            MAX-ACCESS read-only
            STATUS current
            DESCRIPTION
                "The driver module current (I_DRV)."
            ::= { ostEntry 409 }

        
        ostRackAmpUDc OBJECT-TYPE
            SYNTAX FloatingPoint
            UNITS "Volt"
            MAX-ACCESS read-only
            STATUS current
            DESCRIPTION
                "The power amplifier supply voltage."
            ::= { ostEntry 410 }

        
        ostRackAmpIDc OBJECT-TYPE
            SYNTAX FloatingPoint
            UNITS "Ampere"
            MAX-ACCESS read-only
            STATUS current
            DESCRIPTION
                "The power amplifier supply current."
            ::= { ostEntry 411 }

        
        ostRackAmpUDcControl OBJECT-TYPE
            SYNTAX FloatingPoint
            UNITS "Volt"
            MAX-ACCESS read-only
            STATUS current
            DESCRIPTION
                "The power supply control voltage."
            ::= { ostEntry 412 }

        
        ostRackAmpUReg OBJECT-TYPE
            SYNTAX FloatingPoint
            UNITS "Volt"
            MAX-ACCESS read-only
            STATUS current
            DESCRIPTION
                "The power amplifier AGC voltage."
            ::= { ostEntry 413 }

        
        ostRackAmpPowerA OBJECT-TYPE
            SYNTAX FloatingPoint
            UNITS "Volt"
            MAX-ACCESS read-only
            STATUS current
            DESCRIPTION
                "The voltage power detector A."
            ::= { ostEntry 414 }

        
        ostRackAmpPowerB OBJECT-TYPE
            SYNTAX FloatingPoint
            UNITS "Volt"
            MAX-ACCESS read-only
            STATUS current
            DESCRIPTION
                "The voltage power detector B."
            ::= { ostEntry 415 }

        
        ostRackAmpPowerOut OBJECT-TYPE
            SYNTAX FloatingPoint
            UNITS "Volt"
            MAX-ACCESS read-only
            STATUS current
            DESCRIPTION
                "The voltage forward power detector."
            ::= { ostEntry 416 }

        
        ostRackAmpPowerReflection OBJECT-TYPE
            SYNTAX FloatingPoint
            UNITS "Volt"
            MAX-ACCESS read-only
            STATUS current
            DESCRIPTION
                "The voltage reflected power detector."
            ::= { ostEntry 417 }

        
        ostRackAmpPowerReference OBJECT-TYPE
            SYNTAX FloatingPoint
            UNITS "Volt"
            MAX-ACCESS read-only
            STATUS current
            DESCRIPTION
                "The reference voltage for output power."
            ::= { ostEntry 418 }

        
        ostRackAmpDeltaPhase OBJECT-TYPE
            SYNTAX FloatingPoint
            UNITS "Percent"
            MAX-ACCESS read-only
            STATUS current
            DESCRIPTION
                "The measured phase delta for output power."
            ::= { ostEntry 419 }

        
        ostRackAmpCmdDeltaPhase OBJECT-TYPE
            SYNTAX FloatingPoint
            UNITS "Percent"
            MAX-ACCESS read-write
            STATUS current
            DESCRIPTION
                "The phase delta setting for output power.
                The range is -50.0% to 50.0%."
            ::= { ostEntry 420 }

        
        exciterStatusTable OBJECT-TYPE
            SYNTAX SEQUENCE OF ExciterStatusEntry
            MAX-ACCESS not-accessible
            STATUS current
            DESCRIPTION
                "Exciter status values."
            ::= { detailedInfo 20 }

        
        exciterStatusEntry OBJECT-TYPE
            SYNTAX ExciterStatusEntry
            MAX-ACCESS not-accessible
            STATUS current
            DESCRIPTION
                "A row (an entry) for one exciter."
            INDEX { excStatusExcIdx }
            ::= { exciterStatusTable 1 }

        
        ExciterStatusEntry ::=
            SEQUENCE { 
                excStatusExcIdx
                    IndexAB,
                excStatusRfOutputAgcRegulation
                    FloatingPoint,
                excStatusRfIqAdjustAuto
                    INTEGER,
                excStatusRfIqAdjustLO1Frequency
                    Integer32,
                excStatusNominalPower
                    Integer32,
                excStatusRfMonitorSyncLvlAntenna
                    FloatingPoint,
                excStatusVSWR
                    FloatingPoint,
                excStatusVideoInputClipping
                    INTEGER,
                excStatusWhiteCtrlMemoryGain
                    FloatingPoint,
                excStatusWhiteGainSource
                    INTEGER,
                excStatusWhiteInputAmplitude
                    Integer32,
                excStatusWhiteOutputAmplitude
                    Integer32,
                excStatusWhiteInputLevel
                    INTEGER,
                excStatusWhiteLimiterActive
                    TruthValue,
                excStatusSyncMonitoring
                    INTEGER,
                excStatusSyncInputAmplitude
                    Integer32,
                excStatusSyncOutputAmplitude
                    Integer32,
                excStatusAudioInputClippingAF1
                    SwitchOnOff,
                excStatusAudioInputClippingAF2
                    SwitchOnOff,
                excStatusAudioInputClippingAF3
                    SwitchOnOff,
                excStatusAudioInputClippingBTSC
                    SwitchOnOff,
                excStatusAudioInputLevelAF1
                    FloatingPoint,
                excStatusAudioInputLevelAF2
                    FloatingPoint,
                excStatusAudioInputLevelAF3
                    FloatingPoint,
                excStatusAudioInputLevelBTSC
                    FloatingPoint,
                excStatusNicamInputClippingAF1
                    SwitchOnOff,
                excStatusNicamInputClippingAF2
                    SwitchOnOff,
                excStatusNicam728Datastream
                    SwitchOnOff,
                excStatusNicamSubcarrier
                    INTEGER,
                excStatusNicamInputLevelAF1
                    FloatingPoint,
                excStatusNicamInputLevelAF2
                    FloatingPoint,
                excStatusFmAudioDataLineInfo
                    INTEGER,
                excStatusFmAudioMode
                    INTEGER,
                excStatusFmCarrier1
                    INTEGER,
                excStatusFmCarrier2
                    INTEGER,
                excStatusFmAudioPilotDeviation
                    Integer32,
                excStatusFmAF1Deviation
                    Integer32,
                excStatusFmAF2Deviation
                    Integer32,
                excStatusFmLimiterC1
                    SwitchOnOff,
                excStatusFmLimiterC2
                    SwitchOnOff,
                excStatusFailDelay
                    FailDelayStatus
             }

        excStatusExcIdx OBJECT-TYPE
            SYNTAX IndexAB
            MAX-ACCESS not-accessible
            STATUS current
            DESCRIPTION
                "The dedicated exciter (A/B)."
            ::= { exciterStatusEntry 3 }

        
        excStatusRfOutputAgcRegulation OBJECT-TYPE
            SYNTAX FloatingPoint
            UNITS "Percent"
            MAX-ACCESS read-only
            STATUS current
            DESCRIPTION
                "Shows the operating point of the RF regulator.
                The shown value should be around 50 per cent."
            ::= { exciterStatusEntry 4 }

        
        excStatusRfIqAdjustAuto OBJECT-TYPE
            SYNTAX INTEGER
                {
                notAdjusted(1),
                inProgress(2),
                adjusted(3)
                }
            MAX-ACCESS read-only
            STATUS current
            DESCRIPTION
                "Automatic I/Q-Adjust."
            ::= { exciterStatusEntry 5 }

        
        excStatusRfIqAdjustLO1Frequency OBJECT-TYPE
            SYNTAX Integer32 (1800..2300)
            UNITS "MHz"
            MAX-ACCESS read-only
            STATUS current
            DESCRIPTION
                "Modulator LO1."
            ::= { exciterStatusEntry 6 }

        
        excStatusNominalPower OBJECT-TYPE
            SYNTAX Integer32
            UNITS "W"
            MAX-ACCESS read-write
            STATUS current
            DESCRIPTION
                "Description."
            ::= { exciterStatusEntry 7 }

        
        excStatusRfMonitorSyncLvlAntenna OBJECT-TYPE
            SYNTAX FloatingPoint
            UNITS "Percent"
            MAX-ACCESS read-only
            STATUS current
            DESCRIPTION
                "Display of the current level of the sync pulse as a percentage
                with reference to the black shoulders."
            ::= { exciterStatusEntry 8 }

        
        excStatusVSWR OBJECT-TYPE
            SYNTAX FloatingPoint
            MAX-ACCESS read-only
            STATUS current
            DESCRIPTION
                "Voltage Standing Wave Ratio"
            ::= { exciterStatusEntry 9 }

        
        excStatusVideoInputClipping OBJECT-TYPE
            SYNTAX INTEGER
                {
                noClipping(1),
                noHeadroom(2),
                clipping(3)
                }
            MAX-ACCESS read-only
            STATUS current
            DESCRIPTION
                "Indicates Video input clipping"
            ::= { exciterStatusEntry 12 }

        
        excStatusWhiteCtrlMemoryGain OBJECT-TYPE
            SYNTAX FloatingPoint
            UNITS "Percent"
            MAX-ACCESS read-only
            STATUS current
            DESCRIPTION
                "Display of the last value saved by the white control
                which can be used for fixed video gain."
            ::= { exciterStatusEntry 13 }

        
        excStatusWhiteGainSource OBJECT-TYPE
            SYNTAX INTEGER
                {
                manual(1),
                memory(2),
                controlled(3)
                }
            MAX-ACCESS read-only
            STATUS current
            DESCRIPTION
                "Display of the active source for the video gain"
            ::= { exciterStatusEntry 14 }

        
        excStatusWhiteInputAmplitude OBJECT-TYPE
            SYNTAX Integer32 (0..1300)
            UNITS "mV"
            MAX-ACCESS read-only
            STATUS current
            DESCRIPTION
                "shows the white level of input signal"
            ::= { exciterStatusEntry 15 }

        
        excStatusWhiteOutputAmplitude OBJECT-TYPE
            SYNTAX Integer32 (0..1100)
            UNITS "mV"
            MAX-ACCESS read-only
            STATUS current
            DESCRIPTION
                "shows the white level of output signal"
            ::= { exciterStatusEntry 16 }

        
        excStatusWhiteInputLevel OBJECT-TYPE
            SYNTAX INTEGER
                {
                none(1),
                ok(2),
                veryLow(3),
                low(4),
                high(5),
                veryHigh(6)
                }
            MAX-ACCESS read-only
            STATUS current
            DESCRIPTION
                "Status display for the white pulse monitoring"
            ::= { exciterStatusEntry 17 }

        
        excStatusWhiteLimiterActive OBJECT-TYPE
            SYNTAX TruthValue
            MAX-ACCESS read-only
            STATUS current
            DESCRIPTION
                "display for indicating if the white limiter responds"
            ::= { exciterStatusEntry 18 }

        
        excStatusSyncMonitoring OBJECT-TYPE
            SYNTAX INTEGER
                {
                ok(1),
                noVSync(2),
                noHVSync(3),
                lowLevel(4)
                }
            MAX-ACCESS read-only
            STATUS current
            DESCRIPTION
                "The state of the monitored sync pulse"
            ::= { exciterStatusEntry 19 }

        
        excStatusSyncInputAmplitude OBJECT-TYPE
            SYNTAX Integer32
            UNITS "mV"
            MAX-ACCESS read-only
            STATUS current
            DESCRIPTION
                "Shows the synchronimpulse level of the input signal."
            ::= { exciterStatusEntry 20 }

        
        excStatusSyncOutputAmplitude OBJECT-TYPE
            SYNTAX Integer32
            UNITS "mV"
            MAX-ACCESS read-only
            STATUS current
            DESCRIPTION
                "Shows the synchronimpulse level of the output signal."
            ::= { exciterStatusEntry 21 }

        
        excStatusAudioInputClippingAF1 OBJECT-TYPE
            SYNTAX SwitchOnOff
            MAX-ACCESS read-only
            STATUS current
            DESCRIPTION
                "Input Clipping AF1"
            ::= { exciterStatusEntry 22 }

        
        excStatusAudioInputClippingAF2 OBJECT-TYPE
            SYNTAX SwitchOnOff
            MAX-ACCESS read-only
            STATUS current
            DESCRIPTION
                "Input Clipping AF2
                "
            ::= { exciterStatusEntry 23 }

        
        excStatusAudioInputClippingAF3 OBJECT-TYPE
            SYNTAX SwitchOnOff
            MAX-ACCESS read-only
            STATUS current
            DESCRIPTION
                "Input Clipping AF3
                "
            ::= { exciterStatusEntry 24 }

        
        excStatusAudioInputClippingBTSC OBJECT-TYPE
            SYNTAX SwitchOnOff
            MAX-ACCESS read-only
            STATUS current
            DESCRIPTION
                "Input Clipping BTSC
                
                "
            ::= { exciterStatusEntry 25 }

        
        excStatusAudioInputLevelAF1 OBJECT-TYPE
            SYNTAX FloatingPoint
            UNITS "Percent"
            MAX-ACCESS read-only
            STATUS current
            DESCRIPTION
                "Current Input Level AF1"
            ::= { exciterStatusEntry 26 }

        
        excStatusAudioInputLevelAF2 OBJECT-TYPE
            SYNTAX FloatingPoint
            UNITS "Percent"
            MAX-ACCESS read-only
            STATUS current
            DESCRIPTION
                "Current Input Level AF2"
            ::= { exciterStatusEntry 27 }

        
        excStatusAudioInputLevelAF3 OBJECT-TYPE
            SYNTAX FloatingPoint
            UNITS "Percent"
            MAX-ACCESS read-only
            STATUS current
            DESCRIPTION
                "Current Input Level AF3"
            ::= { exciterStatusEntry 28 }

        
        excStatusAudioInputLevelBTSC OBJECT-TYPE
            SYNTAX FloatingPoint
            UNITS "Percent"
            MAX-ACCESS read-only
            STATUS current
            DESCRIPTION
                "Current input level in percent"
            ::= { exciterStatusEntry 29 }

        
        excStatusNicamInputClippingAF1 OBJECT-TYPE
            SYNTAX SwitchOnOff
            MAX-ACCESS read-only
            STATUS current
            DESCRIPTION
                "Input Clipping AF1"
            ::= { exciterStatusEntry 30 }

        
        excStatusNicamInputClippingAF2 OBJECT-TYPE
            SYNTAX SwitchOnOff
            MAX-ACCESS read-only
            STATUS current
            DESCRIPTION
                "Input Clipping AF2"
            ::= { exciterStatusEntry 31 }

        
        excStatusNicam728Datastream OBJECT-TYPE
            SYNTAX SwitchOnOff
            MAX-ACCESS read-only
            STATUS current
            DESCRIPTION
                "displays if a NICAM 728 datastream is available or not"
            ::= { exciterStatusEntry 32 }

        
        excStatusNicamSubcarrier OBJECT-TYPE
            SYNTAX INTEGER
                {
                tooSmall(1),
                ok(2),
                tooBig(3)
                }
            MAX-ACCESS read-only
            STATUS current
            DESCRIPTION
                "displays the level of an external NICAM subcarrier"
            ::= { exciterStatusEntry 33 }

        
        excStatusNicamInputLevelAF1 OBJECT-TYPE
            SYNTAX FloatingPoint
            UNITS "Percent"
            MAX-ACCESS read-only
            STATUS current
            DESCRIPTION
                "Current Input Level NICAM AF1"
            ::= { exciterStatusEntry 34 }

        
        excStatusNicamInputLevelAF2 OBJECT-TYPE
            SYNTAX FloatingPoint
            UNITS "Percent"
            MAX-ACCESS read-only
            STATUS current
            DESCRIPTION
                "Current Input Level NICAM AF2"
            ::= { exciterStatusEntry 35 }

        
        excStatusFmAudioDataLineInfo OBJECT-TYPE
            SYNTAX INTEGER
                {
                none(1),
                mono(2),
                stereo(3),
                dual(4)
                }
            MAX-ACCESS read-only
            STATUS current
            DESCRIPTION
                "Displays the information transmitted via dataline."
            ::= { exciterStatusEntry 36 }

        
        excStatusFmAudioMode OBJECT-TYPE
            SYNTAX INTEGER
                {
                mono(1),
                stereo(2),
                dual(3)
                }
            MAX-ACCESS read-only
            STATUS current
            DESCRIPTION
                "Displays the currently active sound mode.
                The value depends on the content of dataline information (if available)
                or on the manual selected sound mode."
            ::= { exciterStatusEntry 37 }

        
        excStatusFmCarrier1 OBJECT-TYPE
            SYNTAX INTEGER
                {
                off(1),
                modOff(2),
                af1Af2(3),
                af3(4),
                btsc(5),
                af1(6)
                }
            MAX-ACCESS read-only
            STATUS current
            DESCRIPTION
                "displays the carrier 1 state"
            ::= { exciterStatusEntry 38 }

        
        excStatusFmCarrier2 OBJECT-TYPE
            SYNTAX INTEGER
                {
                off(1),
                modOff(2),
                af1Af2(3),
                af1(6),
                af1Xaf2(7),
                af2(8),
                af1Pilot(9),
                af1Xaf2Pilot(10),
                af2Pilot(11),
                nicamAf10(12),
                nicamAf1Af2(13),
                nicamDigital(14),
                nicamPRBS(15),
                nicamExtCarrier(16)
                }
            MAX-ACCESS read-only
            STATUS current
            DESCRIPTION
                "displays the carrier 2 state"
            ::= { exciterStatusEntry 39 }

        
        excStatusFmAudioPilotDeviation OBJECT-TYPE
            SYNTAX Integer32 (0..25000)
            UNITS "Hz"
            MAX-ACCESS read-only
            STATUS current
            DESCRIPTION
                "Shows the current deviation of the pilot signal."
            ::= { exciterStatusEntry 40 }

        
        excStatusFmAF1Deviation OBJECT-TYPE
            SYNTAX Integer32 (0..250000)
            UNITS "Hz"
            MAX-ACCESS read-only
            STATUS current
            DESCRIPTION
                "Current deviation of audio carrier 1"
            ::= { exciterStatusEntry 41 }

        
        excStatusFmAF2Deviation OBJECT-TYPE
            SYNTAX Integer32 (0..250000)
            UNITS "Hz"
            MAX-ACCESS read-only
            STATUS current
            DESCRIPTION
                "Current deviation of audio carrier 2"
            ::= { exciterStatusEntry 42 }

        
        excStatusFmLimiterC1 OBJECT-TYPE
            SYNTAX SwitchOnOff
            MAX-ACCESS read-only
            STATUS current
            DESCRIPTION
                "Shows when the limiter reacts for carrier 1"
            ::= { exciterStatusEntry 43 }

        
        excStatusFmLimiterC2 OBJECT-TYPE
            SYNTAX SwitchOnOff
            MAX-ACCESS read-only
            STATUS current
            DESCRIPTION
                "Shows when the limiter reacts for carrier 2"
            ::= { exciterStatusEntry 44 }

        
        excStatusFailDelay OBJECT-TYPE
            SYNTAX FailDelayStatus
            MAX-ACCESS read-only
            STATUS current
            DESCRIPTION
                "Shows whether the fail delay time is qualified."
            ::= { exciterStatusEntry 45 }

        
        exciterPrecorrectionTable OBJECT-TYPE
            SYNTAX SEQUENCE OF ExciterPrecorrectionEntry
            MAX-ACCESS not-accessible
            STATUS current
            DESCRIPTION
                "Exciter status values."
            ::= { detailedInfo 21 }

        
        exciterPrecorrectionEntry OBJECT-TYPE
            SYNTAX ExciterPrecorrectionEntry
            MAX-ACCESS not-accessible
            STATUS current
            DESCRIPTION
                "A row (an entry) for one exciter."
            INDEX { excPrecExcIdx }
            ::= { exciterPrecorrectionTable 1 }

        
        ExciterPrecorrectionEntry ::=
            SEQUENCE { 
                excPrecExcIdx
                    IndexAB,
                excPrecLinCorrection
                    SwitchOnOff,
                excPrecLinAmplitude
                    SwitchOnOff,
                excPrecLinGroupDelay
                    SwitchOnOff,
                excPrecNonlinCorrection
                    SwitchOnOff,
                excPrecNonlinAmplitude
                    SwitchOnOff,
                excPrecNonlinPhase
                    SwitchOnOff,
                excPrecNonlinFrequencyCorrection
                    SwitchOnOff,
                excPrecNonlinCorrectionPoint1
                    SwitchOnOff,
                excPrecNonlinCorrectionPoint2
                    SwitchOnOff,
                excPrecUserState
                    EqualizerCalibrationState,
                excPrecFactoryState
                    EqualizerCalibrationState,
                excPrecRestoreCurrentSettings
                    INTEGER,
                excPrecRestoreAllSettings
                    INTEGER
             }

        excPrecExcIdx OBJECT-TYPE
            SYNTAX IndexAB
            MAX-ACCESS not-accessible
            STATUS current
            DESCRIPTION
                "The dedicated exciter (A/B)."
            ::= { exciterPrecorrectionEntry 3 }

        
        excPrecLinCorrection OBJECT-TYPE
            SYNTAX SwitchOnOff
            MAX-ACCESS read-write
            STATUS current
            DESCRIPTION
                "Switches on/turns off the linear precorrector."
            ::= { exciterPrecorrectionEntry 4 }

        
        excPrecLinAmplitude OBJECT-TYPE
            SYNTAX SwitchOnOff
            MAX-ACCESS read-write
            STATUS current
            DESCRIPTION
                "Switch amplitude linear correction on or off."
            ::= { exciterPrecorrectionEntry 5 }

        
        excPrecLinGroupDelay OBJECT-TYPE
            SYNTAX SwitchOnOff
            MAX-ACCESS read-write
            STATUS current
            DESCRIPTION
                "Switch group delay linear correction on or off."
            ::= { exciterPrecorrectionEntry 6 }

        
        excPrecNonlinCorrection OBJECT-TYPE
            SYNTAX SwitchOnOff
            MAX-ACCESS read-write
            STATUS current
            DESCRIPTION
                "Switches on/turns off the nonlinear precorrector."
            ::= { exciterPrecorrectionEntry 12 }

        
        excPrecNonlinAmplitude OBJECT-TYPE
            SYNTAX SwitchOnOff
            MAX-ACCESS read-write
            STATUS current
            DESCRIPTION
                "Switch amplitude non-linear correction on or off."
            ::= { exciterPrecorrectionEntry 13 }

        
        excPrecNonlinPhase OBJECT-TYPE
            SYNTAX SwitchOnOff
            MAX-ACCESS read-write
            STATUS current
            DESCRIPTION
                "Switch phase non-linear correction on or off."
            ::= { exciterPrecorrectionEntry 14 }

        
        excPrecNonlinFrequencyCorrection OBJECT-TYPE
            SYNTAX SwitchOnOff
            MAX-ACCESS read-write
            STATUS current
            DESCRIPTION
                "Switch frequency non-linear correction on or off."
            ::= { exciterPrecorrectionEntry 15 }

        
        excPrecNonlinCorrectionPoint1 OBJECT-TYPE
            SYNTAX SwitchOnOff
            MAX-ACCESS read-write
            STATUS current
            DESCRIPTION
                "Switch correction point 1 of frequency non-linear correction on or off."
            ::= { exciterPrecorrectionEntry 16 }

        
        excPrecNonlinCorrectionPoint2 OBJECT-TYPE
            SYNTAX SwitchOnOff
            MAX-ACCESS read-write
            STATUS current
            DESCRIPTION
                "Switch correction point 2 of frequency non-linear correction on or off."
            ::= { exciterPrecorrectionEntry 17 }

        
        excPrecUserState OBJECT-TYPE
            SYNTAX EqualizerCalibrationState
            MAX-ACCESS read-only
            STATUS current
            DESCRIPTION
                "status of the user precorrection settings"
            ::= { exciterPrecorrectionEntry 100 }

        
        excPrecFactoryState OBJECT-TYPE
            SYNTAX EqualizerCalibrationState
            MAX-ACCESS read-only
            STATUS current
            DESCRIPTION
                "status of the factory precorrection settings"
            ::= { exciterPrecorrectionEntry 101 }

        
        excPrecRestoreCurrentSettings OBJECT-TYPE
            SYNTAX INTEGER
                {
                stop(1),
                start(2)
                }
            MAX-ACCESS read-write
            STATUS current
            DESCRIPTION
                "restores current factory precorrection setting"
            ::= { exciterPrecorrectionEntry 102 }

        
        excPrecRestoreAllSettings OBJECT-TYPE
            SYNTAX INTEGER
                {
                stop(1),
                start(2)
                }
            MAX-ACCESS read-write
            STATUS current
            DESCRIPTION
                "restores all factory precorrection settings"
            ::= { exciterPrecorrectionEntry 103 }

        
        configurationTable OBJECT-TYPE
            SYNTAX SEQUENCE OF ConfigurationEntry
            MAX-ACCESS not-accessible
            STATUS current
            DESCRIPTION
                "Table for Type Configuration parameters."
            ::= { detailedInfo 30 }

        
        configurationEntry OBJECT-TYPE
            SYNTAX ConfigurationEntry
            MAX-ACCESS not-accessible
            STATUS current
            DESCRIPTION
                "An entry for the Type Configuration parameters."
            INDEX { configTvStandardIdx }
            ::= { configurationTable 1 }

        
        ConfigurationEntry ::=
            SEQUENCE { 
                configTvStandardIdx
                    TvStandard,
                configTvStandardName
                    TvStandard,
                configRxFrequency
                    Integer32,
                configFrequency
                    Integer32,
                configPower
                    FloatingPoint,
                configInputSource
                    InputSource
             }

        configTvStandardIdx OBJECT-TYPE
            SYNTAX TvStandard
            MAX-ACCESS not-accessible
            STATUS current
            DESCRIPTION
                "The index for the TV standard."
            ::= { configurationEntry 3 }

        
        configTvStandardName OBJECT-TYPE
            SYNTAX TvStandard
            MAX-ACCESS read-only
            STATUS current
            DESCRIPTION
                "The name of the TV standard as a text."
            ::= { configurationEntry 5 }

        
        configRxFrequency OBJECT-TYPE
            SYNTAX Integer32 (160000000..910000000)
            UNITS "Hz"
            MAX-ACCESS read-write
            STATUS current
            DESCRIPTION
                "The input frequency for input 1."
            ::= { configurationEntry 6 }

        
        configFrequency OBJECT-TYPE
            SYNTAX Integer32 (47000000..1500000000)
            UNITS "Hz"
            MAX-ACCESS read-write
            STATUS current
            DESCRIPTION
                "The output frequency for input 1."
            ::= { configurationEntry 7 }

        
        configPower OBJECT-TYPE
            SYNTAX FloatingPoint
            UNITS "W"
            MAX-ACCESS read-write
            STATUS current
            DESCRIPTION
                "The power (0.0 ... 440.0) for input 1."
            ::= { configurationEntry 8 }

        
        configInputSource OBJECT-TYPE
            SYNTAX InputSource
            MAX-ACCESS read-write
            STATUS current
            DESCRIPTION
                "The source for input 1."
            ::= { configurationEntry 9 }

        
        timeSchedulerTable OBJECT-TYPE
            SYNTAX SEQUENCE OF TimeSchedulerEntry
            MAX-ACCESS not-accessible
            STATUS current
            DESCRIPTION
                "Table for Time Scheduler parameters."
            ::= { detailedInfo 31 }

        
        timeSchedulerEntry OBJECT-TYPE
            SYNTAX TimeSchedulerEntry
            MAX-ACCESS not-accessible
            STATUS current
            DESCRIPTION
                "An entry in the table for the Time Scheduler parameters.
                
                A row in this table is created by setting the value of schedulerRowStatus to 
                'createAndGo' or 'createAndWait'.
                
                A row in this table is deleted by setting the value of schedulerRowStatus to 
                'destroy'."
            INDEX { schedulerDateTimeIdx }
            ::= { timeSchedulerTable 1 }

        
        TimeSchedulerEntry ::=
            SEQUENCE { 
                schedulerDateTimeIdx
                    DateAndTime,
                schedulerRowStatus
                    RowStatus,
                schedulerEvent
                    INTEGER,
                schedulerDateTime
                    DateAndTime,
                schedulerTvStandard
                    TvStandard
             }

        schedulerDateTimeIdx OBJECT-TYPE
            SYNTAX DateAndTime
            MAX-ACCESS not-accessible
            STATUS current
            DESCRIPTION
                "The DateAndTime index.
                
                Note: Deci-seconds different from 0 and UTC values are ignored.
                      The index is implemented as a Fixed length string of 8 components. The last
                      component (Deci-seconds) is always 0.
                Example:
                      The DateTime of 2008-9-15,17:45:30.0 
                      has the index: 7.216.9.15.17.45.30.0
                "
            ::= { timeSchedulerEntry 3 }

        
        schedulerRowStatus OBJECT-TYPE
            SYNTAX RowStatus
            MAX-ACCESS read-create
            STATUS current
            DESCRIPTION
                "This object is used to create and delete rows in the timeSchedulerTable."
            ::= { timeSchedulerEntry 5 }

        
        schedulerEvent OBJECT-TYPE
            SYNTAX INTEGER
                {
                daily(1),
                once(2)
                }
            MAX-ACCESS read-create
            STATUS current
            DESCRIPTION
                "The event type."
            ::= { timeSchedulerEntry 6 }

        
        schedulerDateTime OBJECT-TYPE
            SYNTAX DateAndTime
            MAX-ACCESS read-only
            STATUS current
            DESCRIPTION
                "The start date and the time of a daily or one-time event."
            ::= { timeSchedulerEntry 7 }

        
        schedulerTvStandard OBJECT-TYPE
            SYNTAX TvStandard
            MAX-ACCESS read-create
            STATUS current
            DESCRIPTION
                "The TV standard."
            ::= { timeSchedulerEntry 8 }

        
        configuration2Table OBJECT-TYPE
            SYNTAX SEQUENCE OF Configuration2Entry
            MAX-ACCESS not-accessible
            STATUS current
            DESCRIPTION
                "Table for Type Configuration parameters of input 2."
            ::= { detailedInfo 32 }

        
        configuration2Entry OBJECT-TYPE
            SYNTAX Configuration2Entry
            MAX-ACCESS not-accessible
            STATUS current
            DESCRIPTION
                "An entry for the Type Configuration parameters of input 2."
            AUGMENTS { configurationEntry }
            ::= { configuration2Table 1 }

        
        Configuration2Entry ::=
            SEQUENCE { 
                config2TvStandardName
                    TvStandard,
                config2RxFrequency
                    Integer32,
                config2Frequency
                    Integer32,
                config2Power
                    FloatingPoint,
                config2InputSource
                    InputSource
             }

        config2TvStandardName OBJECT-TYPE
            SYNTAX TvStandard
            MAX-ACCESS read-only
            STATUS current
            DESCRIPTION
                "The name of the TV standard as a text."
            ::= { configuration2Entry 5 }

        
        config2RxFrequency OBJECT-TYPE
            SYNTAX Integer32 (160000000..910000000)
            UNITS "Hz"
            MAX-ACCESS read-write
            STATUS current
            DESCRIPTION
                "The input frequency for input 2."
            ::= { configuration2Entry 6 }

        
        config2Frequency OBJECT-TYPE
            SYNTAX Integer32 (47000000..1500000000)
            UNITS "Hz"
            MAX-ACCESS read-write
            STATUS current
            DESCRIPTION
                "The output frequency for input 2."
            ::= { configuration2Entry 7 }

        
        config2Power OBJECT-TYPE
            SYNTAX FloatingPoint
            UNITS "W"
            MAX-ACCESS read-write
            STATUS current
            DESCRIPTION
                "The output power (0.0 ... 2500.0)  for input 2."
            ::= { configuration2Entry 8 }

        
        config2InputSource OBJECT-TYPE
            SYNTAX InputSource
            MAX-ACCESS read-write
            STATUS current
            DESCRIPTION
                "The source for input 2."
            ::= { configuration2Entry 9 }

        
        productInfoTable OBJECT-TYPE
            SYNTAX SEQUENCE OF ProductInfoEntry
            MAX-ACCESS not-accessible
            STATUS current
            DESCRIPTION
                "The table for product typeplates."
            ::= { detailedInfo 100 }

        
        productInfoEntry OBJECT-TYPE
            SYNTAX ProductInfoEntry
            MAX-ACCESS not-accessible
            STATUS current
            DESCRIPTION
                "A row (an entry) for one typeplate."
            INDEX { prodInfoModuleIdx, prodInfoDeviceIdx, prodInfoRackIdx, prodInfoAmpIdx }
            ::= { productInfoTable 1 }

        
        ProductInfoEntry ::=
            SEQUENCE { 
                prodInfoModuleIdx
                    ProdInfoModuleNameTv,
                prodInfoDeviceIdx
                    IndexAB,
                prodInfoRackIdx
                    IndexRack,
                prodInfoAmpIdx
                    IndexAmplifier,
                prodInfoModuleName
                    ProdInfoModuleNameTv,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime
             }

        prodInfoModuleIdx OBJECT-TYPE
            SYNTAX ProdInfoModuleNameTv
            MAX-ACCESS not-accessible
            STATUS current
            DESCRIPTION
                "The module index."
            ::= { productInfoEntry 1 }

        
        prodInfoDeviceIdx OBJECT-TYPE
            SYNTAX IndexAB
            MAX-ACCESS not-accessible
            STATUS current
            DESCRIPTION
                "The dedicated device (A/B)."
            ::= { productInfoEntry 2 }

        
        prodInfoRackIdx OBJECT-TYPE
            SYNTAX IndexRack
            MAX-ACCESS not-accessible
            STATUS current
            DESCRIPTION
                "The rack number (1..10)."
            ::= { productInfoEntry 3 }

        
        prodInfoAmpIdx OBJECT-TYPE
            SYNTAX IndexAmplifier
            MAX-ACCESS not-accessible
            STATUS current
            DESCRIPTION
                "Amplifier Index"
            ::= { productInfoEntry 4 }

        
        prodInfoModuleName OBJECT-TYPE
            SYNTAX ProdInfoModuleNameTv
            MAX-ACCESS read-only
            STATUS current
            DESCRIPTION
                "The name of the module as a text."
            ::= { productInfoEntry 5 }

        
        prodInfoSerialNumber OBJECT-TYPE
            SYNTAX ReadableString
            MAX-ACCESS read-only
            STATUS current
            DESCRIPTION
                "The serial number of the subdevice."
            ::= { productInfoEntry 6 }

        
        prodInfoIdentNumberSW OBJECT-TYPE
            SYNTAX ReadableString
            MAX-ACCESS read-only
            STATUS current
            DESCRIPTION
                "The Rohde&Schwarz identification number of the software, for example 2094.2090.02."
            ::= { productInfoEntry 7 }

        
        prodInfoVersionNumberSW OBJECT-TYPE
            SYNTAX ReadableString
            MAX-ACCESS read-only
            STATUS current
            DESCRIPTION
                "The Rohde&Schwarz revision number of the software, for example 1.2.1."
            ::= { productInfoEntry 8 }

        
        prodInfoIdentNumberHW OBJECT-TYPE
            SYNTAX ReadableString
            MAX-ACCESS read-only
            STATUS current
            DESCRIPTION
                "The Rohde&Schwarz identification number of the hardware, for example 2095.8007.02 (NetCCU)."
            ::= { productInfoEntry 9 }

        
        prodInfoVersionNumberHW OBJECT-TYPE
            SYNTAX ReadableString
            MAX-ACCESS read-only
            STATUS current
            DESCRIPTION
                "The Rohde&Schwarz revision number (product index) of the hardware, for example 03.03."
            ::= { productInfoEntry 10 }

        
        productInfoProductDateHW OBJECT-TYPE
            SYNTAX DateAndTime
            MAX-ACCESS read-only
            STATUS current
            DESCRIPTION
                "The Rohde&Schwarz production date of the hardware,"
            ::= { productInfoEntry 11 }

        
        logbook OBJECT IDENTIFIER ::= { rsXx8000AtvTxObjs 4 }

        
        netCCUNumberOfEntries OBJECT-TYPE
            SYNTAX LogbookMaxEntryNumber
            MAX-ACCESS read-only
            STATUS current
            DESCRIPTION
                "The number of entries in logbook."
            ::= { logbook 1 }

        
        netCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 2 }

        
        netCCULogbookTable OBJECT-TYPE
            SYNTAX SEQUENCE OF NetCCULogbookEntry
            MAX-ACCESS not-accessible
            STATUS current
            DESCRIPTION
                "NetCCU logbook table."
            ::= { logbook 3 }

        
        netCCULogbookEntry OBJECT-TYPE
            SYNTAX NetCCULogbookEntry
            MAX-ACCESS not-accessible
            STATUS current
            DESCRIPTION
                "This is a entry in the logbook."
            INDEX { netCCULogbookEntryIdx }
            ::= { netCCULogbookTable 1 }

        
        NetCCULogbookEntry ::=
            SEQUENCE { 
                netCCULogbookEntryIdx
                    LogbookMaxEntryNumber,
                netCCULogbookEntryNbr
                    LogbookMaxEntryNumber,
                netCCULogbookType
                    EventClass,
                netCCULogbookSlope
                    LogbookEntrySlope,
                netCCULogbookMessage
                    LogbookEntryMessagesNetCCU,
                netCCULogbookDateTime
                    DateAndTime
             }

        netCCULogbookEntryIdx OBJECT-TYPE
            SYNTAX LogbookMaxEntryNumber
            MAX-ACCESS not-accessible
            STATUS current
            DESCRIPTION
                "This is an increasing number from 1 to 128. It is used as an index column for SNMP."
            ::= { netCCULogbookEntry 1 }

        
        netCCULogbookEntryNbr OBJECT-TYPE
            SYNTAX LogbookMaxEntryNumber
            MAX-ACCESS read-only
            STATUS current
            DESCRIPTION
                "This is the number of the logbook entry. It is an decreasing number from max 128 down to 1."
            ::= { netCCULogbookEntry 2 }

        
        netCCULogbookType OBJECT-TYPE
            SYNTAX EventClass
            MAX-ACCESS read-only
            STATUS current
            DESCRIPTION
                "Can either be Fault, Warning or State."
            ::= { netCCULogbookEntry 3 }

        
        netCCULogbookSlope OBJECT-TYPE
            SYNTAX LogbookEntrySlope
            MAX-ACCESS read-only
            STATUS current
            DESCRIPTION
                "Either set (event raises) or reset (event disappears)"
            ::= { netCCULogbookEntry 4 }

        
        netCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { netCCULogbookEntry 5 }

        
        netCCULogbookDateTime OBJECT-TYPE
            SYNTAX DateAndTime
            MAX-ACCESS read-only
            STATUS current
            DESCRIPTION
                "netCCULogbookDateTime"
            ::= { netCCULogbookEntry 6 }

        
        exciterANumberOfEntries OBJECT-TYPE
            SYNTAX LogbookMaxEntryNumber
            MAX-ACCESS read-only
            STATUS current
            DESCRIPTION
                "The number of entries in logbook."
            ::= { logbook 4 }

        
        exciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 5 }

        
        exciterALogbookTable OBJECT-TYPE
            SYNTAX SEQUENCE OF ExciterALogbookEntry
            MAX-ACCESS not-accessible
            STATUS current
            DESCRIPTION
                "ExciterA logbook table."
            ::= { logbook 6 }

        
        exciterALogbookEntry OBJECT-TYPE
            SYNTAX ExciterALogbookEntry
            MAX-ACCESS not-accessible
            STATUS current
            DESCRIPTION
                "This is a entry in the logbook."
            INDEX { excALogbookEntryIdx }
            ::= { exciterALogbookTable 1 }

        
        ExciterALogbookEntry ::=
            SEQUENCE { 
                excALogbookEntryIdx
                    LogbookMaxEntryNumber,
                excALogbookEntryNbr
                    LogbookMaxEntryNumber,
                excALogbookType
                    EventClass,
                excALogbookSlope
                    LogbookEntrySlope,
                excALogbookMessage
                    LogbookEntryMessagesExcTv,
                excALogbookDateTime
                    DateAndTime
             }

        excALogbookEntryIdx OBJECT-TYPE
            SYNTAX LogbookMaxEntryNumber
            MAX-ACCESS not-accessible
            STATUS current
            DESCRIPTION
                "This is an increasing number from 1 to 128. It is used as an index column for SNMP."
            ::= { exciterALogbookEntry 1 }

        
        excALogbookEntryNbr OBJECT-TYPE
            SYNTAX LogbookMaxEntryNumber
            MAX-ACCESS read-only
            STATUS current
            DESCRIPTION
                "This is the number of the logbook entry. It is an decreasing number from max 128 down to 1."
            ::= { exciterALogbookEntry 2 }

        
        excALogbookType OBJECT-TYPE
            SYNTAX EventClass
            MAX-ACCESS read-only
            STATUS current
            DESCRIPTION
                "Can either be Fault, Warning or State."
            ::= { exciterALogbookEntry 3 }

        
        excALogbookSlope OBJECT-TYPE
            SYNTAX LogbookEntrySlope
            MAX-ACCESS read-only
            STATUS current
            DESCRIPTION
                "Either set (event raises) or reset (event disappears)"
            ::= { exciterALogbookEntry 4 }

        
        excALogbookMessage OBJECT-TYPE
            SYNTAX LogbookEntryMessagesExcTv
            MAX-ACCESS read-only
            STATUS current
            DESCRIPTION
                "See RS-XX8000-COMMON-MIB - TextualConvention for details."
            ::= { exciterALogbookEntry 5 }

        
        excALogbookDateTime OBJECT-TYPE
            SYNTAX DateAndTime
            MAX-ACCESS read-only
            STATUS current
            DESCRIPTION
                "The time of the logbook entry."
            ::= { exciterALogbookEntry 6 }

        
        outputstageANumberOfEntries OBJECT-TYPE
            SYNTAX LogbookMaxEntryNumber
            MAX-ACCESS read-only
            STATUS current
            DESCRIPTION
                "The number of entries in logbook."
            ::= { logbook 7 }

        
        outputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 8 }

        
        outputstageALogbookTable OBJECT-TYPE
            SYNTAX SEQUENCE OF OutputstageALogbookEntry
            MAX-ACCESS not-accessible
            STATUS current
            DESCRIPTION
                "OutputstageA logbook table."
            ::= { logbook 9 }

        
        outputstageALogbookEntry OBJECT-TYPE
            SYNTAX OutputstageALogbookEntry
            MAX-ACCESS not-accessible
            STATUS current
            DESCRIPTION
                "This is a entry in the logbook."
            INDEX { ostALogbookEntryIdx }
            ::= { outputstageALogbookTable 1 }

        
        OutputstageALogbookEntry ::=
            SEQUENCE { 
                ostALogbookEntryIdx
                    LogbookMaxEntryNumber,
                ostALogbookEntryNbr
                    LogbookMaxEntryNumber,
                ostALogbookType
                    EventClass,
                ostALogbookSlope
                    LogbookEntrySlope,
                ostALogbookMessage
                    LogbookEntryMessagesOST,
                ostALogbookDateTime
                    DateAndTime
             }

        ostALogbookEntryIdx OBJECT-TYPE
            SYNTAX LogbookMaxEntryNumber
            MAX-ACCESS not-accessible
            STATUS current
            DESCRIPTION
                "This is an increasing number from 1 to 128. It is used as an index column for SNMP."
            ::= { outputstageALogbookEntry 1 }

        
        ostALogbookEntryNbr OBJECT-TYPE
            SYNTAX LogbookMaxEntryNumber
            MAX-ACCESS read-only
            STATUS current
            DESCRIPTION
                "This is the number of the logbook entry. It is an decreasing number from max 128 down to 1."
            ::= { outputstageALogbookEntry 2 }

        
        ostALogbookType OBJECT-TYPE
            SYNTAX EventClass
            MAX-ACCESS read-only
            STATUS current
            DESCRIPTION
                "Can either be Fault, Warning or State."
            ::= { outputstageALogbookEntry 3 }

        
        ostALogbookSlope OBJECT-TYPE
            SYNTAX LogbookEntrySlope
            MAX-ACCESS read-only
            STATUS current
            DESCRIPTION
                "Either set (event raises) or reset (event disappears)"
            ::= { outputstageALogbookEntry 4 }

        
        ostALogbookMessage OBJECT-TYPE
            SYNTAX LogbookEntryMessagesOST
            MAX-ACCESS read-only
            STATUS current
            DESCRIPTION
                "See RS-XX8000-COMMON-MIB - TextualConvention for details."
            ::= { outputstageALogbookEntry 5 }

        
        ostALogbookDateTime OBJECT-TYPE
            SYNTAX DateAndTime
            MAX-ACCESS read-only
            STATUS current
            DESCRIPTION
                "The time of the logbook entry."
            ::= { outputstageALogbookEntry 6 }

        
        exciterBNumberOfEntries OBJECT-TYPE
            SYNTAX LogbookMaxEntryNumber
            MAX-ACCESS read-only
            STATUS current
            DESCRIPTION
                "The number of entries in logbook."
            ::= { logbook 10 }

        
        exciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 11 }

        
        exciterBLogbookTable OBJECT-TYPE
            SYNTAX SEQUENCE OF ExciterBLogbookEntry
            MAX-ACCESS not-accessible
            STATUS current
            DESCRIPTION
                "ExciterB logbook table."
            ::= { logbook 12 }

        
        exciterBLogbookEntry OBJECT-TYPE
            SYNTAX ExciterBLogbookEntry
            MAX-ACCESS not-accessible
            STATUS current
            DESCRIPTION
                "This is a entry in the logbook."
            INDEX { excBLogbookEntryIdx }
            ::= { exciterBLogbookTable 1 }

        
        ExciterBLogbookEntry ::=
            SEQUENCE { 
                excBLogbookEntryIdx
                    LogbookMaxEntryNumber,
                excBLogbookEntryNbr
                    LogbookMaxEntryNumber,
                excBLogbookType
                    EventClass,
                excBLogbookSlope
                    LogbookEntrySlope,
                excBLogbookMessage
                    LogbookEntryMessagesExcTv,
                excBLogbookDateTime
                    DateAndTime
             }

        excBLogbookEntryIdx OBJECT-TYPE
            SYNTAX LogbookMaxEntryNumber
            MAX-ACCESS not-accessible
            STATUS current
            DESCRIPTION
                "This is an increasing number from 1 to 128. It is used as an index column for SNMP."
            ::= { exciterBLogbookEntry 1 }

        
        excBLogbookEntryNbr OBJECT-TYPE
            SYNTAX LogbookMaxEntryNumber
            MAX-ACCESS read-only
            STATUS current
            DESCRIPTION
                "This is the number of the logbook entry. It is an decreasing number from max 128 down to 1."
            ::= { exciterBLogbookEntry 2 }

        
        excBLogbookType OBJECT-TYPE
            SYNTAX EventClass
            MAX-ACCESS read-only
            STATUS current
            DESCRIPTION
                "Can either be Fault, Warning or State."
            ::= { exciterBLogbookEntry 3 }

        
        excBLogbookSlope OBJECT-TYPE
            SYNTAX LogbookEntrySlope
            MAX-ACCESS read-only
            STATUS current
            DESCRIPTION
                "Either set (event raises) or reset (event disappears)"
            ::= { exciterBLogbookEntry 4 }

        
        excBLogbookMessage OBJECT-TYPE
            SYNTAX LogbookEntryMessagesExcTv
            MAX-ACCESS read-only
            STATUS current
            DESCRIPTION
                "See RS-XX8000-COMMON-MIB - TextualConvention for details."
            ::= { exciterBLogbookEntry 5 }

        
        excBLogbookDateTime OBJECT-TYPE
            SYNTAX DateAndTime
            MAX-ACCESS read-only
            STATUS current
            DESCRIPTION
                "The time of the logbook entry."
            ::= { exciterBLogbookEntry 6 }

        
        outputstageBNumberOfEntries OBJECT-TYPE
            SYNTAX LogbookMaxEntryNumber
            MAX-ACCESS read-only
            STATUS current
            DESCRIPTION
                "The number of entries in logbook."
            ::= { logbook 13 }

        
        outputstageBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbook 14 }

        
        outputstageBLogbookTable OBJECT-TYPE
            SYNTAX SEQUENCE OF OutputstageBLogbookEntry
            MAX-ACCESS not-accessible
            STATUS current
            DESCRIPTION
                "OutputstageB logbook table."
            ::= { logbook 15 }

        
        outputstageBLogbookEntry OBJECT-TYPE
            SYNTAX OutputstageBLogbookEntry
            MAX-ACCESS not-accessible
            STATUS current
            DESCRIPTION
                "This is a entry in the logbook."
            INDEX { ostBLogbookEntryIdx }
            ::= { outputstageBLogbookTable 1 }

        
        OutputstageBLogbookEntry ::=
            SEQUENCE { 
                ostBLogbookEntryIdx
                    LogbookMaxEntryNumber,
                ostBLogbookEntryNbr
                    LogbookMaxEntryNumber,
                ostBLogbookType
                    EventClass,
                ostBLogbookSlope
                    LogbookEntrySlope,
                ostBLogbookMessage
                    LogbookEntryMessagesOST,
                ostBLogbookDateTime
                    DateAndTime
             }

        ostBLogbookEntryIdx OBJECT-TYPE
            SYNTAX LogbookMaxEntryNumber
            MAX-ACCESS not-accessible
            STATUS current
            DESCRIPTION
                "This is an increasing number from 1 to 128. It is used as an index column for SNMP."
            ::= { outputstageBLogbookEntry 1 }

        
        ostBLogbookEntryNbr OBJECT-TYPE
            SYNTAX LogbookMaxEntryNumber
            MAX-ACCESS read-only
            STATUS current
            DESCRIPTION
                "This is the number of the logbook entry. It is an decreasing number from max 128 down to 1."
            ::= { outputstageBLogbookEntry 2 }

        
        ostBLogbookType OBJECT-TYPE
            SYNTAX EventClass
            MAX-ACCESS read-only
            STATUS current
            DESCRIPTION
                "Can either be Fault, Warning or State."
            ::= { outputstageBLogbookEntry 3 }

        
        ostBLogbookSlope OBJECT-TYPE
            SYNTAX LogbookEntrySlope
            MAX-ACCESS read-only
            STATUS current
            DESCRIPTION
                "Either set (event raises) or reset (event disappears)"
            ::= { outputstageBLogbookEntry 4 }

        
        ostBLogbookMessage OBJECT-TYPE
            SYNTAX LogbookEntryMessagesOST
            MAX-ACCESS read-only
            STATUS current
            DESCRIPTION
                "See RS-XX8000-COMMON-MIB - TextualConvention for details."
            ::= { outputstageBLogbookEntry 5 }

        
        ostBLogbookDateTime OBJECT-TYPE
            SYNTAX DateAndTime
            MAX-ACCESS read-only
            STATUS current
            DESCRIPTION
                "The time of the logbook entry."
            ::= { outputstageBLogbookEntry 6 }

        
        rfProbesTable OBJECT-TYPE
            SYNTAX SEQUENCE OF RfProbesEntry
            MAX-ACCESS not-accessible
            STATUS current
            DESCRIPTION
                "This table contains all commands for the RF probes."
            ::= { rsXx8000AtvTxObjs 5 }

        
        rfProbesEntry OBJECT-TYPE
            SYNTAX RfProbesEntry
            MAX-ACCESS not-accessible
            STATUS current
            DESCRIPTION
                "An entry for a designated transmitter and device."
            INDEX { rfProbesOstIdx }
            ::= { rfProbesTable 1 }

        
        RfProbesEntry ::=
            SEQUENCE { 
                rfProbesNetCCURfProbe1
                    FloatingPoint,
                rfProbesNetCCURfProbe2
                    FloatingPoint,
                rfProbesAntFwdNominal
                    FloatingPoint,
                rfProbesAntFwdWarningLimit
                    FloatingPoint,
                rfProbesAntFwdFailLimit
                    FloatingPoint,
                rfProbesAntFwdDelayTimeRfFail
                    Integer32,
                rfProbesAntFwdSetOffset
                    Trigger,
                rfProbesAntFwdSetGain
                    Trigger,
                rfProbesAntReflWarningLimit
                    FloatingPoint,
                rfProbesAntReflSetOffset
                    Trigger,
                rfProbesAntReflSetGain
                    Trigger,
                rfProbesDLFwdNominal
                    FloatingPoint,
                rfProbesDLFwdWarningLimit
                    FloatingPoint,
                rfProbesDLFwdFailLimit
                    FloatingPoint,
                rfProbesDLFwdDelayTimeRfFail
                    Integer32,
                rfProbesDLFwdSetOffset
                    Trigger,
                rfProbesDLFwdSetGain
                    Trigger,
                rfProbesDLReflWarningLimit
                    FloatingPoint,
                rfProbesDLReflSetOffset
                    Trigger,
                rfProbesDLReflSetGain
                    Trigger,
                rfProbesOstIdx
                    IndexAB,
                rfProbesOstFwdNominal
                    FloatingPoint,
                rfProbesOstFwdWarningLimit
                    FloatingPoint,
                rfProbesOstFwdFailLimit
                    FloatingPoint,
                rfProbesOstFwdDelayTimeRfFail
                    Integer32,
                rfProbesOstFwdSetOffset
                    Trigger,
                rfProbesOstFwdSetGain
                    Trigger,
                rfProbesOstReflWarningLimit
                    FloatingPoint,
                rfProbesOstReflSetOffset
                    Trigger,
                rfProbesOstReflSetGain
                    Trigger
             }

        rfProbesNetCCURfProbe1 OBJECT-TYPE
            SYNTAX FloatingPoint
            UNITS "Volt"
            MAX-ACCESS read-only
            STATUS current
            DESCRIPTION
                "Current voltage on RF Probe 1."
            ::= { rfProbesEntry 1 }

        
        rfProbesNetCCURfProbe2 OBJECT-TYPE
            SYNTAX FloatingPoint
            UNITS "Volt"
            MAX-ACCESS read-only
            STATUS current
            DESCRIPTION
                "Current voltage on RF Probe 2."
            ::= { rfProbesEntry 2 }

        
        rfProbesAntFwdNominal OBJECT-TYPE
            SYNTAX FloatingPoint
            UNITS "Watt"
            MAX-ACCESS read-write
            STATUS current
            DESCRIPTION
                "This sets the nominal value [W] of the transmitter (to antenna)."
            ::= { rfProbesEntry 3 }

        
        rfProbesAntFwdWarningLimit OBJECT-TYPE
            SYNTAX FloatingPoint
            UNITS "dB"
            MAX-ACCESS read-write
            STATUS current
            DESCRIPTION
                "This sets the warning limit for the transmitters RF control (to antenna)."
            ::= { rfProbesEntry 4 }

        
        rfProbesAntFwdFailLimit OBJECT-TYPE
            SYNTAX FloatingPoint
            UNITS "dB"
            MAX-ACCESS read-write
            STATUS current
            DESCRIPTION
                "This sets the fault limit for the transmitters RF control (to antenna)."
            ::= { rfProbesEntry 5 }

        
        rfProbesAntFwdDelayTimeRfFail OBJECT-TYPE
            SYNTAX Integer32 (1..20)
            UNITS "seconds"
            MAX-ACCESS read-write
            STATUS current
            DESCRIPTION
                "This sets the delay time for the RF Fail control (to antenna)."
            ::= { rfProbesEntry 6 }

        
        rfProbesAntFwdSetOffset OBJECT-TYPE
            SYNTAX Trigger
            MAX-ACCESS read-write
            STATUS current
            DESCRIPTION
                "This triggers Set Offset."
            ::= { rfProbesEntry 7 }

        
        rfProbesAntFwdSetGain OBJECT-TYPE
            SYNTAX Trigger
            MAX-ACCESS read-write
            STATUS current
            DESCRIPTION
                "This triggers Set Gain."
            ::= { rfProbesEntry 8 }

        
        rfProbesAntReflWarningLimit OBJECT-TYPE
            SYNTAX FloatingPoint
            UNITS "dB"
            MAX-ACCESS read-write
            STATUS current
            DESCRIPTION
                "This sets the warning limit for the transmitters reflection control (to antenna)."
            ::= { rfProbesEntry 9 }

        
        rfProbesAntReflSetOffset OBJECT-TYPE
            SYNTAX Trigger
            MAX-ACCESS read-write
            STATUS current
            DESCRIPTION
                "This triggers Set Offset."
            ::= { rfProbesEntry 10 }

        
        rfProbesAntReflSetGain OBJECT-TYPE
            SYNTAX Trigger
            MAX-ACCESS read-write
            STATUS current
            DESCRIPTION
                "This triggers Set Gain."
            ::= { rfProbesEntry 11 }

        
        rfProbesDLFwdNominal OBJECT-TYPE
            SYNTAX FloatingPoint
            UNITS "Watt"
            MAX-ACCESS read-write
            STATUS current
            DESCRIPTION
                "This sets the nominal value [W] of the transmitter (to dummyload)."
            ::= { rfProbesEntry 12 }

        
        rfProbesDLFwdWarningLimit OBJECT-TYPE
            SYNTAX FloatingPoint
            UNITS "dB"
            MAX-ACCESS read-write
            STATUS current
            DESCRIPTION
                "This sets the warning limit for the transmitters RF control (to dummyload)."
            ::= { rfProbesEntry 13 }

        
        rfProbesDLFwdFailLimit OBJECT-TYPE
            SYNTAX FloatingPoint
            UNITS "dB"
            MAX-ACCESS read-write
            STATUS current
            DESCRIPTION
                "This sets the fault limit for the transmitters RF control (to dummyload)."
            ::= { rfProbesEntry 14 }

        
        rfProbesDLFwdDelayTimeRfFail OBJECT-TYPE
            SYNTAX Integer32 (1..20)
            UNITS "seconds"
            MAX-ACCESS read-write
            STATUS current
            DESCRIPTION
                "This sets the delay time for the RF Fail control (to dummyload)."
            ::= { rfProbesEntry 15 }

        
        rfProbesDLFwdSetOffset OBJECT-TYPE
            SYNTAX Trigger
            MAX-ACCESS read-write
            STATUS current
            DESCRIPTION
                "This triggers Set Offset."
            ::= { rfProbesEntry 16 }

        
        rfProbesDLFwdSetGain OBJECT-TYPE
            SYNTAX Trigger
            MAX-ACCESS read-write
            STATUS current
            DESCRIPTION
                "This triggers Set Gain."
            ::= { rfProbesEntry 17 }

        
        rfProbesDLReflWarningLimit OBJECT-TYPE
            SYNTAX FloatingPoint
            UNITS "dB"
            MAX-ACCESS read-write
            STATUS current
            DESCRIPTION
                "This sets the warning limit for the transmitters reflection control (to dummyload)."
            ::= { rfProbesEntry 18 }

        
        rfProbesDLReflSetOffset OBJECT-TYPE
            SYNTAX Trigger
            MAX-ACCESS read-write
            STATUS current
            DESCRIPTION
                "This triggers Set Offset."
            ::= { rfProbesEntry 19 }

        
        rfProbesDLReflSetGain OBJECT-TYPE
            SYNTAX Trigger
            MAX-ACCESS read-write
            STATUS current
            DESCRIPTION
                "This triggers Set Gain."
            ::= { rfProbesEntry 20 }

        
        rfProbesOstIdx OBJECT-TYPE
            SYNTAX IndexAB
            MAX-ACCESS not-accessible
            STATUS current
            DESCRIPTION
                "The dedicated outputstage (A/B)."
            ::= { rfProbesEntry 21 }

        
        rfProbesOstFwdNominal OBJECT-TYPE
            SYNTAX FloatingPoint
            UNITS "Watt"
            MAX-ACCESS read-write
            STATUS current
            DESCRIPTION
                "This sets the nominal value [W] of the outputstage."
            ::= { rfProbesEntry 22 }

        
        rfProbesOstFwdWarningLimit OBJECT-TYPE
            SYNTAX FloatingPoint
            UNITS "dB"
            MAX-ACCESS read-write
            STATUS current
            DESCRIPTION
                "This sets the warning limit for the outputstage RF control."
            ::= { rfProbesEntry 23 }

        
        rfProbesOstFwdFailLimit OBJECT-TYPE
            SYNTAX FloatingPoint
            UNITS "dB"
            MAX-ACCESS read-write
            STATUS current
            DESCRIPTION
                "This sets the fault limit for the outputstage RF control."
            ::= { rfProbesEntry 24 }

        
        rfProbesOstFwdDelayTimeRfFail OBJECT-TYPE
            SYNTAX Integer32 (1..20)
            UNITS "seconds"
            MAX-ACCESS read-write
            STATUS current
            DESCRIPTION
                "This sets the delay time for the outputstage RF Fail control."
            ::= { rfProbesEntry 25 }

        
        rfProbesOstFwdSetOffset OBJECT-TYPE
            SYNTAX Trigger
            MAX-ACCESS read-write
            STATUS current
            DESCRIPTION
                "This triggers Set Offset."
            ::= { rfProbesEntry 26 }

        
        rfProbesOstFwdSetGain OBJECT-TYPE
            SYNTAX Trigger
            MAX-ACCESS read-write
            STATUS current
            DESCRIPTION
                "This triggers Set Gain."
            ::= { rfProbesEntry 27 }

        
        rfProbesOstReflWarningLimit OBJECT-TYPE
            SYNTAX FloatingPoint
            UNITS "dB"
            MAX-ACCESS read-write
            STATUS current
            DESCRIPTION
                "This sets the warning limit for the outputstage reflection control."
            ::= { rfProbesEntry 28 }

        
        rfProbesOstReflSetOffset OBJECT-TYPE
            SYNTAX Trigger
            MAX-ACCESS read-write
            STATUS current
            DESCRIPTION
                "This triggers Set Offset."
            ::= { rfProbesEntry 29 }

        
        rfProbesOstReflSetGain OBJECT-TYPE
            SYNTAX Trigger
            MAX-ACCESS read-write
            STATUS current
            DESCRIPTION
                "This triggers Set Gain."
            ::= { rfProbesEntry 30 }

        
        rackTable OBJECT-TYPE
            SYNTAX SEQUENCE OF RackEntry
            MAX-ACCESS not-accessible
            STATUS current
            DESCRIPTION
                "This table contains important commands for the racks."
            ::= { rsXx8000AtvTxObjs 6 }

        
        rackEntry OBJECT-TYPE
            SYNTAX RackEntry
            MAX-ACCESS not-accessible
            STATUS current
            DESCRIPTION
                "An entry for a designated rack or rack's rf probe."
            INDEX { ostDeviceIdx, rackIdx, rackRfProbeIdx }
            ::= { rackTable 1 }

        
        RackEntry ::=
            SEQUENCE { 
                ostDeviceIdx
                    IndexAB,
                rackIdx
                    IndexRack,
                rackRfProbeIdx
                    INTEGER,
                amplifiersPerRack
                    Integer32,
                rackRfEventSignalling
                    TruthValue,
                rackReferenceVoltage
                    FloatingPoint,
                amplifiersPowerSupply
                    FloatingPoint,
                rackGeneralPurposeInput
                    INTEGER,
                rackOnOff
                    SwitchOnOff,
                rfProbePresent
                    TruthValue,
                rfProbeConfigurationLabel
                    ReadableString,
                rfProbeConfigurationNominalValue
                    Integer32,
                rfProbeThresholdRfFailLimit
                    FloatingPoint,
                rfProbeThresholdTimeoutRfFailCtr
                    Integer32,
                rfProbeThresholdWarningLimit
                    FloatingPoint,
                rfProbeCalibrationGain
                    FloatingPoint,
                rfProbeCalibrationOffset
                    FloatingPoint,
                rfProbeCalibrationSetGain
                    Trigger,
                rfProbeCalibrationSetOffset
                    Trigger,
                rfProbeMeasuredValue
                    FloatingPoint
             }

        ostDeviceIdx OBJECT-TYPE
            SYNTAX IndexAB
            MAX-ACCESS not-accessible
            STATUS current
            DESCRIPTION
                "The index to address outputstageA and outputstageB."
            ::= { rackEntry 2 }

        
        rackIdx OBJECT-TYPE
            SYNTAX IndexRack
            MAX-ACCESS not-accessible
            STATUS current
            DESCRIPTION
                "The index to address the racks."
            ::= { rackEntry 3 }

        
        rackRfProbeIdx OBJECT-TYPE
            SYNTAX INTEGER
                {
                forward(1),
                reflected(2)
                }
            MAX-ACCESS not-accessible
            STATUS current
            DESCRIPTION
                "The index to address forward and reflected RF probes.
                For not RF probe parameters this index is always 1."
            ::= { rackEntry 4 }

        
        amplifiersPerRack OBJECT-TYPE
            SYNTAX Integer32 (1..10)
            MAX-ACCESS read-only
            STATUS current
            DESCRIPTION
                "The number of amplifiers of a rack."
            ::= { rackEntry 6 }

        
        rackRfEventSignalling OBJECT-TYPE
            SYNTAX TruthValue
            MAX-ACCESS read-write
            STATUS current
            DESCRIPTION
                "This configures whether to signal rf events or not."
            ::= { rackEntry 7 }

        
        rackReferenceVoltage OBJECT-TYPE
            SYNTAX FloatingPoint
            UNITS "percent"
            MAX-ACCESS read-write
            STATUS current
            DESCRIPTION
                "This parameter controls the reference voltage (31.0 ... 100.0)."
            ::= { rackEntry 8 }

        
        amplifiersPowerSupply OBJECT-TYPE
            SYNTAX FloatingPoint
            UNITS "percent"
            MAX-ACCESS read-write
            STATUS current
            DESCRIPTION
                "This parameter controls the power supplies of the amplifier 
                within the rack (31.0 ... 100.0)."
            ::= { rackEntry 9 }

        
        rackGeneralPurposeInput OBJECT-TYPE
            SYNTAX INTEGER
                {
                unused(1),
                doorOpen(2),
                extCoolingWarning(3),
                extCoolingFault(4)
                }
            MAX-ACCESS read-write
            STATUS current
            DESCRIPTION
                "Setting of the general purpose input behaviour."
            ::= { rackEntry 10 }

        
        rackOnOff OBJECT-TYPE
            SYNTAX SwitchOnOff
            MAX-ACCESS read-write
            STATUS current
            DESCRIPTION
                "This switches the rack on/off."
            ::= { rackEntry 20 }

        
        rfProbePresent OBJECT-TYPE
            SYNTAX TruthValue
            MAX-ACCESS read-only
            STATUS current
            DESCRIPTION
                "If the RF probe of this rack is present."
            ::= { rackEntry 50 }

        
        rfProbeConfigurationLabel OBJECT-TYPE
            SYNTAX ReadableString (SIZE (0..12))
            MAX-ACCESS read-write
            STATUS obsolete
            DESCRIPTION
                "Name for the measured signal on RF Probe."
            ::= { rackEntry 51 }

        
        rfProbeConfigurationNominalValue OBJECT-TYPE
            SYNTAX Integer32 (0..100000)
            UNITS "W"
            MAX-ACCESS read-write
            STATUS current
            DESCRIPTION
                "The nominal value of the measured signal."
            ::= { rackEntry 52 }

        
        rfProbeThresholdRfFailLimit OBJECT-TYPE
            SYNTAX FloatingPoint
            UNITS "dB"
            MAX-ACCESS read-write
            STATUS current
            DESCRIPTION
                "Fault limit for the RF control (-20.0 ... 0.0)."
            ::= { rackEntry 55 }

        
        rfProbeThresholdTimeoutRfFailCtr OBJECT-TYPE
            SYNTAX Integer32 (1..20)
            UNITS "s"
            MAX-ACCESS read-write
            STATUS current
            DESCRIPTION
                "Timeout for RF Fail Control."
            ::= { rackEntry 56 }

        
        rfProbeThresholdWarningLimit OBJECT-TYPE
            SYNTAX FloatingPoint
            UNITS "dB"
            MAX-ACCESS read-write
            STATUS current
            DESCRIPTION
                "Warning limit for the RF control (-20.0 ... 0.0).
                
                For reflected probes:
                Warning limit for the reflection control. This limit is added to the 
                fault limit to generate the real warning limit; e.g. the fault limit 
                is -17.0dB and the warning limit is -3.0dB, so the warning is active 
                on a reflected power higher than -20.0 dB."
            ::= { rackEntry 57 }

        
        rfProbeCalibrationGain OBJECT-TYPE
            SYNTAX FloatingPoint
            UNITS "V"
            MAX-ACCESS read-only
            STATUS current
            DESCRIPTION
                "Measured value of gain calibration."
            ::= { rackEntry 60 }

        
        rfProbeCalibrationOffset OBJECT-TYPE
            SYNTAX FloatingPoint
            UNITS "V"
            MAX-ACCESS read-only
            STATUS current
            DESCRIPTION
                "Measured value of offset calibration."
            ::= { rackEntry 61 }

        
        rfProbeCalibrationSetGain OBJECT-TYPE
            SYNTAX Trigger
            MAX-ACCESS read-write
            STATUS current
            DESCRIPTION
                "Sets the gain calibration."
            ::= { rackEntry 62 }

        
        rfProbeCalibrationSetOffset OBJECT-TYPE
            SYNTAX Trigger
            MAX-ACCESS read-write
            STATUS current
            DESCRIPTION
                "Sets the offset calibration."
            ::= { rackEntry 63 }

        
        rfProbeMeasuredValue OBJECT-TYPE
            SYNTAX FloatingPoint
            UNITS "W"
            MAX-ACCESS read-only
            STATUS current
            DESCRIPTION
                "Measured forward/reflected power of antenna signal."
            ::= { rackEntry 65 }

        
        sx801AmplifierTable OBJECT-TYPE
            SYNTAX SEQUENCE OF Sx801AmplifierEntry
            MAX-ACCESS not-accessible
            STATUS current
            DESCRIPTION
                "Amplifier status values for SX801 amplifiers."
            ::= { rsXx8000AtvTxObjs 7 }

        
        sx801AmplifierEntry OBJECT-TYPE
            SYNTAX Sx801AmplifierEntry
            MAX-ACCESS not-accessible
            STATUS current
            DESCRIPTION
                "Description."
            INDEX { sx801AmpIdx }
            ::= { sx801AmplifierTable 1 }

        
        Sx801AmplifierEntry ::=
            SEQUENCE { 
                sx801AmpIdx
                    IndexAmplifier,
                sx801AmpRfOut
                    Sx801AmplifierState,
                sx801AmpRfIn
                    Sx801AmplifierState,
                sx801AmpReflection
                    INTEGER,
                sx801AmpOn
                    INTEGER,
                sx801AmpAC
                    Sx801AmplifierState,
                sx801AmpCommunication
                    INTEGER,
                sx801AmpTransistor
                    Sx801AmplifierState,
                sx801AmpDriver
                    Sx801AmplifierState,
                sx801AmpTemperature
                    Sx801AmplifierState,
                sx801AmpBlower
                    Sx801AmplifierState,
                sx801AmpRegulation
                    Sx801AmplifierState,
                sx801AmpUpdate
                    TruthValue,
                sx801Supply1Temperature
                    Sx801AmplifierState,
                sx801Supply2Temperature
                    Sx801AmplifierState,
                sx801SupplyRTemperature
                    Sx801AmplifierState,
                sx801Supply1DC
                    Sx801AmplifierState,
                sx801Supply2DC
                    Sx801AmplifierState,
                sx801SupplyRDC
                    Sx801AmplifierState,
                sx801AmpValueI1
                    FloatingPoint,
                sx801AmpValueI2
                    FloatingPoint,
                sx801AmpValueI3
                    FloatingPoint,
                sx801AmpValueI4
                    FloatingPoint,
                sx801AmpValueIPre
                    FloatingPoint,
                sx801AmpValueIDrv1
                    FloatingPoint,
                sx801AmpValueIDrv2
                    FloatingPoint,
                sx801AmpValuePowerOut
                    FloatingPoint,
                sx801AmpValueReflection
                    FloatingPoint,
                sx801AmpValueVRef
                    FloatingPoint,
                sx801AmpValueVReg
                    FloatingPoint,
                sx801AmpValueTemperature
                    FloatingPoint,
                sx801AmpValueMonAtt
                    FloatingPoint,
                sx801AmpValueVAux1
                    FloatingPoint,
                sx801AmpValueVAux2
                    FloatingPoint,
                sx801Supply1ValuePwr
                    FloatingPoint,
                sx801Supply2ValuePwr
                    FloatingPoint,
                sx801Supply1ValueDc
                    FloatingPoint,
                sx801Supply2ValueDc
                    FloatingPoint
             }

        sx801AmpIdx OBJECT-TYPE
            SYNTAX IndexAmplifier
            MAX-ACCESS not-accessible
            STATUS current
            DESCRIPTION
                "The amplifier index."
            ::= { sx801AmplifierEntry 1 }

        
        sx801AmpRfOut OBJECT-TYPE
            SYNTAX Sx801AmplifierState
            MAX-ACCESS read-only
            STATUS current
            DESCRIPTION
                "Shows if the amplifier generates an RF or not.
                off(1): The amplifier output is switched off
                e.g. because the amplifier gets no input signal or the transmitter has been switched off
                warning(2): There is an RF but its level is less than the RF warning limit.
                ok(3): The RF level is greater than the RF warning limit."
            ::= { sx801AmplifierEntry 2 }

        
        sx801AmpRfIn OBJECT-TYPE
            SYNTAX Sx801AmplifierState
            MAX-ACCESS read-only
            STATUS current
            DESCRIPTION
                "Displays the state of the amplifier input.
                off(1): no input signal detected
                warning(2): the level of the input signal is too low or too high.
                ok(3): input signal is OK."
            ::= { sx801AmplifierEntry 3 }

        
        sx801AmpReflection OBJECT-TYPE
            SYNTAX INTEGER
                {
                off(1),
                warning(2),
                unknown(3),
                fault(4)
                }
            MAX-ACCESS read-only
            STATUS current
            DESCRIPTION
                " A reflection on RF output of this Amplifier module has been detected.
                This leads to a reduction of output power of the amplifier.
                
                "
            ::= { sx801AmplifierEntry 4 }

        
        sx801AmpOn OBJECT-TYPE
            SYNTAX INTEGER
                {
                off(1),
                on(3),
                unknown(4)
                }
            MAX-ACCESS read-only
            STATUS current
            DESCRIPTION
                "Shows if the amplifier has been switched on by the control unit."
            ::= { sx801AmplifierEntry 5 }

        
        sx801AmpAC OBJECT-TYPE
            SYNTAX Sx801AmplifierState
            MAX-ACCESS read-only
            STATUS current
            DESCRIPTION
                "Shows the state of primary voltage of the power supply."
            ::= { sx801AmplifierEntry 6 }

        
        sx801AmpCommunication OBJECT-TYPE
            SYNTAX INTEGER
                {
                off(1),
                unknown(2),
                ok(3),
                fault(4)
                }
            MAX-ACCESS read-only
            STATUS current
            DESCRIPTION
                "Displays if the CAN communication between amplifier and Sx801 is working or not."
            ::= { sx801AmplifierEntry 7 }

        
        sx801AmpTransistor OBJECT-TYPE
            SYNTAX Sx801AmplifierState
            MAX-ACCESS read-only
            STATUS current
            DESCRIPTION
                "A transistor fail is displayed here.
                For further information please see the amplifiers service menue."
            ::= { sx801AmplifierEntry 8 }

        
        sx801AmpDriver OBJECT-TYPE
            SYNTAX Sx801AmplifierState
            MAX-ACCESS read-only
            STATUS current
            DESCRIPTION
                "Shows a failure if one of the internal driver transistors does not work properly.
                For further information please see the amplifiers service menue."
            ::= { sx801AmplifierEntry 9 }

        
        sx801AmpTemperature OBJECT-TYPE
            SYNTAX Sx801AmplifierState
            MAX-ACCESS read-only
            STATUS current
            DESCRIPTION
                "Shows a fault if the temperature of amplifier module is too high."
            ::= { sx801AmplifierEntry 10 }

        
        sx801AmpBlower OBJECT-TYPE
            SYNTAX Sx801AmplifierState
            MAX-ACCESS read-only
            STATUS current
            DESCRIPTION
                "Displays the state of the internal blowers."
            ::= { sx801AmplifierEntry 11 }

        
        sx801AmpRegulation OBJECT-TYPE
            SYNTAX Sx801AmplifierState
            MAX-ACCESS read-only
            STATUS current
            DESCRIPTION
                "Shows a fault if the amplifier is not able to control its output power."
            ::= { sx801AmplifierEntry 12 }

        
        sx801AmpUpdate OBJECT-TYPE
            SYNTAX TruthValue
            MAX-ACCESS read-only
            STATUS current
            DESCRIPTION
                "Firmware update is in progress.
                This will be started automatically during a software update procedure of the transmitter."
            ::= { sx801AmplifierEntry 13 }

        
        sx801Supply1Temperature OBJECT-TYPE
            SYNTAX Sx801AmplifierState
            MAX-ACCESS read-only
            STATUS current
            DESCRIPTION
                "Shows a fault if the temperature of power supply one is too high."
            ::= { sx801AmplifierEntry 14 }

        
        sx801Supply2Temperature OBJECT-TYPE
            SYNTAX Sx801AmplifierState
            MAX-ACCESS read-only
            STATUS current
            DESCRIPTION
                "Shows a fault if the temperature of power supply two is too high."
            ::= { sx801AmplifierEntry 15 }

        
        sx801SupplyRTemperature OBJECT-TYPE
            SYNTAX Sx801AmplifierState
            MAX-ACCESS read-only
            STATUS current
            DESCRIPTION
                "Shows a fault if the temperature of the reserve power supply is too high."
            ::= { sx801AmplifierEntry 16 }

        
        sx801Supply1DC OBJECT-TYPE
            SYNTAX Sx801AmplifierState
            MAX-ACCESS read-only
            STATUS current
            DESCRIPTION
                "Shows a fault if the output voltage of power supply one is not ok."
            ::= { sx801AmplifierEntry 17 }

        
        sx801Supply2DC OBJECT-TYPE
            SYNTAX Sx801AmplifierState
            MAX-ACCESS read-only
            STATUS current
            DESCRIPTION
                "Shows a fault if the output voltage of power supply two is not ok."
            ::= { sx801AmplifierEntry 18 }

        
        sx801SupplyRDC OBJECT-TYPE
            SYNTAX Sx801AmplifierState
            MAX-ACCESS read-only
            STATUS current
            DESCRIPTION
                "Shows a fault if the output voltage of the reserve power supply is not ok."
            ::= { sx801AmplifierEntry 19 }

        
        sx801AmpValueI1 OBJECT-TYPE
            SYNTAX FloatingPoint
            UNITS "Ampere"
            MAX-ACCESS read-only
            STATUS current
            DESCRIPTION
                "The internal current from transistor pair 1."
            ::= { sx801AmplifierEntry 50 }

        
        sx801AmpValueI2 OBJECT-TYPE
            SYNTAX FloatingPoint
            UNITS "Ampere"
            MAX-ACCESS read-only
            STATUS current
            DESCRIPTION
                "The internal current from transistor pair 2."
            ::= { sx801AmplifierEntry 51 }

        
        sx801AmpValueI3 OBJECT-TYPE
            SYNTAX FloatingPoint
            UNITS "Ampere"
            MAX-ACCESS read-only
            STATUS current
            DESCRIPTION
                "The internal current from transistor pair 3."
            ::= { sx801AmplifierEntry 52 }

        
        sx801AmpValueI4 OBJECT-TYPE
            SYNTAX FloatingPoint
            UNITS "Ampere"
            MAX-ACCESS read-only
            STATUS current
            DESCRIPTION
                "The internal current from transistor pair 4."
            ::= { sx801AmplifierEntry 53 }

        
        sx801AmpValueIPre OBJECT-TYPE
            SYNTAX FloatingPoint
            UNITS "Ampere"
            MAX-ACCESS read-only
            STATUS current
            DESCRIPTION
                "The internal current from preamplifier."
            ::= { sx801AmplifierEntry 54 }

        
        sx801AmpValueIDrv1 OBJECT-TYPE
            SYNTAX FloatingPoint
            UNITS "Ampere"
            MAX-ACCESS read-only
            STATUS current
            DESCRIPTION
                "The internal current from driver transistor pair 1."
            ::= { sx801AmplifierEntry 55 }

        
        sx801AmpValueIDrv2 OBJECT-TYPE
            SYNTAX FloatingPoint
            UNITS "Ampere"
            MAX-ACCESS read-only
            STATUS current
            DESCRIPTION
                "The internal current from driver transistor pair 2."
            ::= { sx801AmplifierEntry 56 }

        
        sx801AmpValuePowerOut OBJECT-TYPE
            SYNTAX FloatingPoint
            UNITS "Watt"
            MAX-ACCESS read-only
            STATUS current
            DESCRIPTION
                "The base value in Volt to calculate the output power
                of this amplifier module."
            ::= { sx801AmplifierEntry 57 }

        
        sx801AmpValueReflection OBJECT-TYPE
            SYNTAX FloatingPoint
            UNITS "Watt"
            MAX-ACCESS read-only
            STATUS current
            DESCRIPTION
                "The base value in Volt for detection of reflections."
            ::= { sx801AmplifierEntry 58 }

        
        sx801AmpValueVRef OBJECT-TYPE
            SYNTAX FloatingPoint
            UNITS "Volt"
            MAX-ACCESS read-only
            STATUS current
            DESCRIPTION
                "The internal reference voltage to set the output power."
            ::= { sx801AmplifierEntry 59 }

        
        sx801AmpValueVReg OBJECT-TYPE
            SYNTAX FloatingPoint
            UNITS "Volt"
            MAX-ACCESS read-only
            STATUS current
            DESCRIPTION
                "The internal value for output power regulation."
            ::= { sx801AmplifierEntry 60 }

        
        sx801AmpValueTemperature OBJECT-TYPE
            SYNTAX FloatingPoint
            UNITS "degree Celsius"
            MAX-ACCESS read-only
            STATUS current
            DESCRIPTION
                "The internal temperature of Amplifier.
                In case of L-band amplifier, the shown temperature is valid only,
                if the amplifier is switched on."
            ::= { sx801AmplifierEntry 61 }

        
        sx801AmpValueMonAtt OBJECT-TYPE
            SYNTAX FloatingPoint
            UNITS "dB"
            MAX-ACCESS read-only
            STATUS current
            DESCRIPTION
                "The attenuation of monitoring output on the front of the
                amplifier module (Amp RF Mon)."
            ::= { sx801AmplifierEntry 62 }

        
        sx801AmpValueVAux1 OBJECT-TYPE
            SYNTAX FloatingPoint
            UNITS "Volt"
            MAX-ACCESS read-only
            STATUS current
            DESCRIPTION
                "The voltage power detector 1."
            ::= { sx801AmplifierEntry 63 }

        
        sx801AmpValueVAux2 OBJECT-TYPE
            SYNTAX FloatingPoint
            UNITS "Volt"
            MAX-ACCESS read-only
            STATUS current
            DESCRIPTION
                "The voltage power detector 2."
            ::= { sx801AmplifierEntry 64 }

        
        sx801Supply1ValuePwr OBJECT-TYPE
            SYNTAX FloatingPoint
            UNITS "Volt"
            MAX-ACCESS read-only
            STATUS current
            DESCRIPTION
                "The power supply one control voltage."
            ::= { sx801AmplifierEntry 65 }

        
        sx801Supply2ValuePwr OBJECT-TYPE
            SYNTAX FloatingPoint
            UNITS "Volt"
            MAX-ACCESS read-only
            STATUS current
            DESCRIPTION
                "The power supply two control voltage."
            ::= { sx801AmplifierEntry 66 }

        
        sx801Supply1ValueDc OBJECT-TYPE
            SYNTAX FloatingPoint
            UNITS "Volt"
            MAX-ACCESS read-only
            STATUS current
            DESCRIPTION
                "The internal supply voltage of transistor path two.
                In systems with two power supplies this value is equal
                to the output voltage of supply one."
            ::= { sx801AmplifierEntry 67 }

        
        sx801Supply2ValueDc OBJECT-TYPE
            SYNTAX FloatingPoint
            UNITS "Volt"
            MAX-ACCESS read-only
            STATUS current
            DESCRIPTION
                "The internal supply voltage of transistor path two.
                In systems with two power supplies this value is equal
                to the output voltage of supply two."
            ::= { sx801AmplifierEntry 68 }

        
-- *****************************************************************************
-- **          event definitions
-- *****************************************************************************
        rsXx8000AtvTxEvents OBJECT IDENTIFIER ::= { rsXx8000AtvTx 3 }

        
-- *****************************************************************************
-- **          events transmitter
-- *****************************************************************************
        eventTx OBJECT IDENTIFIER ::= { rsXx8000AtvTxEvents 2 }

        
        eventsTxV2 OBJECT-IDENTITY
            STATUS current
            DESCRIPTION 
                "Compatibility to SMIv1."
            ::= { eventTx 0 }

        
        txSummaryFault NOTIFICATION-TYPE
            OBJECTS { eventAlarmPriority, eventAlarmClass, eventEvent }
            STATUS current
            DESCRIPTION 
                "Transmitter Summary Fault"
            ::= { eventsTxV2 1 }

        
        txSummaryWarning NOTIFICATION-TYPE
            OBJECTS { eventAlarmPriority, eventAlarmClass, eventEvent }
            STATUS current
            DESCRIPTION 
                "Transmitter Summary Warning"
            ::= { eventsTxV2 2 }

        
        txLocal NOTIFICATION-TYPE
            OBJECTS { eventAlarmPriority, eventAlarmClass, eventEvent }
            STATUS current
            DESCRIPTION 
                "Transmitter Local/Remote"
            ::= { eventsTxV2 3 }

        
        txRfOn NOTIFICATION-TYPE
            OBJECTS { eventAlarmPriority, eventAlarmClass, eventEvent }
            STATUS current
            DESCRIPTION 
                "Transmitter RF On/Off"
            ::= { eventsTxV2 4 }

        
        txRfOk NOTIFICATION-TYPE
            OBJECTS { eventAlarmPriority, eventAlarmClass, eventEvent }
            STATUS current
            DESCRIPTION 
                "Transmitter RF Ok / Not OK"
            ::= { eventsTxV2 5 }

        
        txParamSetSubDeviceDiffers NOTIFICATION-TYPE
            OBJECTS { eventAlarmPriority, eventAlarmClass, eventEvent }
            STATUS obsolete
            DESCRIPTION 
                "Parameterset of subdevice is different.
                The currently loaded parameterset is inconsistent because
                a subdevice (e.g. an exciter) has a different configuration than expected.
                To correct this, save settings to the current or save a complete new."
            ::= { eventsTxV2 6 }

        
        txParamSetValuesChanged NOTIFICATION-TYPE
            OBJECTS { eventAlarmPriority, eventAlarmClass, eventEvent }
            STATUS current
            DESCRIPTION 
                "Value Of Current Parameterset Changed.
                The currently loaded parameterset is inconsistent because
                there were changes happening since the load/save of it.
                To correct this, save settings to the current or save a complete new."
            ::= { eventsTxV2 7 }

        
        txRfLoopProgram NOTIFICATION-TYPE
            OBJECTS { eventAlarmPriority, eventAlarmClass, eventEvent }
            STATUS current
            DESCRIPTION 
                "NetCCU Loop Program"
            ::= { eventsTxV2 8 }

        
        txRfLoopReserve NOTIFICATION-TYPE
            OBJECTS { eventAlarmPriority, eventAlarmClass, eventEvent }
            STATUS current
            DESCRIPTION 
                "NetCCU Loop Reserve"
            ::= { eventsTxV2 9 }

        
        txRfWarning NOTIFICATION-TYPE
            OBJECTS { eventAlarmPriority, eventAlarmClass, eventEvent }
            STATUS current
            DESCRIPTION 
                "NetCCU RF Warning"
            ::= { eventsTxV2 10 }

        
        txReflectionWarning NOTIFICATION-TYPE
            OBJECTS { eventAlarmPriority, eventAlarmClass, eventEvent }
            STATUS current
            DESCRIPTION 
                "NetCCU Reflection Warning"
            ::= { eventsTxV2 11 }

        
        txNetCCUFanFault NOTIFICATION-TYPE
            OBJECTS { eventAlarmPriority, eventAlarmClass, eventEvent }
            STATUS current
            DESCRIPTION 
                "NetCCU Fan Fault.
                This is valid, if Fan Control is switched on (see menu NetCCU Setup - Common)."
            ::= { eventsTxV2 12 }

        
        txNetCCUPowerSupply NOTIFICATION-TYPE
            OBJECTS { eventAlarmPriority, eventAlarmClass, eventEvent }
            STATUS current
            DESCRIPTION 
                "NetCCU Power Supply fault"
            ::= { eventsTxV2 13 }

        
        txRfFail NOTIFICATION-TYPE
            OBJECTS { eventAlarmPriority, eventAlarmClass, eventEvent }
            STATUS current
            DESCRIPTION 
                "NetCCU RF Fail"
            ::= { eventsTxV2 14 }

        
        txReflectionFault NOTIFICATION-TYPE
            OBJECTS { eventAlarmPriority, eventAlarmClass, eventEvent }
            STATUS current
            DESCRIPTION 
                "NetCCU Reflection Fault"
            ::= { eventsTxV2 15 }

        
        txNetCCUBoardTemperatureFault NOTIFICATION-TYPE
            OBJECTS { eventAlarmPriority, eventAlarmClass, eventEvent }
            STATUS deprecated
            DESCRIPTION 
                "NetCCU Board Temperature Fault
                
                deprecated: this information is now handled as a warning
                (txNetCCUBoardTemperatureWarning)"
            ::= { eventsTxV2 16 }

        
        txNetCCUNoConnectionToExcA NOTIFICATION-TYPE
            OBJECTS { eventAlarmPriority, eventAlarmClass, eventEvent }
            STATUS current
            DESCRIPTION 
                "NetCCU Connection To ExciterA Faulty"
            ::= { eventsTxV2 17 }

        
        txNetCCUNoConnectionToOstA NOTIFICATION-TYPE
            OBJECTS { eventAlarmPriority, eventAlarmClass, eventEvent }
            STATUS current
            DESCRIPTION 
                "NetCCU Connection To OutputstageA Faulty"
            ::= { eventsTxV2 18 }

        
        txNetCCUNoConnectionToExcB NOTIFICATION-TYPE
            OBJECTS { eventAlarmPriority, eventAlarmClass, eventEvent }
            STATUS current
            DESCRIPTION 
                "NetCCU Connection To ExciterB Faulty"
            ::= { eventsTxV2 19 }

        
        txNetCCUNoConnectionToOstB NOTIFICATION-TYPE
            OBJECTS { eventAlarmPriority, eventAlarmClass, eventEvent }
            STATUS current
            DESCRIPTION 
                "NetCCU Connection To OutputstageB Faulty"
            ::= { eventsTxV2 20 }

        
        txAutomaticExcReady NOTIFICATION-TYPE
            OBJECTS { eventAlarmPriority, eventAlarmClass, eventEvent }
            STATUS current
            DESCRIPTION 
                "Exciter Automatic Ready."
            ::= { eventsTxV2 21 }

        
        txAutomaticExcChanged NOTIFICATION-TYPE
            OBJECTS { eventAlarmPriority, eventAlarmClass, eventEvent }
            STATUS current
            DESCRIPTION 
                "Exciter Automatic Changed."
            ::= { eventsTxV2 22 }

        
        txAutomaticExcFault NOTIFICATION-TYPE
            OBJECTS { eventAlarmPriority, eventAlarmClass, eventEvent }
            STATUS current
            DESCRIPTION 
                "Exciter Automatic Fault."
            ::= { eventsTxV2 23 }

        
        txAutomaticOstReady NOTIFICATION-TYPE
            OBJECTS { eventAlarmPriority, eventAlarmClass, eventEvent }
            STATUS current
            DESCRIPTION 
                "Outputstage Automatic Ready.
                
                This paramter is only available for systems with an automatic output switch."
            ::= { eventsTxV2 24 }

        
        txAutomaticOstChanged NOTIFICATION-TYPE
            OBJECTS { eventAlarmPriority, eventAlarmClass, eventEvent }
            STATUS current
            DESCRIPTION 
                "Outputstage Automatic Changed.
                
                This paramter is only available for systems with an automatic output switch."
            ::= { eventsTxV2 25 }

        
        txAutomaticOstFault NOTIFICATION-TYPE
            OBJECTS { eventAlarmPriority, eventAlarmClass, eventEvent }
            STATUS current
            DESCRIPTION 
                "Outputstage Automatic Fault.
                
                This paramter is only available for systems with an automatic output switch."
            ::= { eventsTxV2 26 }

        
        txNetCCUBoardTemperatureWarning NOTIFICATION-TYPE
            OBJECTS { eventAlarmPriority, eventAlarmClass, eventEvent }
            STATUS current
            DESCRIPTION 
                "NetCCU Board Temperature Warning"
            ::= { eventsTxV2 27 }

        
        txInternalPowerSupplyWarning NOTIFICATION-TYPE
            OBJECTS { eventAlarmPriority, eventAlarmClass, eventEvent }
            STATUS current
            DESCRIPTION 
                "NetCCU internal Power Supply warning"
            ::= { eventsTxV2 30 }

        
        txExternalPowerSupplyWarning NOTIFICATION-TYPE
            OBJECTS { eventAlarmPriority, eventAlarmClass, eventEvent }
            STATUS current
            DESCRIPTION 
                "NetCCU external (additional) Power Supply warning"
            ::= { eventsTxV2 31 }

        
        txModeSwitchOverStarted NOTIFICATION-TYPE
            OBJECTS { eventAlarmPriority, eventAlarmClass, eventEvent }
            STATUS current
            DESCRIPTION 
                "Switch over of TX mode started."
            ::= { eventsTxV2 35 }

        
        txModeSwitchOverEnded NOTIFICATION-TYPE
            OBJECTS { eventAlarmPriority, eventAlarmClass, eventEvent }
            STATUS current
            DESCRIPTION 
                "Switch over of TX mode ended."
            ::= { eventsTxV2 36 }

        
        txModeInconsistent NOTIFICATION-TYPE
            OBJECTS { eventAlarmPriority, eventAlarmClass, eventEvent }
            STATUS current
            DESCRIPTION 
                "An inconsistency in configuration of TX mode was detected.
                The CCU and exiter configurations are incompatible."
            ::= { eventsTxV2 37 }

        
        txModeSwitchOverFailed NOTIFICATION-TYPE
            OBJECTS { eventAlarmPriority, eventAlarmClass, eventEvent }
            STATUS current
            DESCRIPTION 
                "Switch over of TX mode failed.
                Please check whether the configurations of CCU and exciter are correct."
            ::= { eventsTxV2 38 }

        
        txExcSummaryFault NOTIFICATION-TYPE
            OBJECTS { eventAlarmPriority, eventAlarmClass, eventEvent, indexAB }
            STATUS current
            DESCRIPTION 
                "Exciter Summary Fault"
            ::= { eventsTxV2 100 }

        
        txExcSummaryWarning NOTIFICATION-TYPE
            OBJECTS { eventAlarmPriority, eventAlarmClass, eventEvent, indexAB }
            STATUS current
            DESCRIPTION 
                "Exciter Summary Warning"
            ::= { eventsTxV2 101 }

        
        txExcLocal NOTIFICATION-TYPE
            OBJECTS { eventAlarmPriority, eventAlarmClass, eventEvent, indexAB }
            STATUS current
            DESCRIPTION 
                "Exciter Local/Remote"
            ::= { eventsTxV2 102 }

        
        txExcOn NOTIFICATION-TYPE
            OBJECTS { eventAlarmPriority, eventAlarmClass, eventEvent, indexAB }
            STATUS current
            DESCRIPTION 
                "Exciter On"
            ::= { eventsTxV2 113 }

        
        txExcRfOn NOTIFICATION-TYPE
            OBJECTS { eventAlarmPriority, eventAlarmClass, eventEvent, indexAB }
            STATUS current
            DESCRIPTION 
                "Exciter RF On"
            ::= { eventsTxV2 114 }

        
        txExcNoInput NOTIFICATION-TYPE
            OBJECTS { eventAlarmPriority, eventAlarmClass, eventEvent, indexAB }
            STATUS current
            DESCRIPTION 
                "Exciter has no valid input signal."
            ::= { eventsTxV2 115 }

        
        txExcRfLoop NOTIFICATION-TYPE
            OBJECTS { eventAlarmPriority, eventAlarmClass, eventEvent, indexAB }
            STATUS current
            DESCRIPTION 
                "Exciter RF loop"
            ::= { eventsTxV2 116 }

        
        txExcSelfTest NOTIFICATION-TYPE
            OBJECTS { eventAlarmPriority, eventAlarmClass, eventEvent, indexAB }
            STATUS current
            DESCRIPTION 
                "Exciter hardware self test"
            ::= { eventsTxV2 118 }

        
        txExcOutputOpen NOTIFICATION-TYPE
            OBJECTS { eventAlarmPriority, eventAlarmClass, eventEvent, indexAB }
            STATUS current
            DESCRIPTION 
                "Exciter output open"
            ::= { eventsTxV2 119 }

        
        txExcBoardTemperatureWarning NOTIFICATION-TYPE
            OBJECTS { eventAlarmPriority, eventAlarmClass, eventEvent, indexAB }
            STATUS current
            DESCRIPTION 
                "Exciter Board Temperature"
            ::= { eventsTxV2 120 }

        
        txExcFanWarning NOTIFICATION-TYPE
            OBJECTS { eventAlarmPriority, eventAlarmClass, eventEvent, indexAB }
            STATUS current
            DESCRIPTION 
                "Exciter has one faulty fan"
            ::= { eventsTxV2 121 }

        
        txExcFanFault NOTIFICATION-TYPE
            OBJECTS { eventAlarmPriority, eventAlarmClass, eventEvent, indexAB }
            STATUS current
            DESCRIPTION 
                "Both exciter fans are faulty."
            ::= { eventsTxV2 122 }

        
        txExcTestSignal NOTIFICATION-TYPE
            OBJECTS { eventAlarmPriority, eventAlarmClass, eventEvent, indexAB }
            STATUS current
            DESCRIPTION 
                "Exciter Testsignal Active"
            ::= { eventsTxV2 124 }

        
        txOstSummaryFault NOTIFICATION-TYPE
            OBJECTS { eventAlarmPriority, eventAlarmClass, eventEvent, indexAB }
            STATUS current
            DESCRIPTION 
                "Outputstage Summary Fault"
            ::= { eventsTxV2 200 }

        
        txOstSummaryWarning NOTIFICATION-TYPE
            OBJECTS { eventAlarmPriority, eventAlarmClass, eventEvent, indexAB }
            STATUS current
            DESCRIPTION 
                "Outputstage Summary Warning"
            ::= { eventsTxV2 201 }

        
        txOstRfOn NOTIFICATION-TYPE
            OBJECTS { eventAlarmPriority, eventAlarmClass, eventEvent, indexAB }
            STATUS current
            DESCRIPTION 
                "Outputstage RF On"
            ::= { eventsTxV2 202 }

        
        txOstRfOk NOTIFICATION-TYPE
            OBJECTS { eventAlarmPriority, eventAlarmClass, eventEvent, indexAB }
            STATUS current
            DESCRIPTION 
                "Outputstage RF Ok"
            ::= { eventsTxV2 203 }

        
        txOstNoInput NOTIFICATION-TYPE
            OBJECTS { eventAlarmPriority, eventAlarmClass, eventEvent, indexAB }
            STATUS current
            DESCRIPTION 
                "Outputstage no input signal"
            ::= { eventsTxV2 204 }

        
        txOstRfWarning NOTIFICATION-TYPE
            OBJECTS { eventAlarmPriority, eventAlarmClass, eventEvent, indexAB }
            STATUS current
            DESCRIPTION 
                "Outputstage RF Warning"
            ::= { eventsTxV2 205 }

        
        txOstReflectionWarning NOTIFICATION-TYPE
            OBJECTS { eventAlarmPriority, eventAlarmClass, eventEvent, indexAB }
            STATUS current
            DESCRIPTION 
                "Outputstage Reflection Warning"
            ::= { eventsTxV2 206 }

        
        txOstRackWarning NOTIFICATION-TYPE
            OBJECTS { eventAlarmPriority, eventAlarmClass, eventEvent, indexAB }
            STATUS current
            DESCRIPTION 
                "Outputstage Rack Warning. At least one rack has an error pending."
            ::= { eventsTxV2 207 }

        
        txOstCoolingWarning NOTIFICATION-TYPE
            OBJECTS { eventAlarmPriority, eventAlarmClass, eventEvent, indexAB }
            STATUS current
            DESCRIPTION 
                "Outputstage Cooling Warning"
            ::= { eventsTxV2 208 }

        
        txOstRfFail NOTIFICATION-TYPE
            OBJECTS { eventAlarmPriority, eventAlarmClass, eventEvent, indexAB }
            STATUS current
            DESCRIPTION 
                "Outputstage RF Fail"
            ::= { eventsTxV2 209 }

        
        txOstReflectionFault NOTIFICATION-TYPE
            OBJECTS { eventAlarmPriority, eventAlarmClass, eventEvent, indexAB }
            STATUS current
            DESCRIPTION 
                "Outputstage Reflection Fault"
            ::= { eventsTxV2 210 }

        
        txOstACFault NOTIFICATION-TYPE
            OBJECTS { eventAlarmPriority, eventAlarmClass, eventEvent, indexAB }
            STATUS current
            DESCRIPTION 
                "Outputstage AC Fault"
            ::= { eventsTxV2 211 }

        
        txOstCoolingFault NOTIFICATION-TYPE
            OBJECTS { eventAlarmPriority, eventAlarmClass, eventEvent, indexAB }
            STATUS current
            DESCRIPTION 
                "Outputstage Cooling Fault"
            ::= { eventsTxV2 212 }

        
        txOstCommFault NOTIFICATION-TYPE
            OBJECTS { eventAlarmPriority, eventAlarmClass, eventEvent, indexAB }
            STATUS current
            DESCRIPTION 
                "Outputstage Communication Fault"
            ::= { eventsTxV2 213 }

        
        txRackSumFault NOTIFICATION-TYPE
            OBJECTS { eventAlarmPriority, eventAlarmClass, eventEvent, indexAB, indexRack
                 }
            STATUS current
            DESCRIPTION 
                "Summary Fault at a designated rack.
                This event automatically leads to txOstRackWarning."
            ::= { eventsTxV2 300 }

        
        txRackSumWarning NOTIFICATION-TYPE
            OBJECTS { eventAlarmPriority, eventAlarmClass, eventEvent, indexAB, indexRack
                 }
            STATUS current
            DESCRIPTION 
                "Summary Warning at a designated rack."
            ::= { eventsTxV2 301 }

        
        txRackOn NOTIFICATION-TYPE
            OBJECTS { eventAlarmPriority, eventAlarmClass, eventEvent, indexAB, indexRack
                 }
            STATUS current
            DESCRIPTION 
                "The designated racks operation mode is on."
            ::= { eventsTxV2 302 }

        
        txRackGpiWarning NOTIFICATION-TYPE
            OBJECTS { eventAlarmPriority, eventAlarmClass, eventEvent, indexAB, indexRack
                 }
            STATUS current
            DESCRIPTION 
                "A warning on the general purpose input occurred.
                This depends on the current configuration of the GPI. (See:Rack Setup/Rack Controller)"
            ::= { eventsTxV2 303 }

        
        txRackFan1Fault NOTIFICATION-TYPE
            OBJECTS { eventAlarmPriority, eventAlarmClass, eventEvent, indexAB, indexRack
                 }
            STATUS current
            DESCRIPTION 
                "The designated rack signals a fault of fan 1."
            ::= { eventsTxV2 304 }

        
        txRackFan2Fault NOTIFICATION-TYPE
            OBJECTS { eventAlarmPriority, eventAlarmClass, eventEvent, indexAB, indexRack
                 }
            STATUS current
            DESCRIPTION 
                "The designated rack signals a fault of fan 2."
            ::= { eventsTxV2 305 }

        
        txRackCoolingSumWarning NOTIFICATION-TYPE
            OBJECTS { eventAlarmPriority, eventAlarmClass, eventEvent, indexAB, indexRack
                 }
            STATUS current
            DESCRIPTION 
                "The designated rack signals a summary cooling warning."
            ::= { eventsTxV2 306 }

        
        txRackAmplifierSumFault NOTIFICATION-TYPE
            OBJECTS { eventAlarmPriority, eventAlarmClass, eventEvent, indexAB, indexRack
                 }
            STATUS current
            DESCRIPTION 
                "The designated rack signals at least one faulty amplifier."
            ::= { eventsTxV2 307 }

        
        txRackNoLink NOTIFICATION-TYPE
            OBJECTS { eventAlarmPriority, eventAlarmClass, eventEvent, indexAB, indexRack
                 }
            STATUS current
            DESCRIPTION 
                "No communication to the designated rack."
            ::= { eventsTxV2 308 }

        
        txRackGpiFault NOTIFICATION-TYPE
            OBJECTS { eventAlarmPriority, eventAlarmClass, eventEvent, indexAB, indexRack
                 }
            STATUS current
            DESCRIPTION 
                "A fault on the general purpose input occurred.
                This depends on the current configuration of the GPI. (See:Rack Setup/Rack Controller)"
            ::= { eventsTxV2 309 }

        
        txRackTemperatureFault NOTIFICATION-TYPE
            OBJECTS { eventAlarmPriority, eventAlarmClass, eventEvent, indexAB, indexRack
                 }
            STATUS current
            DESCRIPTION 
                "The designated rack signals a temperature fault - temperature too high."
            ::= { eventsTxV2 310 }

        
        txRackACFault NOTIFICATION-TYPE
            OBJECTS { eventAlarmPriority, eventAlarmClass, eventEvent, indexAB, indexRack
                 }
            STATUS current
            DESCRIPTION 
                "The designated rack signals an AC (phase) fault."
            ::= { eventsTxV2 311 }

        
        txRackCoolingSumFault NOTIFICATION-TYPE
            OBJECTS { eventAlarmPriority, eventAlarmClass, eventEvent, indexAB, indexRack
                 }
            STATUS current
            DESCRIPTION 
                "The designated rack signals a summary cooling fault."
            ::= { eventsTxV2 312 }

        
        txRackTempFaultAbs1 NOTIFICATION-TYPE
            OBJECTS { eventAlarmPriority, eventAlarmClass, eventEvent, indexAB, indexRack
                 }
            STATUS current
            DESCRIPTION 
                "The designated rack signals a temperature fault of absorber 1."
            ::= { eventsTxV2 313 }

        
        txRackTempFaultAbs2 NOTIFICATION-TYPE
            OBJECTS { eventAlarmPriority, eventAlarmClass, eventEvent, indexAB, indexRack
                 }
            STATUS current
            DESCRIPTION 
                "The designated rack signals a temperature fault of absorber 2."
            ::= { eventsTxV2 314 }

        
        txRackDCFault NOTIFICATION-TYPE
            OBJECTS { eventAlarmPriority, eventAlarmClass, eventEvent, indexAB, indexRack
                 }
            STATUS current
            DESCRIPTION 
                "The designated rack signals a DC fault."
            ::= { eventsTxV2 315 }

        
        txRackRfOn NOTIFICATION-TYPE
            OBJECTS { eventAlarmPriority, eventAlarmClass, eventEvent, indexAB, indexRack
                 }
            STATUS current
            DESCRIPTION 
                "RF power is on."
            ::= { eventsTxV2 318 }

        
        txRackRfOk NOTIFICATION-TYPE
            OBJECTS { eventAlarmPriority, eventAlarmClass, eventEvent, indexAB, indexRack
                 }
            STATUS current
            DESCRIPTION 
                "RF power is ok."
            ::= { eventsTxV2 319 }

        
        txRackRfWarning NOTIFICATION-TYPE
            OBJECTS { eventAlarmPriority, eventAlarmClass, eventEvent, indexAB, indexRack
                 }
            STATUS current
            DESCRIPTION 
                "RF power falls below the warning threshold."
            ::= { eventsTxV2 320 }

        
        txRackRfFault NOTIFICATION-TYPE
            OBJECTS { eventAlarmPriority, eventAlarmClass, eventEvent, indexAB, indexRack
                 }
            STATUS current
            DESCRIPTION 
                "RF output power falls below the fault threshold."
            ::= { eventsTxV2 321 }

        
        txRackReflectionWarning NOTIFICATION-TYPE
            OBJECTS { eventAlarmPriority, eventAlarmClass, eventEvent, indexAB, indexRack
                 }
            STATUS current
            DESCRIPTION 
                "The reflected power exceeded the warning threshold"
            ::= { eventsTxV2 322 }

        
        txRackReflectionFault NOTIFICATION-TYPE
            OBJECTS { eventAlarmPriority, eventAlarmClass, eventEvent, indexAB, indexRack
                 }
            STATUS current
            DESCRIPTION 
                "The reflected power exceeded the fault threshold."
            ::= { eventsTxV2 323 }

        
        txRackProbeNotCalibrated NOTIFICATION-TYPE
            OBJECTS { eventAlarmPriority, eventAlarmClass, eventEvent, indexAB, indexRack
                 }
            STATUS current
            DESCRIPTION 
                "At least one probe is not calibrated."
            ::= { eventsTxV2 330 }

        
        txRackTemperatureWarning NOTIFICATION-TYPE
            OBJECTS { eventAlarmPriority, eventAlarmClass, eventEvent, indexAB, indexRack
                 }
            STATUS current
            DESCRIPTION 
                "Rack temperature exceeded the warning threshold."
            ::= { eventsTxV2 331 }

        
        txRackOvervoltProtectWarning NOTIFICATION-TYPE
            OBJECTS { eventAlarmPriority, eventAlarmClass, eventEvent, indexAB, indexRack
                 }
            STATUS current
            DESCRIPTION 
                "Overvoltage protection is out of order."
            ::= { eventsTxV2 335 }

        
        txAmpSumFault NOTIFICATION-TYPE
            OBJECTS { eventAlarmPriority, eventAlarmClass, eventEvent, indexAB, indexRack, 
                indexAmplifier }
            STATUS current
            DESCRIPTION 
                "The designated amplifier signals summary fault."
            ::= { eventsTxV2 400 }

        
        txAmpSumWarning NOTIFICATION-TYPE
            OBJECTS { eventAlarmPriority, eventAlarmClass, eventEvent, indexAB, indexRack, 
                indexAmplifier }
            STATUS current
            DESCRIPTION 
                "The designated amplifier signals summary warning."
            ::= { eventsTxV2 401 }

        
        txAmpPowerOn NOTIFICATION-TYPE
            OBJECTS { eventAlarmPriority, eventAlarmClass, eventEvent, indexAB, indexRack, 
                indexAmplifier }
            STATUS current
            DESCRIPTION 
                "The designated amplifiers power is on."
            ::= { eventsTxV2 402 }

        
        txAmpDCOk NOTIFICATION-TYPE
            OBJECTS { eventAlarmPriority, eventAlarmClass, eventEvent, indexAB, indexRack, 
                indexAmplifier }
            STATUS current
            DESCRIPTION 
                "The designated amplifiers DC is ok."
            ::= { eventsTxV2 403 }

        
        txAmpACOk NOTIFICATION-TYPE
            OBJECTS { eventAlarmPriority, eventAlarmClass, eventEvent, indexAB, indexRack, 
                indexAmplifier }
            STATUS current
            DESCRIPTION 
                "The designated amplifiers AC is ok."
            ::= { eventsTxV2 404 }

        
        txAmpRfInFail NOTIFICATION-TYPE
            OBJECTS { eventAlarmPriority, eventAlarmClass, eventEvent, indexAB, indexRack, 
                indexAmplifier }
            STATUS current
            DESCRIPTION 
                "The designated amplifier signals RF input fail."
            ::= { eventsTxV2 405 }

        
        txAmpRfFail NOTIFICATION-TYPE
            OBJECTS { eventAlarmPriority, eventAlarmClass, eventEvent, indexAB, indexRack, 
                indexAmplifier }
            STATUS current
            DESCRIPTION 
                "The designated amplifier signals RF fail."
            ::= { eventsTxV2 406 }

        
        txAmpReflectionFault NOTIFICATION-TYPE
            OBJECTS { eventAlarmPriority, eventAlarmClass, eventEvent, indexAB, indexRack, 
                indexAmplifier }
            STATUS current
            DESCRIPTION 
                "The designated amplifier signals a reflection fault."
            ::= { eventsTxV2 407 }

        
        txAmpTemperatureFault NOTIFICATION-TYPE
            OBJECTS { eventAlarmPriority, eventAlarmClass, eventEvent, indexAB, indexRack, 
                indexAmplifier }
            STATUS current
            DESCRIPTION 
                "The designated amplifier signals a temperature fault - temperature is too high."
            ::= { eventsTxV2 408 }

        
        txAmpTransistorFault NOTIFICATION-TYPE
            OBJECTS { eventAlarmPriority, eventAlarmClass, eventEvent, indexAB, indexRack, 
                indexAmplifier }
            STATUS current
            DESCRIPTION 
                "The designated amplifier signals at least one faulty transistor."
            ::= { eventsTxV2 409 }

        
        eventsTxTable OBJECT-TYPE
            SYNTAX SEQUENCE OF EventsTxEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventTx 1 }

        
        eventsTxEntry OBJECT-TYPE
            SYNTAX EventsTxEntry
            MAX-ACCESS not-accessible
            STATUS current
            DESCRIPTION
                "An event entry always consists of its indexes
                (used for addressing within redundancy systems) and 3 values:
                - name: an enumerated list of all possible notifications
                - mask: the corresponding mask (enable/disable)
                - priority: the corresponding priority (value in range 0..255)
                - event: the event itself (active/inactive)"
            INDEX { eventTxABIdx, eventTxRackIdx, eventTxAmpIdx, eventTxNameIdx }
            ::= { eventsTxTable 1 }

        
        EventsTxEntry ::=
            SEQUENCE { 
                eventTxABIdx
                    INTEGER,
                eventTxRackIdx
                    Integer32,
                eventTxAmpIdx
                    Integer32,
                eventTxNameIdx
                    EventMaxEntryNumber,
                eventTxName
                    INTEGER,
                eventTxMask
                    EventMask,
                eventTxPriority
                    EventPriority,
                eventTxEvent
                    EventState
             }

        eventTxABIdx OBJECT-TYPE
            SYNTAX INTEGER
                {
                a(1),
                b(2)
                }
            MAX-ACCESS not-accessible
            STATUS current
            DESCRIPTION
                "The value for the module A (exciterA, outputstageA) or 
                B (exciterB, outputstageB) for alarms.
                This is a helper column and therefore not-accessible."
            ::= { eventsTxEntry 1 }

        
        eventTxRackIdx OBJECT-TYPE
            SYNTAX Integer32 (1..10)
            MAX-ACCESS not-accessible
            STATUS current
            DESCRIPTION
                "The number of the designated rack.
                This is a helper column and therefore not-accessible."
            ::= { eventsTxEntry 2 }

        
        eventTxAmpIdx OBJECT-TYPE
            SYNTAX Integer32 (1..10)
            MAX-ACCESS not-accessible
            STATUS current
            DESCRIPTION
                "The number of the designated amplifier.
                This is a helper column and therefore not-accessible."
            ::= { eventsTxEntry 3 }

        
        eventTxNameIdx OBJECT-TYPE
            SYNTAX EventMaxEntryNumber
            MAX-ACCESS not-accessible
            STATUS current
            DESCRIPTION
                "The event number as integer.
                This is a helper column and therefore not-accessible."
            ::= { eventsTxEntry 4 }

        
        eventTxName OBJECT-TYPE
            SYNTAX INTEGER
                {
                txSummaryFault(1),
                txSummaryWarning(2),
                txLocal(3),
                txRfOn(4),
                txRfOk(5),
                txParamSetSubDeviceDiffers(6),
                txParamSetValuesChanged(7),
                txRfLoopProgram(8),
                txRfLoopReserve(9),
                txRfWarning(10),
                txReflectionWarning(11),
                txNetCCUFanFault(12),
                txNetCCUPowerSupply(13),
                txRfFail(14),
                txReflectionFault(15),
                txNetCCUBoardTemperatureFault(16),
                txNetCCUNoConnectionToExcA(17),
                txNetCCUNoConnectionToOstA(18),
                txNetCCUNoConnectionToExcB(19),
                txNetCCUNoConnectionToOstB(20),
                txAutomaticExcReady(21),
                txAutomaticExcChanged(22),
                txAutomaticExcFault(23),
                txAutomaticOstReady(24),
                txAutomaticOstChanged(25),
                txAutomaticOstFault(26),
                txNetCCUBoardTemperatureWarning(27),
                txInternalPowerSupplyWarning(30),
                txExternalPowerSupplyWarning(31),
                txModeSwitchOverStarted(35),
                txModeSwitchOverEnded(36),
                txModeInconsistent(37),
                txModeSwitchOverFailed(38),
                txExcSummaryFault(100),
                txExcSummaryWarning(101),
                txExcLocal(102),
                txExcOn(113),
                txExcRfOn(114),
                txExcNoInput(115),
                txExcRfLoop(116),
                txExcSelfTest(118),
                txExcOutputOpen(119),
                txExcBoardTemperatureWarning(120),
                txExcFanWarning(121),
                txExcFanFault(122),
                txExcTestSignal(124),
                txOstSummaryFault(200),
                txOstSummaryWarning(201),
                txOstRfOn(202),
                txOstRfOk(203),
                txOstNoInput(204),
                txOstRfWarning(205),
                txOstReflectionWarning(206),
                txOstRackWarning(207),
                txOstCoolingWarning(208),
                txOstRfFail(209),
                txOstReflectionFault(210),
                txOstACFault(211),
                txOstCoolingFault(212),
                txOstCommFault(213),
                txRackSumFault(300),
                txRackSumWarning(301),
                txRackOn(302),
                txRackGpiWarning(303),
                txRackFan1Fault(304),
                txRackFan2Fault(305),
                txRackCoolingSumWarning(306),
                txRackAmplifierSumFault(307),
                txRackNoLink(308),
                txRackGpiFault(309),
                txRackTemperatureFault(310),
                txRackACFault(311),
                txRackCoolingSumFault(312),
                txRackTempFaultAbs1(313),
                txRackTempFaultAbs2(314),
                txRackDCFault(315),
                txRackRfOn(318),
                txRackRfOk(319),
                txRackRfWarning(320),
                txRackRfFault(321),
                txRackReflectionWarning(322),
                txRackReflectionFault(323),
                txRackProbeNotCalibrated(330),
                txRackTemperatureWarning(331),
                txRackOvervoltProtectWarning(335),
                txAmpSumFault(400),
                txAmpSumWarning(401),
                txAmpPowerOn(402),
                txAmpDCOk(403),
                txAmpACOk(404),
                txAmpRfInFail(405),
                txAmpRfFail(406),
                txAmpReflectionFault(407),
                txAmpTemperatureFault(408),
                txAmpTransistorFault(409)
                }
            MAX-ACCESS read-only
            STATUS current
            DESCRIPTION
                "The event number as integer and the value as readable text.
                The enumeration correlates with the notifications under eventsTxV2."
            ::= { eventsTxEntry 5 }

        
        eventTxMask OBJECT-TYPE
            SYNTAX EventMask
            MAX-ACCESS read-write
            STATUS current
            DESCRIPTION
                "See TextualConvention for details."
            ::= { eventsTxEntry 6 }

        
        eventTxPriority OBJECT-TYPE
            SYNTAX EventPriority
            MAX-ACCESS read-write
            STATUS current
            DESCRIPTION
                "See TextualConvention for details."
            ::= { eventsTxEntry 7 }

        
        eventTxEvent OBJECT-TYPE
            SYNTAX EventState
            MAX-ACCESS read-only
            STATUS current
            DESCRIPTION
                "See TextualConvention for details."
            ::= { eventsTxEntry 8 }

        
-- *****************************************************************************
-- **          conformance statements
-- *****************************************************************************
        rsXx8000AtvTxConf OBJECT IDENTIFIER ::= { rsXx8000AtvTx 5 }

        
        rsXx8000AtvTxGroups OBJECT IDENTIFIER ::= { rsXx8000AtvTxConf 1 }

        
        groupEvents OBJECT-GROUP
            OBJECTS { eventTxName, eventTxMask, eventTxPriority, eventTxEvent }
            STATUS current
            DESCRIPTION 
                "This group includes all OIDs for event handling."
            ::= { rsXx8000AtvTxGroups 1 }

        
        groupSingleTxMP OBJECT-GROUP
            OBJECTS { cmdTxResetSumFault, cmdTxParametersetLoad, cmdTxParametersetSave, cmdTxOperationModeProgram, cmdOstRefVoltageVision, 
                cmdOstMaxOutletTempThreshold, netCCUNumberOfEntries, netCCULogbookClear, netCCULogbookEntryNbr, netCCULogbookType, 
                netCCULogbookSlope, netCCULogbookMessage, netCCULogbookDateTime, outputstageANumberOfEntries, outputstageALogbookClear, 
                ostALogbookEntryNbr, ostALogbookType, ostALogbookSlope, ostALogbookMessage, exciterANumberOfEntries, 
                exciterALogbookClear, excALogbookEntryNbr, excALogbookType, excALogbookSlope, excALogbookMessage, 
                excALogbookDateTime, additionalPowerSupply, powerSupply, cmdTxSystemMode, ostALogbookDateTime, 
                summaryFaultTx, summaryWarningTx, localModeTx, rfOnTx, forwardPower, 
                reflectedPower, summaryFaultExcA, summaryFaultOstA, noConnectionExcA, noConnectionOstA, 
                ostRackInletTemperature, ostRackOutletTemperature, ostRackAuxPowerSupply, amplifiersPerRack, rackRfEventSignalling, 
                rackGeneralPurposeInput, rfProbePresent, rfProbeConfigurationNominalValue, rfProbeThresholdRfFailLimit, rfProbeThresholdTimeoutRfFailCtr, 
                rfProbeThresholdWarningLimit, rfProbeCalibrationGain, rfProbeCalibrationOffset, rfProbeCalibrationSetGain, rfProbeCalibrationSetOffset, 
                rfProbeMeasuredValue }
            STATUS current
            DESCRIPTION 
                "This group includes all OIDs for reserve concept
                SingleTransmitter (NetCCU + exciter + outputstage)
                in case of MediumPower."
            ::= { rsXx8000AtvTxGroups 2 }

        
        groupAlarmSingleTxMP NOTIFICATION-GROUP
            NOTIFICATIONS { txSummaryFault, txSummaryWarning, txLocal, txRfOn, txRfOk, 
                txParamSetValuesChanged, txRfLoopProgram, txRfWarning, txReflectionWarning, txNetCCUFanFault, 
                txNetCCUPowerSupply, txRfFail, txReflectionFault, txNetCCUNoConnectionToExcA, txNetCCUNoConnectionToOstA, 
                txOstSummaryFault, txOstSummaryWarning, txOstRfOn, txOstRfOk, txOstNoInput, 
                txOstRfWarning, txOstReflectionWarning, txOstRackWarning, txOstCoolingWarning, txOstRfFail, 
                txOstReflectionFault, txOstACFault, txOstCoolingFault, txOstCommFault, txRackSumFault, 
                txRackSumWarning, txRackOn, txRackGpiWarning, txRackFan1Fault, txRackFan2Fault, 
                txRackCoolingSumWarning, txRackAmplifierSumFault, txRackNoLink, txRackGpiFault, txRackTemperatureFault, 
                txRackACFault, txRackCoolingSumFault, txRackTempFaultAbs1, txRackTempFaultAbs2, txRackDCFault, 
                txRackRfWarning, txRackRfFault, txRackReflectionWarning, txRackReflectionFault, txExcSummaryFault, 
                txExcSummaryWarning, txExcOn, txExcNoInput, txExcOutputOpen, txExcRfLoop, 
                txExcBoardTemperatureWarning, txExcTestSignal, txExcFanWarning, txExcRfOn, txRackProbeNotCalibrated, 
                txRackRfOk, txRackRfOn, txExcLocal, txModeSwitchOverFailed, txModeInconsistent, 
                txModeSwitchOverEnded, txModeSwitchOverStarted, txRackOvervoltProtectWarning, txExcFanFault, txNetCCUBoardTemperatureWarning, 
                txExcSelfTest, txRackTemperatureWarning }
            STATUS current
            DESCRIPTION 
                "This group includes all alarm OIDs for reserve concept
                SingleTransmitter (NetCCU + exciter + outputstage)
                in case of MediumPower."
            ::= { rsXx8000AtvTxGroups 3 }

        
        groupDualDriveMP OBJECT-GROUP
            OBJECTS { cmdTxResetSumFault, cmdTxParametersetLoad, cmdTxParametersetSave, cmdTxOperationModeProgram, cmdTxOperationModeReserve, 
                cmdTxOpModeExcAutomatic, cmdTxPreselectExciter, cmdTxDelayTimeExcAutomatic, cmdOstRefVoltageVision, cmdOstMaxOutletTempThreshold, 
                netCCUNumberOfEntries, netCCULogbookClear, netCCULogbookEntryNbr, netCCULogbookType, netCCULogbookSlope, 
                netCCULogbookMessage, netCCULogbookDateTime, outputstageANumberOfEntries, outputstageALogbookClear, ostALogbookEntryNbr, 
                ostALogbookType, ostALogbookSlope, ostALogbookMessage, exciterBNumberOfEntries, exciterBLogbookClear, 
                excBLogbookEntryNbr, excBLogbookType, excBLogbookSlope, excBLogbookMessage, excBLogbookDateTime, 
                exciterANumberOfEntries, exciterALogbookClear, excALogbookEntryNbr, excALogbookType, excALogbookSlope, 
                excALogbookMessage, excALogbookDateTime, additionalPowerSupply, powerSupply, cmdTxSystemMode, 
                ostALogbookDateTime, summaryFaultTx, summaryWarningTx, localModeTx, rfOnTx, 
                forwardPower, reflectedPower, summaryFaultExcA, summaryFaultOstA, summaryFaultExcB, 
                exciterAutomaticReady, exciterAutomaticChanged, exciterAutomaticFault, noConnectionExcA, noConnectionOstA, 
                noConnectionExcB, activeExcA, activeExcB, ostRackInletTemperature, ostRackOutletTemperature, 
                ostRackAuxPowerSupply, amplifiersPerRack, rackRfEventSignalling, rackGeneralPurposeInput, rfProbePresent, 
                rfProbeConfigurationNominalValue, rfProbeThresholdRfFailLimit, rfProbeThresholdTimeoutRfFailCtr, rfProbeThresholdWarningLimit, rfProbeCalibrationGain, 
                rfProbeCalibrationOffset, rfProbeCalibrationSetGain, rfProbeCalibrationSetOffset, rfProbeMeasuredValue }
            STATUS current
            DESCRIPTION 
                "This group includes all OIDs for reserve concept
                DualDrive (NetCCU + 2 * exciter + outputstage)
                in case of MediumPower."
            ::= { rsXx8000AtvTxGroups 4 }

        
        groupAlarmDualDriveMP NOTIFICATION-GROUP
            NOTIFICATIONS { txSummaryFault, txSummaryWarning, txLocal, txRfOn, txRfOk, 
                txParamSetValuesChanged, txRfLoopProgram, txRfLoopReserve, txRfWarning, txReflectionWarning, 
                txNetCCUFanFault, txNetCCUPowerSupply, txRfFail, txReflectionFault, txNetCCUNoConnectionToExcA, 
                txNetCCUNoConnectionToOstA, txNetCCUNoConnectionToExcB, txOstSummaryFault, txOstSummaryWarning, txOstRfOn, 
                txOstRfOk, txOstNoInput, txOstRfWarning, txOstReflectionWarning, txOstRackWarning, 
                txOstCoolingWarning, txOstRfFail, txOstReflectionFault, txOstACFault, txOstCoolingFault, 
                txOstCommFault, txRackSumFault, txRackSumWarning, txRackOn, txRackGpiWarning, 
                txRackFan1Fault, txRackFan2Fault, txRackCoolingSumWarning, txRackAmplifierSumFault, txRackNoLink, 
                txRackGpiFault, txRackTemperatureFault, txRackACFault, txRackCoolingSumFault, txRackTempFaultAbs1, 
                txRackTempFaultAbs2, txRackDCFault, txRackRfWarning, txRackRfFault, txRackReflectionWarning, 
                txRackReflectionFault, txAutomaticExcFault, txExcSummaryFault, txExcSummaryWarning, txExcOn, 
                txExcNoInput, txExcOutputOpen, txExcRfLoop, txExcBoardTemperatureWarning, txExcTestSignal, 
                txExcFanWarning, txExcFanFault, txAutomaticExcChanged, txAutomaticExcReady, txExcRfOn, 
                txRackProbeNotCalibrated, txRackRfOk, txExcLocal, txModeSwitchOverFailed, txModeInconsistent, 
                txModeSwitchOverEnded, txModeSwitchOverStarted, txRackOvervoltProtectWarning, txRackRfOn, txNetCCUBoardTemperatureWarning, 
                txExcSelfTest, txRackTemperatureWarning }
            STATUS current
            DESCRIPTION 
                "This group includes all alarm OIDs for reserve concept
                DualDrive (NetCCU + 2 * exciter + outputstage)
                in case of MediumPower."
            ::= { rsXx8000AtvTxGroups 5 }

        
        groupPowerReserveMP OBJECT-GROUP
            OBJECTS { cmdTxResetSumFault, cmdTxParametersetLoad, cmdTxParametersetSave, cmdTxOperationModeProgram, cmdTxOperationModeReserve, 
                cmdTxOpModeExcAutomatic, cmdTxOpModeOstAutomatic, cmdTxPreselectExciter, cmdTxPreselectOutputstage, cmdTxDelayTimeExcAutomatic, 
                cmdTxDelayTimeOstAutomatic, cmdOstRefVoltageVision, cmdOstMaxOutletTempThreshold, netCCUNumberOfEntries, netCCULogbookClear, 
                netCCULogbookEntryNbr, netCCULogbookType, netCCULogbookSlope, netCCULogbookMessage, netCCULogbookDateTime, 
                outputstageANumberOfEntries, outputstageALogbookClear, ostALogbookEntryNbr, ostALogbookType, ostALogbookSlope, 
                ostALogbookMessage, ostALogbookDateTime, outputstageBNumberOfEntries, outputstageBLogbookClear, ostBLogbookEntryNbr, 
                ostBLogbookType, ostBLogbookSlope, ostBLogbookMessage, forwardPowerOstA, reflectedPowerOstA, 
                forwardPowerOstB, reflectedPowerOstB, exciterBNumberOfEntries, exciterBLogbookClear, excBLogbookEntryNbr, 
                excBLogbookType, excBLogbookSlope, excBLogbookMessage, excBLogbookDateTime, exciterANumberOfEntries, 
                exciterALogbookClear, excALogbookEntryNbr, excALogbookType, excALogbookSlope, excALogbookMessage, 
                excALogbookDateTime, additionalPowerSupply, powerSupply, cmdTxSystemMode, ostBLogbookDateTime, 
                summaryFaultTx, summaryWarningTx, localModeTx, rfOnTx, forwardPower, 
                reflectedPower, summaryFaultExcA, summaryFaultOstA, summaryFaultExcB, summaryFaultOstB, 
                exciterAutomaticReady, exciterAutomaticChanged, exciterAutomaticFault, outputstageAutomaticReady, outputstageAutomaticChanged, 
                outputstageAutomaticFault, noConnectionExcA, noConnectionOstA, noConnectionExcB, noConnectionOstB, 
                activeExcA, activeOstA, activeExcB, activeOstB, ostRackInletTemperature, 
                ostRackOutletTemperature, ostRackAuxPowerSupply, amplifiersPerRack, rackRfEventSignalling, rackGeneralPurposeInput, 
                rfProbePresent, rfProbeConfigurationNominalValue, rfProbeThresholdRfFailLimit, rfProbeThresholdTimeoutRfFailCtr, rfProbeThresholdWarningLimit, 
                rfProbeCalibrationGain, rfProbeCalibrationOffset, rfProbeCalibrationSetGain, rfProbeCalibrationSetOffset, rfProbeMeasuredValue
                 }
            STATUS current
            DESCRIPTION 
                "This group includes all OIDs for reserve concept
                Active/Passive Reserve (NetCCU + 2 * exciter + 2 * outputstage),
                in case of MediumPower.
                For more details, refer to manual."
            ::= { rsXx8000AtvTxGroups 6 }

        
        groupAlarmPowerReserveMP NOTIFICATION-GROUP
            NOTIFICATIONS { txSummaryFault, txSummaryWarning, txLocal, txRfOn, txRfOk, 
                txParamSetValuesChanged, txRfLoopProgram, txRfLoopReserve, txRfWarning, txReflectionWarning, 
                txNetCCUFanFault, txNetCCUPowerSupply, txRfFail, txReflectionFault, txNetCCUNoConnectionToExcA, 
                txNetCCUNoConnectionToOstA, txNetCCUNoConnectionToExcB, txNetCCUNoConnectionToOstB, txAutomaticExcReady, txAutomaticExcChanged, 
                txAutomaticExcFault, txAutomaticOstReady, txAutomaticOstChanged, txAutomaticOstFault, txOstSummaryFault, 
                txOstSummaryWarning, txOstRfOn, txOstRfOk, txOstNoInput, txOstRfWarning, 
                txOstReflectionWarning, txOstRackWarning, txOstCoolingWarning, txOstRfFail, txOstReflectionFault, 
                txOstACFault, txOstCoolingFault, txOstCommFault, txRackSumFault, txRackSumWarning, 
                txRackOn, txRackGpiWarning, txRackFan1Fault, txRackFan2Fault, txRackCoolingSumWarning, 
                txRackAmplifierSumFault, txRackNoLink, txRackGpiFault, txRackTemperatureFault, txRackACFault, 
                txRackCoolingSumFault, txRackTempFaultAbs1, txRackTempFaultAbs2, txRackDCFault, txRackRfWarning, 
                txRackRfFault, txRackReflectionWarning, txRackReflectionFault, txExcSummaryFault, txExcSummaryWarning, 
                txExcOn, txExcNoInput, txExcOutputOpen, txExcRfLoop, txExcBoardTemperatureWarning, 
                txExcTestSignal, txExcFanWarning, txExcRfOn, txRackProbeNotCalibrated, txRackRfOk, 
                txRackRfOn, txExcLocal, txModeSwitchOverFailed, txModeInconsistent, txModeSwitchOverEnded, 
                txModeSwitchOverStarted, txRackOvervoltProtectWarning, txExcFanFault, txNetCCUBoardTemperatureWarning, txExcSelfTest, 
                txRackTemperatureWarning }
            STATUS current
            DESCRIPTION 
                "This group includes all alarm OIDs for reserve concept
                ActiveReserve (NetCCU + 2 * exciter + 2 * outputstage),
                in case of MediumPower.
                For more details, refer to manual."
            ::= { rsXx8000AtvTxGroups 7 }

        
        groupAlarmAdditionalPowerSupply NOTIFICATION-GROUP
            NOTIFICATIONS { txInternalPowerSupplyWarning, txExternalPowerSupplyWarning }
            STATUS current
            DESCRIPTION 
                "Alarms that are available only when additionalPowerSupply is true."
            ::= { rsXx8000AtvTxGroups 8 }

        
        groupAlarmAmplifier NOTIFICATION-GROUP
            NOTIFICATIONS { txAmpSumFault, txAmpSumWarning, txAmpPowerOn, txAmpDCOk, txAmpACOk, 
                txAmpRfInFail, txAmpRfFail, txAmpReflectionFault, txAmpTemperatureFault, txAmpTransistorFault
                 }
            STATUS current
            DESCRIPTION 
                "alarms from the amplifier (medium/high power only)"
            ::= { rsXx8000AtvTxGroups 9 }

        
        groupIndependentRacks OBJECT-GROUP
            OBJECTS { rackReferenceVoltage, amplifiersPowerSupply, rackOnOff }
            STATUS current
            DESCRIPTION 
                "object types that are relevant for NX variants with independent racks only"
            ::= { rsXx8000AtvTxGroups 10 }

        
        groupObjsAdditionalPowerSupply OBJECT-GROUP
            OBJECTS { internalPowerSupply, externalPowerSupply }
            STATUS current
            DESCRIPTION 
                "Objects that are available only when additionalPowerSupply is true."
            ::= { rsXx8000AtvTxGroups 11 }

        
        groupObjectsControlExciter OBJECT-GROUP
            OBJECTS { cmdTxOperationModeReserve, cmdTxOpModeExcAutomatic, cmdTxDelayTimeExcAutomatic, summaryFaultExcB, exciterAutomaticReady, 
                exciterAutomaticChanged, exciterAutomaticFault, noConnectionExcB, activeExcB, cmdTxProgramExciterPrio, 
                cmdTxChangeOver, cmdTxSwitchPosition }
            STATUS current
            DESCRIPTION 
                "additional objects in case Sx801 is control exciter"
            ::= { rsXx8000AtvTxGroups 12 }

        
        groupProductInfo OBJECT-GROUP
            OBJECTS { prodInfoModuleName, prodInfoSerialNumber, prodInfoIdentNumberSW, prodInfoVersionNumberSW, prodInfoIdentNumberHW, 
                prodInfoVersionNumberHW, productInfoProductDateHW }
            STATUS current
            DESCRIPTION 
                "This group includes all OIDs for device product information."
            ::= { rsXx8000AtvTxGroups 18 }

        
        groupAmpMeasureValues OBJECT-GROUP
            OBJECTS { ostRackAmpI1A, ostRackAmpI2A, ostRackAmpI3A, ostRackAmpI4A, ostRackAmpI1B, 
                ostRackAmpI2B, ostRackAmpI3B, ostRackAmpI4B, ostRackAmpIDrv, ostRackAmpUDc, 
                ostRackAmpIDc, ostRackAmpUDcControl, ostRackAmpUReg, ostRackAmpPowerA, ostRackAmpPowerB, 
                ostRackAmpPowerOut, ostRackAmpPowerReflection, ostRackAmpPowerReference, ostRackAmpDeltaPhase, ostRackAmpCmdDeltaPhase
                 }
            STATUS current
            DESCRIPTION 
                "This group includes all OIDs amplifier measure values.
                Practically, these information are not important to customers, they are needed in manufactory."
            ::= { rsXx8000AtvTxGroups 19 }

        
        groupRfProbes OBJECT-GROUP
            OBJECTS { rfProbesNetCCURfProbe1, rfProbesNetCCURfProbe2, rfProbesAntFwdNominal, rfProbesAntFwdWarningLimit, rfProbesAntFwdFailLimit, 
                rfProbesAntFwdDelayTimeRfFail, rfProbesAntFwdSetOffset, rfProbesAntFwdSetGain, rfProbesAntReflWarningLimit, rfProbesAntReflSetOffset, 
                rfProbesAntReflSetGain, rfProbesOstFwdNominal, rfProbesOstFwdWarningLimit, rfProbesOstFwdFailLimit, rfProbesOstFwdDelayTimeRfFail, 
                rfProbesOstFwdSetOffset, rfProbesOstFwdSetGain, rfProbesOstReflWarningLimit, rfProbesOstReflSetOffset, rfProbesOstReflSetGain
                 }
            STATUS current
            DESCRIPTION 
                "This group includes all OIDs regarding RF Probes."
            ::= { rsXx8000AtvTxGroups 20 }

        
        groupExcCommon OBJECT-GROUP
            OBJECTS { cmdExcTvStandard, cmdExcVideoInputNominalLevel, cmdExcWhiteCtrlAutomatic, cmdExcWhiteCtrlTestLine, cmdExcWhiteCtrlGainSource, 
                cmdExcWhiteCtrlManualGain, cmdExcWhiteLimiter, cmdExcWhiteLimiterThreshold, cmdExcSyncRegeneration, cmdExcSyncAmplitude, 
                cmdExcDiplexer, cmdExcDiplexerPeaking, cmdExcDiplexerPreEqualization, cmdExcFmSubCarrier1, cmdExcFmAf1Deviation, 
                cmdExcFmDeviationLimiter, cmdExcFmDeviationLimiterThrshold, cmdExcFmDeviationLimiterWrnThrsh, cmdExcFmPrecorrChn1, cmdExcFmPrecorrChn1Point1, 
                cmdExcFmPrecorrChn1Slope1, cmdExcFmPrecorrChn1Point2, cmdExcFmPrecorrChn1Slope2, cmdExcFrequency, cmdExcFrequencyOffset, 
                cmdExcReferenceSource, cmdExcOcxoAdjust, cmdExcRfOutput, cmdExcRfOutputAttenuation, cmdExcRfOutputRfSlope, 
                cmdExcRfOutputModulationSlope, cmdExcRfOutputResidualCarrier, cmdExcRfMonitorCommon, cmdExcRfMonitorSound1, cmdExcRfOutputCarrier1, 
                cmdExcLevelVsVisionAntennaSound1, cmdExcRfIqAdjustTestsignal, cmdExcRfIqAdjustBiasCoarseI, cmdExcRfIqAdjustBiasCoarseQ, cmdExcRfIqAdjustBiasFineI, 
                cmdExcRfIqAdjustBiasFineQ, cmdExcRfIqAdjustGainI, cmdExcRfIqAdjustGainQ, cmdExcRfIqAdjustPhase, excStatusSyncOutputAmplitude, 
                excStatusSyncInputAmplitude, excStatusSyncMonitoring, excStatusWhiteLimiterActive, excStatusWhiteInputLevel, excStatusRfIqAdjustLO1Frequency, 
                excStatusRfOutputAgcRegulation, excStatusFmLimiterC1, excStatusFmAF1Deviation, excPrecNonlinCorrectionPoint2, excPrecNonlinCorrectionPoint1, 
                excPrecNonlinFrequencyCorrection, excPrecNonlinPhase, excPrecNonlinAmplitude, excPrecNonlinCorrection, excPrecLinGroupDelay, 
                excPrecLinAmplitude, excPrecLinCorrection, excStatusFmCarrier1, excStatusVideoInputClipping, excStatusWhiteCtrlMemoryGain, 
                excStatusWhiteGainSource, excStatusWhiteInputAmplitude, cmdExcTypeLossOfInput, excStatusFailDelay, cmdExcFailDelayMode, 
                excStatusWhiteOutputAmplitude, excStatusRfMonitorSyncLvlAntenna }
            STATUS current
            DESCRIPTION 
                "Exciter parameters for all module compliances."
            ::= { rsXx8000AtvTxGroups 21 }

        
        groupExcCommonNoSLx OBJECT-GROUP
            OBJECTS { cmdExcVideoInput, cmdExcVideoInputLimiter, cmdExcRfOutputRegulation, cmdExcRfOutputManualRfLevel, cmdExcRfIqAdjustStart, 
                excStatusRfIqAdjustAuto }
            STATUS current
            DESCRIPTION 
                "Exciter parameters for all module compliances except SLx."
            ::= { rsXx8000AtvTxGroups 22 }

        
        groupExcDual OBJECT-GROUP
            OBJECTS { cmdExcFmSubCarrier2, cmdExcFmAf2Deviation, cmdExcFmPrecorrChn2, cmdExcFmPrecorrChn2Point1, cmdExcFmPrecorrChn2Slope1, 
                cmdExcFmPrecorrChn2Point2, cmdExcFmPrecorrChn2Slope2, cmdExcRfOutputCarrier2, cmdExcRfMonitorSound2, cmdExcLevelVsVisionAntennaSound2, 
                excStatusFmCarrier2, excStatusFmAF2Deviation, excStatusFmLimiterC2 }
            STATUS current
            DESCRIPTION 
                "dual tone mode"
            ::= { rsXx8000AtvTxGroups 23 }

        
        groupExcNicam OBJECT-GROUP
            OBJECTS { cmdExcNicamMode, cmdExcNicamPrecorrection }
            STATUS current
            DESCRIPTION 
                "object types that are available for all NICAM modes"
            ::= { rsXx8000AtvTxGroups 24 }

        
        groupExcNicamModulator OBJECT-GROUP
            OBJECTS { excStatusNicam728Datastream }
            STATUS current
            DESCRIPTION 
                "object types available for NICAM mode 'Modulator' only"
            ::= { rsXx8000AtvTxGroups 25 }

        
        groupExcNicamCoder OBJECT-GROUP
            OBJECTS { cmdExcAfMode, cmdExcNicamGainAdjustAF1, cmdExcNicamGainAdjustAF2, cmdExcNicamInputPreemphasis, cmdExcNicamAudioMode, 
                cmdExcNicamAudioReserveSound, excStatusAudioInputLevelAF1, excStatusAudioInputLevelAF2, excStatusNicamInputClippingAF1, excStatusNicamInputClippingAF2, 
                excStatusNicamInputLevelAF1, excStatusNicamInputLevelAF2 }
            STATUS current
            DESCRIPTION 
                "object types available for NICAM mode 'Coder' only"
            ::= { rsXx8000AtvTxGroups 26 }

        
        groupExcNicamExtern OBJECT-GROUP
            OBJECTS { excStatusNicamSubcarrier }
            STATUS current
            DESCRIPTION 
                "object types available for NICAM mode 'Extern' only"
            ::= { rsXx8000AtvTxGroups 27 }

        
        groupExcNicamNotExtern OBJECT-GROUP
            OBJECTS { cmdExcNicamRolloff, cmdExcNicamInsertPrbs }
            STATUS current
            DESCRIPTION 
                "object types that are available when NICAM mode 'Coder' or 'Modulator' is selected"
            ::= { rsXx8000AtvTxGroups 28 }

        
        groupExcFm OBJECT-GROUP
            OBJECTS { cmdExcSoundSelect, cmdExcAudioNominalLevelAF2, cmdExcFmAudioMode, cmdExcFmAudioDataLine, cmdExcFmAudioPilot, 
                cmdExcFmAudioPilotGain, excStatusFmAudioPilotDeviation, excStatusAudioInputLevelAF2, excStatusAudioInputClippingAF2, excStatusFmAudioDataLineInfo, 
                excStatusFmAudioMode }
            STATUS current
            DESCRIPTION 
                "object types that are available only when TV standard is not M nor N"
            ::= { rsXx8000AtvTxGroups 29 }

        
        groupExcNotFm OBJECT-GROUP
            OBJECTS { cmdExcFmInput }
            STATUS current
            DESCRIPTION 
                "object types that are available only when TV standard is M or N
                (the US audio modes)"
            ::= { rsXx8000AtvTxGroups 30 }

        
        groupExcBTSC OBJECT-GROUP
            OBJECTS { cmdExcAudioNominalLevelBTSC, excStatusAudioInputLevelBTSC, excStatusAudioInputClippingBTSC }
            STATUS current
            DESCRIPTION 
                "object types that are available only when US audio mode is BTSC"
            ::= { rsXx8000AtvTxGroups 31 }

        
        groupExcNotBTSC OBJECT-GROUP
            OBJECTS { cmdExcAudioInputLowpass, excStatusAudioInputLevelAF1, excStatusAudioInputClippingAF1, cmdExcAudioInputPreemphasis, cmdExcAudioNominalLevelAF1
                 }
            STATUS current
            DESCRIPTION 
                "object types that are available only when US audio mode is not BTSC"
            ::= { rsXx8000AtvTxGroups 32 }

        
        groupExc3NF OBJECT-GROUP
            OBJECTS { cmdExcAudioNominalLevelAF3, excStatusAudioInputClippingAF3, excStatusAudioInputLevelAF3 }
            STATUS current
            DESCRIPTION 
                "object types that are available only when number of NF inputs is 3"
            ::= { rsXx8000AtvTxGroups 33 }

        
        groupExcLP OBJECT-GROUP
            OBJECTS { cmdExcCarrier, excStatusNominalPower }
            STATUS current
            DESCRIPTION 
                "object types that are available for low power transmitters only"
            ::= { rsXx8000AtvTxGroups 34 }

        
        groupSLx OBJECT-GROUP
            OBJECTS { cmdExcConfNICAM, cmdExcTransmitterType, cmdExcTimeScheduler, cmdExcOutputPower, excPrecUserState, 
                excPrecFactoryState, excPrecRestoreCurrentSettings, excPrecRestoreAllSettings, configTvStandardName, configFrequency, 
                configPower, schedulerRowStatus, schedulerEvent, schedulerDateTime, config2InputSource, 
                config2Power, config2Frequency, config2RxFrequency, config2TvStandardName, excStatusVSWR, 
                schedulerTvStandard, configRxFrequency, configInputSource }
            STATUS current
            DESCRIPTION 
                "object types that are relevant for SLx devices only"
            ::= { rsXx8000AtvTxGroups 35 }

        
        groupObsoleted OBJECT-GROUP
            OBJECTS { cmdTxParametersetReSave, rfProbeConfigurationLabel }
            STATUS obsolete
            DESCRIPTION 
                "This group includes all deprecated and obsoleted objects."
            ::= { rsXx8000AtvTxGroups 36 }

        
        groupAlarmObsoleted NOTIFICATION-GROUP
            NOTIFICATIONS { txParamSetSubDeviceDiffers, txNetCCUBoardTemperatureFault }
            STATUS obsolete
            DESCRIPTION 
                "This group includes all deprecated and obsoleted alarms."
            ::= { rsXx8000AtvTxGroups 37 }

        
        groupDummyLoadRF OBJECT-GROUP
            OBJECTS { rfProbesDLFwdNominal, rfProbesDLFwdWarningLimit, rfProbesDLFwdFailLimit, rfProbesDLFwdDelayTimeRfFail, rfProbesDLFwdSetOffset, 
                rfProbesDLFwdSetGain, rfProbesDLReflWarningLimit, rfProbesDLReflSetOffset, rfProbesDLReflSetGain }
            STATUS current
            DESCRIPTION 
                "This group includes all object types regarding probes from dummy load.
                The object types in this group are defined only when a dummy load measure point exists.
                This can occur in reserve concept active reserve only.
                "
            ::= { rsXx8000AtvTxGroups 38 }

        
        groupObjectsSingleEnded OBJECT-GROUP
            OBJECTS { cmdTxRfSwitch }
            STATUS current
            DESCRIPTION 
                "Group for objects in case of SingleTx or DualDrive."
            ::= { rsXx8000AtvTxGroups 39 }

        
        groupObjectsSx801Amplifier OBJECT-GROUP
            OBJECTS { sx801AmpRfOut, sx801AmpRfIn, sx801AmpReflection, sx801AmpOn, sx801AmpAC, 
                sx801AmpCommunication, sx801AmpTransistor, sx801AmpDriver, sx801AmpTemperature, sx801AmpBlower, 
                sx801AmpRegulation, sx801AmpUpdate, sx801Supply1Temperature, sx801Supply2Temperature, sx801SupplyRTemperature, 
                sx801Supply1DC, sx801Supply2DC, sx801SupplyRDC, sx801AmpValueI1, sx801AmpValueI2, 
                sx801AmpValueI3, sx801AmpValueI4, sx801AmpValueIPre, sx801AmpValueIDrv1, sx801AmpValueIDrv2, 
                sx801AmpValuePowerOut, sx801AmpValueReflection, sx801AmpValueVRef, sx801AmpValueVReg, sx801AmpValueTemperature, 
                sx801AmpValueMonAtt, sx801AmpValueVAux1, sx801AmpValueVAux2, sx801Supply1ValuePwr, sx801Supply2ValuePwr, 
                sx801Supply1ValueDc, sx801Supply2ValueDc }
            STATUS current
            DESCRIPTION 
                "Objects for Sx801/SA801 amplifier status."
            ::= { rsXx8000AtvTxGroups 40 }

        
        rsXx8000AtvTxCompl OBJECT IDENTIFIER ::= { rsXx8000AtvTxConf 3 }

        
        rsXx8000ATVSingleTxMP MODULE-COMPLIANCE
            STATUS current
            DESCRIPTION 
                "Reserve concept SingleTransmitter for Medium Power."
            MODULE -- this module
                MANDATORY-GROUPS { groupEvents, groupSingleTxMP, groupAlarmSingleTxMP, groupProductInfo, groupRfProbes, 
                    groupExcCommon, groupExcCommonNoSLx, groupObjectsSingleEnded }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
                GROUP groupIndependentRacks
                    DESCRIPTION 
                        "for variant with independent racks only"
                OBJECT cmdOstRefVoltageVision
                    MIN-ACCESS not-accessible
                    DESCRIPTION 
                        "not accessible in variant with independent racks"
                GROUP groupAlarmAdditionalPowerSupply
                    DESCRIPTION 
                        "only when additionalPowerSupply is true"
                GROUP groupAmpMeasureValues
                    DESCRIPTION 
                        "not for face-lift configuration"
                GROUP groupAlarmAmplifier
                    DESCRIPTION 
                        "not for face-lift configuration"
                GROUP groupObjsAdditionalPowerSupply
                    DESCRIPTION 
                        "only when additionalPowerSupply is true"
            ::= { rsXx8000AtvTxCompl 1 }

        
        rsXx8000ATVDualDriveMP MODULE-COMPLIANCE
            STATUS current
            DESCRIPTION 
                "Reserve concept DualDrive for Medium Power."
            MODULE -- this module
                MANDATORY-GROUPS { groupEvents, groupDualDriveMP, groupAlarmDualDriveMP, groupProductInfo, groupRfProbes, 
                    groupExcCommon, groupExcCommonNoSLx, groupObjectsSingleEnded }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
                GROUP groupIndependentRacks
                    DESCRIPTION 
                        "for variant with independent racks only"
                OBJECT cmdOstRefVoltageVision
                    MIN-ACCESS not-accessible
                    DESCRIPTION 
                        "not accessible in variant with independent racks"
                GROUP groupAlarmAdditionalPowerSupply
                    DESCRIPTION 
                        "only when additionalPowerSupply is true"
                GROUP groupAmpMeasureValues
                    DESCRIPTION 
                        "not for face-lift configuration"
                GROUP groupAlarmAmplifier
                    DESCRIPTION 
                        "not for face-lift configuration"
                GROUP groupObjsAdditionalPowerSupply
                    DESCRIPTION 
                        "only when additionalPowerSupply is true"
            ::= { rsXx8000AtvTxCompl 2 }

        
        rsXx8000ATVPowerReserveMP MODULE-COMPLIANCE
            STATUS current
            DESCRIPTION 
                "Reserve concept Active/Passive Reserve for Medium Power."
            MODULE -- this module
                MANDATORY-GROUPS { groupEvents, groupProductInfo, groupRfProbes, groupExcCommon, groupExcCommonNoSLx, 
                    groupPowerReserveMP, groupAlarmPowerReserveMP }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
                GROUP groupIndependentRacks
                    DESCRIPTION 
                        "for variant with independent racks only"
                OBJECT cmdOstRefVoltageVision
                    MIN-ACCESS not-accessible
                    DESCRIPTION 
                        "not accessible in variant with independent racks"
                GROUP groupAlarmAdditionalPowerSupply
                    DESCRIPTION 
                        "only when additionalPowerSupply is true"
                GROUP groupAmpMeasureValues
                    DESCRIPTION 
                        "not for face-lift configuration"
                GROUP groupAlarmAmplifier
                    DESCRIPTION 
                        "not for face-lift configuration"
                GROUP groupObjsAdditionalPowerSupply
                    DESCRIPTION 
                        "only when additionalPowerSupply is true"
                GROUP groupDummyLoadRF
                    DESCRIPTION 
                        "only when a dummy load measure point exists"
            ::= { rsXx8000AtvTxCompl 3 }

        
        rsXx8000ATVSingleTxLP MODULE-COMPLIANCE
            STATUS current
            DESCRIPTION 
                "Reserve concept SingleTransmitter for Low Power."
            MODULE -- this module
                MANDATORY-GROUPS { groupEvents, groupSingleTxMP, groupAlarmSingleTxMP, groupProductInfo, groupRfProbes, 
                    groupExcCommon, groupExcCommonNoSLx, groupExcLP }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
                GROUP groupAlarmAdditionalPowerSupply
                    DESCRIPTION 
                        "only when additionalPowerSupply is true"
                GROUP groupObjsAdditionalPowerSupply
                    DESCRIPTION 
                        "only when additionalPowerSupply is true"
            ::= { rsXx8000AtvTxCompl 5 }

        
        rsXx8000ATVSingleTxSLx MODULE-COMPLIANCE
            STATUS current
            DESCRIPTION 
                "Reserve concept SingleTransmitter for SLx devices."
            MODULE -- this module
                MANDATORY-GROUPS { groupEvents, groupSingleTxMP, groupAlarmSingleTxMP, groupProductInfo, groupRfProbes, 
                    groupExcCommon, groupExcLP, groupSLx }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
            ::= { rsXx8000AtvTxCompl 6 }

        
        rsXx8000ATVSx801ControlExiter MODULE-COMPLIANCE
            STATUS current
            DESCRIPTION 
                "Sx801 as control exciter"
            MODULE -- this module
                MANDATORY-GROUPS { groupEvents, groupSingleTxMP, groupAlarmSingleTxMP, groupProductInfo, groupRfProbes, 
                    groupExcCommon, groupExcLP, groupObjectsSx801Amplifier, groupSLx, groupObjectsControlExciter
                     }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
            ::= { rsXx8000AtvTxCompl 7 }

        
        rsXx8000ATVExciterOnly MODULE-COMPLIANCE
            STATUS current
            DESCRIPTION 
                "ATV Exciter of 8000 series in a 7000 environment
                or
                Program Exciter in a Sx801 Backup Exciter environment."
            MODULE -- this module
                MANDATORY-GROUPS { groupEvents, groupProductInfo, groupExcCommon, groupObjectsSx801Amplifier }
            ::= { rsXx8000AtvTxCompl 8 }

        
        rsXx8000ATVSingleTxSx801 MODULE-COMPLIANCE
            STATUS current
            DESCRIPTION 
                "Reserve concept SingleTransmitter for Sx801 devices."
            MODULE -- this module
                MANDATORY-GROUPS { groupEvents, groupSingleTxMP, groupAlarmSingleTxMP, groupProductInfo, groupRfProbes, 
                    groupExcCommon, groupExcLP, groupSLx, groupObjectsSx801Amplifier }
                GROUP groupExcDual
                    DESCRIPTION 
                        "only when 'Dual Carrier' sound is selected"
                GROUP groupExcNicam
                    DESCRIPTION 
                        "only when NICAM (Coder, Modulator or Extern) is selected"
                GROUP groupExcNicamModulator
                    DESCRIPTION 
                        "only when NICAM mode 'Modulator' is selected"
                GROUP groupExcNicamCoder
                    DESCRIPTION 
                        "only when NICAM mode 'Coder' is selected"
                GROUP groupExcNicamExtern
                    DESCRIPTION 
                        "only when NICAM mode 'Extern' is selected"
                GROUP groupExcFm
                    DESCRIPTION 
                        "only when TV standard is not M nor N"
                GROUP groupExcNotFm
                    DESCRIPTION 
                        "only when TV standard is M or N"
                GROUP groupExcBTSC
                    DESCRIPTION 
                        "only when US audio mode is BTSC"
                GROUP groupExcNotBTSC
                    DESCRIPTION 
                        "only when US audio mode is not BTSC"
                GROUP groupExc3NF
                    DESCRIPTION 
                        "only when number of NF inputs is 3"
                GROUP groupExcNicamNotExtern
                    DESCRIPTION 
                        "only when NICAM mode 'Coder' or 'Modulator' is selected"
            ::= { rsXx8000AtvTxCompl 9 }

        
    
    END
