-- *****************************************************************************
-- *****************************************************************************
-- **
-- **  COPYRIGHT      (c) 2006 Rohde & Schwarz GmbH & Co. KG
-- **                          Muehldorfstrasse 15
-- **    R & S                 D-81671 Muenchen
-- **
-- *****************************************************************************
-- **
-- **  MODULE         RS-XX8000-FM-NP1-MIB
-- **  
-- **  DESCRIPTION    Rohde & Schwarz SNMP
-- **
-- **  HISTORY        
-- **
-- **  2008-04-16 kp - initial version
-- **  2008-07-07 kp - change cmdExcActivateDeviationLimiter from 
-- **                  switch to INTEGER(off, on, clipperonly)
-- **  2008-08-20 sr - new loadedTx for switchoverUnit
-- **  2008-08-26 ks - cmdTxParametersetReSave obsolete
-- **                - cmdTxDelayTimeExcAutomatic values 1..60
-- **  2008-09-15 sr - new rackTable
-- **                - new txRackRfWarning, txRackRfFault, txRackReflectionWarning,
-- **                      txRackReflectionFault
-- **                - new groupIndependentRacks
-- **  2008-12-12 sr - loadedTx to bindings of nsuAutomaticChanged
-- **                - rfProbeConfigurationLabel obsolete
-- **                - txRackExtCoolingWarning renamed to txRackGpiWarning
-- **                - txRackExtCoolingFault renamed to txRackGpiFault
-- **  2009-01-07 sr - rfProbeCalibrationSetGain, rfProbeCalibrationSetOffset
-- **  2009-03-30 ks - txRackProbeNotCalibrated added
-- **                - txParamSetSubDeviceDiffers obsoleted
-- **  2009-05-06 ks - device info for TC boards
-- **  2009-05-28 ks - information for additional (external) power supply added
-- **                - txRackRfOn, txRackRfOk, txRackTemperatureWarning added
-- **  2009-07-02 ks - measured values for power supply added
-- **                - conditional groupDummyLoadRF added
-- **  2009-10-08 ks - txRackOvervoltProtectWarning added
-- **                - selectedInputTxB is read-only
-- **  2009-11-13 ks - ampDeltaPhase, ampCmdDeltaPhase added
-- **  2010-01-28 ks - nsuBoardTemperatureFault, txNetCCUBoardTemperatureFault deprecated and
-- **                  nsuBoardTemperatureWarning, txNetCCUBoardTemperatureWarning added
-- **  2010-05-11 ks - evtProgramRfOn added
-- **  2010-06-01 ks - txNoConnection added
-- **  2012-03-20 ks - cmdExcActivateDeviationLimiter value range corrected
-- **
-- *****************************************************************************
-- *****************************************************************************

    RS-XX8000-FM-NP1-MIB DEFINITIONS ::= BEGIN
 
        IMPORTS
            rsXx8000, eventAlarmPriority, eventAlarmClass, eventEvent, indexTransmitter, 
            indexAB, indexRack, indexAmplifier, indexProgram, rsXx8000MibModule, 
            EventPriority, EventClass, EventState, IndexTransmitter, IndexAB, 
            IndexRack, IndexAmplifier, SwitchOnOff, Trigger, LogbookMaxEntryNumber, 
            LogbookEntrySlope, LogbookEntryMessagesNSU, ProdInfoModuleNameNsu, ReadableString, IndexProgram, 
            FloatingPoint, LogbookEntryMessagesNetCCU, LogbookEntryMessagesExcFM, LogbookEntryMessagesOST, ProdInfoModuleNameFm, 
            EventMaxEntryNumber, EventMask            
                FROM RS-XX8000-COMMON-MIB            
            OBJECT-GROUP, MODULE-COMPLIANCE, NOTIFICATION-GROUP            
                FROM SNMPv2-CONF            
            Integer32, OBJECT-TYPE, MODULE-IDENTITY, OBJECT-IDENTITY, NOTIFICATION-TYPE            
                FROM SNMPv2-SMI            
            TruthValue, DateAndTime            
                FROM SNMPv2-TC;
    
    
        rsXx8000FmNp1MibModule MODULE-IDENTITY 
            LAST-UPDATED "201006010900Z"		-- June 01, 2010 at 09:00 GMT
            ORGANIZATION 
                "Rohde&Schwarz GmbH & Co. KG"
            CONTACT-INFO 
                "Torsten Huebscher
                Department 7TS2
                Broadcasting Division
                Muehldorfstrasse 15
                81671 Munich, Germany
                torsten.huebscher@rohde-schwarz.com"
            DESCRIPTION 
                "This MIB defines transmitting systems from Rohde & Schwarz.
                
                Use this MIB if your system meets the following requirements:
                - series XX8000 (NetCCU800),
                - FM,
                - Nplus1-system.
                
                The following MIBs are related to this:
                - RS-COMMON-MIB         - mandatory for this MIB
                - RS-XX8000-COMMON-MIB  - mandatory for this MIB"
            REVISION "201006010900Z"		-- June 01, 2010 at 09:00 GMT
            DESCRIPTION 
                "txNoConnection added"
            REVISION "201005110900Z"		-- May 11, 2010 at 09:00 GMT
            DESCRIPTION 
                "evtProgramRfOn added"
            REVISION "201001280900Z"		-- January 28, 2010 at 09:00 GMT
            DESCRIPTION 
                "nsuBoardTemperatureFault, txNetCCUBoardTemperatureFault deprecated and
                nsuBoardTemperatureWarning, txNetCCUBoardTemperatureWarning added"
            REVISION "200911130900Z"		-- November 13, 2009 at 09:00 GMT
            DESCRIPTION 
                "ampDeltaPhase, ampCmdDeltaPhase added"
            REVISION "200910080900Z"		-- October 08, 2009 at 09:00 GMT
            DESCRIPTION 
                "txRackOvervoltProtectWarning added
                selectedInputTxB is read-only"
            REVISION "200907020900Z"		-- July 02, 2009 at 09:00 GMT
            DESCRIPTION 
                "measured values for power supply added,
                conditional groupDummyLoadRF added"
            REVISION "200905280900Z"		-- May 28, 2009 at 09:00 GMT
            DESCRIPTION 
                "information for additional (external) power supply added
                txRackRfOn, txRackRfOk, txRackTemperatureWarning added"
            REVISION "200905060900Z"		-- May 06, 2009 at 09:00 GMT
            DESCRIPTION 
                "device info for TC boards"
            REVISION "200903300900Z"		-- March 30, 2009 at 09:00 GMT
            DESCRIPTION 
                "txRackProbeNotCalibrated added
                txParamSetSubDeviceDiffers obsoleted"
            REVISION "200901070800Z"		-- January 07, 2009 at 08:00 GMT
            DESCRIPTION 
                "rfProbeCalibrationSetGain, rfProbeCalibrationSetOffset"
            REVISION "200812121430Z"		-- December 12, 2008 at 14:30 GMT
            DESCRIPTION 
                "loadedTx to bindings of nsuAutomaticChanged
                rfProbeConfigurationLabel obsolete
                txRackExtCoolingWarning renamed to txRackGpiWarning
                txRackExtCoolingFault renamed to txRackGpiFault"
            REVISION "200810201030Z"		-- October 20, 2008 at 10:30 GMT
            DESCRIPTION 
                "amplifierTable, rfProbesTable"
            REVISION "200809151030Z"		-- September 15, 2008 at 10:30 GMT
            DESCRIPTION 
                "new rackTable
                new txRackRfWarning, txRackRfFault, txRackReflectionWarning,
                    txRackReflectionFault
                new groupIndependentRacks"
            REVISION "200808260900Z"		-- August 26, 2008 at 09:00 GMT
            DESCRIPTION 
                "- cmdTxParametersetReSave obsolete
                - cmdTxDelayTimeExcAutomatic values 1..60"
            REVISION "200808201000Z"		-- August 20, 2008 at 10:00 GMT
            DESCRIPTION 
                "new loadedTx for switchoverUnit"
            REVISION "200807070900Z"		-- July 07, 2008 at 09:00 GMT
            DESCRIPTION 
                "change cmdExcActivateDeviationLimiter from switch to INTEGER(off, on, clipperonly)"
            REVISION "200804161000Z"		-- April 16, 2008 at 10:00 GMT
            DESCRIPTION 
                "This is the initial version."
            ::= { rsXx8000MibModule 15 }

        
    
    
--
-- Node definitions
--
    
        rsXx8000FmNp1 OBJECT-IDENTITY
            STATUS current
            DESCRIPTION 
                "Xx8000 FM Nplus1 system."
            ::= { rsXx8000 15 }

        
-- *****************************************************************************
-- **          object definitions
-- *****************************************************************************
        rsXx8000FmNp1Objs OBJECT IDENTIFIER ::= { rsXx8000FmNp1 1 }

        
-- *****************************************************************************
-- **          NetCCU switchoverunit
-- *****************************************************************************
        switchoverUnit OBJECT IDENTIFIER ::= { rsXx8000FmNp1Objs 1 }

        
        operationModeAutomatic OBJECT-TYPE
            SYNTAX SwitchOnOff
            MAX-ACCESS read-write
            STATUS current
            DESCRIPTION
                "This switches the automatic switching-over of transmitters on or off.
                An equivalent would be pressing ON or OFF at the NSU frontpanel."
            ::= { switchoverUnit 1 }

        
        operationModePriority OBJECT-TYPE
            SYNTAX SwitchOnOff
            MAX-ACCESS read-write
            STATUS current
            DESCRIPTION
                "This switches the usage of priorities on or off.
                
                With priorities, you can set for each program a priority. 
                If a fault occurs on a transmitter sending out a program with higher priority, 
                a transmitter sending out a program with a lower priority will be switched to the more important program."
            ::= { switchoverUnit 2 }

        
        selectedTxToDummyLoad OBJECT-TYPE
            SYNTAX IndexTransmitter
            MAX-ACCESS read-write
            STATUS current
            DESCRIPTION
                "The preselected transmitter to dummy load."
            ::= { switchoverUnit 3 }

        
        selectedInputTxB OBJECT-TYPE
            SYNTAX Integer32 (1..9)
            MAX-ACCESS read-only
            STATUS current
            DESCRIPTION
                "The preselected input of the reserve transmitter."
            ::= { switchoverUnit 4 }

        
        selectedParametersetTxB OBJECT-TYPE
            SYNTAX Integer32 (1..8)
            MAX-ACCESS read-write
            STATUS current
            DESCRIPTION
                "The preselected parameterset of the reserve transmitter.
                
                This is helpful when configuring the system and if doing tests with switching-over."
            ::= { switchoverUnit 5 }

        
        selectedChannelTxB OBJECT-TYPE
            SYNTAX INTEGER
                {
                undefined(1),
                channel1(2),
                channel2(3),
                channel3(4),
                channel4(5),
                channel5(6),
                channel6(7),
                channel7(8),
                channel8(9)
                }
            MAX-ACCESS read-write
            STATUS current
            DESCRIPTION
                "Both the input and the parameterset of the reserve transmitter.
                This OID is a combination of OIDs selectedInputTxB and selectedParametersetTxB.
                If you want to set this value, TxB (Reserve Transmitter) must be to dummy load.
                The value undefined(1) is only readable - it is not possible to set it (even TxB is to dummyload)."
            ::= { switchoverUnit 6 }

        
        resetAllFaults OBJECT-TYPE
            SYNTAX Trigger
            MAX-ACCESS read-write
            STATUS current
            DESCRIPTION
                "Reset all faults (in all modules).
                
                Practically you reset the whole system (NSU, and of all transmitters all NetCCUs, Exciters, Outputstages).
                An equivalent would be pressing RESET at the NSU frontpanel.
                
                A GET will always return idle(1). A SET idle(1) will return NO_ERROR without doing anything."
            ::= { switchoverUnit 7 }

        
        summaryFaultNSU OBJECT-TYPE
            SYNTAX TruthValue
            MAX-ACCESS read-only
            STATUS current
            DESCRIPTION
                "This indicates a summary fault of the switchover unit (NSU).
                true(1)  --> summary fault
                false(2) --> no summary fault
                
                There is a fault of at least one module (e.g. Exciter A of tx A2) which causes this summary fault.
                
                An equivalent would be the LED Fault at the NSU frontpanel."
            ::= { switchoverUnit 8 }

        
        summaryWarningNSU OBJECT-TYPE
            SYNTAX TruthValue
            MAX-ACCESS read-only
            STATUS current
            DESCRIPTION
                "This indicates a summary warning of the switchover unit (NSU).
                true(1)  --> summary warning
                false(2) --> no summary warning
                
                There is a warning of at least one module (e.g. Exciter A of tx A2) which causes this summary warning.
                
                An equivalent would be the LED Warning at the transmitters frontpanel."
            ::= { switchoverUnit 9 }

        
        localModeNSU OBJECT-TYPE
            SYNTAX TruthValue
            MAX-ACCESS read-only
            STATUS current
            DESCRIPTION
                "This indicates the local/remote-mode of the switchover unit (NSU).
                true(1)  --> local
                false(2) --> remote
                
                The NSU is eigther in local-mode or in remote-mode. 
                For security reasons it is not possible to set this value!
                
                An equivalent would the LED Local at the NSU frontpanel."
            ::= { switchoverUnit 10 }

        
        automaticReady OBJECT-TYPE
            SYNTAX TruthValue
            MAX-ACCESS read-only
            STATUS current
            DESCRIPTION
                "This indicates the state of the automatic.
                true(1)  --> ready
                false(2) --> not ready
                
                If it's ready, a switching-over (because of preselection or faults in a transmitter sending out a program) is possible."
            ::= { switchoverUnit 11 }

        
        automaticChanged OBJECT-TYPE
            SYNTAX TruthValue
            MAX-ACCESS read-only
            STATUS current
            DESCRIPTION
                "This indicates whether the automatic has switched over automatically.
                true(1)  --> switched over
                false(2) --> not switched over"
            ::= { switchoverUnit 12 }

        
        automaticFault OBJECT-TYPE
            SYNTAX TruthValue
            MAX-ACCESS read-only
            STATUS current
            DESCRIPTION
                "This indicates whether the automatic has a fault.
                true(1)  --> fault
                false(2) --> no fault"
            ::= { switchoverUnit 13 }

        
        logbookNSU OBJECT IDENTIFIER ::= { switchoverUnit 14 }

        
        nsuNumberOfEntries OBJECT-TYPE
            SYNTAX LogbookMaxEntryNumber
            MAX-ACCESS read-only
            STATUS current
            DESCRIPTION
                "The number of entries in switchover unit (NSU) logbook."
            ::= { logbookNSU 1 }

        
        nsuLogbookClear OBJECT-TYPE
            SYNTAX Trigger
            MAX-ACCESS read-write
            STATUS current
            DESCRIPTION
                "Clear logbook of the switchover unit (NSU)."
            ::= { logbookNSU 2 }

        
        nsuLogbookTable OBJECT-TYPE
            SYNTAX SEQUENCE OF NsuLogbookEntry
            MAX-ACCESS not-accessible
            STATUS current
            DESCRIPTION
                "NSU Logbook"
            ::= { logbookNSU 3 }

        
        nsuLogbookEntry OBJECT-TYPE
            SYNTAX NsuLogbookEntry
            MAX-ACCESS not-accessible
            STATUS current
            DESCRIPTION
                "A row (an entry) of a logbook."
            INDEX { nsuLogbookEntryIdx }
            ::= { nsuLogbookTable 1 }

        
        NsuLogbookEntry ::=
            SEQUENCE { 
                nsuLogbookEntryIdx
                    LogbookMaxEntryNumber,
                nsuLogbookEntryNbr
                    LogbookMaxEntryNumber,
                nsuLogbookType
                    EventClass,
                nsuLogbookSlope
                    LogbookEntrySlope,
                nsuLogbookMessage
                    LogbookEntryMessagesNSU,
                nsuLogbookDateTime
                    DateAndTime
             }

        nsuLogbookEntryIdx OBJECT-TYPE
            SYNTAX LogbookMaxEntryNumber
            MAX-ACCESS not-accessible
            STATUS current
            DESCRIPTION
                "This is an increasing number from 1 to 128. It is used as an index column for SNMP."
            ::= { nsuLogbookEntry 1 }

        
        nsuLogbookEntryNbr OBJECT-TYPE
            SYNTAX LogbookMaxEntryNumber
            MAX-ACCESS read-only
            STATUS current
            DESCRIPTION
                "This is the number of the logbook entry. It is an decreasing number from max 128 down to 1."
            ::= { nsuLogbookEntry 2 }

        
        nsuLogbookType OBJECT-TYPE
            SYNTAX EventClass
            MAX-ACCESS read-only
            STATUS current
            DESCRIPTION
                "Can either be Fault, Warning or State."
            ::= { nsuLogbookEntry 3 }

        
        nsuLogbookSlope OBJECT-TYPE
            SYNTAX LogbookEntrySlope
            MAX-ACCESS read-only
            STATUS current
            DESCRIPTION
                "Either set (event raises) or reset (event disappears)"
            ::= { nsuLogbookEntry 4 }

        
        nsuLogbookMessage OBJECT-TYPE
            SYNTAX LogbookEntryMessagesNSU
            MAX-ACCESS read-only
            STATUS current
            DESCRIPTION
                "See RS-XX8000-COMMON-MIB - TextualConvention - LogbookEntryMessagesNSU for details."
            ::= { nsuLogbookEntry 5 }

        
        nsuLogbookDateTime OBJECT-TYPE
            SYNTAX DateAndTime
            MAX-ACCESS read-only
            STATUS current
            DESCRIPTION
                "The time of the logbook entry."
            ::= { nsuLogbookEntry 6 }

        
        loadedTx OBJECT-TYPE
            SYNTAX IndexTransmitter
            MAX-ACCESS read-only
            STATUS current
            DESCRIPTION
                "The actual loaded Tx."
            ::= { switchoverUnit 15 }

        
        powerSupply OBJECT-TYPE
            SYNTAX FloatingPoint
            UNITS "volt"
            MAX-ACCESS read-only
            STATUS current
            DESCRIPTION
                "Monitoring value of the output voltages of the NSU power supply."
            ::= { switchoverUnit 19 }

        
        additionalPowerSupply OBJECT-TYPE
            SYNTAX TruthValue
            MAX-ACCESS read-only
            STATUS current
            DESCRIPTION
                "Shows whether the NSU has an additional (external) power supply."
            ::= { switchoverUnit 20 }

        
        internalPowerSupply OBJECT-TYPE
            SYNTAX FloatingPoint
            UNITS "volt"
            MAX-ACCESS read-only
            STATUS current
            DESCRIPTION
                "Monitoring value of the output voltages of the NSU internal power supply."
            ::= { switchoverUnit 21 }

        
        externalPowerSupply OBJECT-TYPE
            SYNTAX FloatingPoint
            UNITS "volt"
            MAX-ACCESS read-only
            STATUS current
            DESCRIPTION
                "Monitoring value of the output voltages of the NSU external power supply."
            ::= { switchoverUnit 22 }

        
        nsuProductInfoTable OBJECT-TYPE
            SYNTAX SEQUENCE OF NsuProductInfoEntry
            MAX-ACCESS not-accessible
            STATUS current
            DESCRIPTION
                "The table for product typeplates."
            ::= { switchoverUnit 100 }

        
        nsuProductInfoEntry OBJECT-TYPE
            SYNTAX NsuProductInfoEntry
            MAX-ACCESS not-accessible
            STATUS current
            DESCRIPTION
                "An entry (conceptual row) in the nsuProductInfoTable."
            INDEX { nsuProdInfoModuleIdx, nsuProdInfoTxIdx }
            ::= { nsuProductInfoTable 1 }

        
        NsuProductInfoEntry ::=
            SEQUENCE { 
                nsuProdInfoModuleIdx
                    ProdInfoModuleNameNsu,
                nsuProdInfoTxIdx
                    IndexTransmitter,
                nsuProdInfoModuleName
                    ProdInfoModuleNameNsu,
                nsuProdInfoSerialNumber
                    ReadableString,
                nsuProdInfoIdentNumberSW
                    ReadableString,
                nsuProdInfoVersionNumberSW
                    ReadableString,
                nsuProdInfoIdentNumberHW
                    ReadableString,
                nsuProdInfoVersionNumberHW
                    ReadableString,
                nsuProductInfoProductDateHW
                    DateAndTime
             }

        nsuProdInfoModuleIdx OBJECT-TYPE
            SYNTAX ProdInfoModuleNameNsu
            MAX-ACCESS not-accessible
            STATUS current
            DESCRIPTION
                "The module index."
            ::= { nsuProductInfoEntry 1 }

        
        nsuProdInfoTxIdx OBJECT-TYPE
            SYNTAX IndexTransmitter
            MAX-ACCESS not-accessible
            STATUS current
            DESCRIPTION
                "The transmitter index."
            ::= { nsuProductInfoEntry 2 }

        
        nsuProdInfoModuleName OBJECT-TYPE
            SYNTAX ProdInfoModuleNameNsu
            MAX-ACCESS read-only
            STATUS current
            DESCRIPTION
                "The name of the module as a text."
            ::= { nsuProductInfoEntry 6 }

        
        nsuProdInfoSerialNumber OBJECT-TYPE
            SYNTAX ReadableString
            MAX-ACCESS read-only
            STATUS current
            DESCRIPTION
                "The serial number of the subdevice."
            ::= { nsuProductInfoEntry 7 }

        
        nsuProdInfoIdentNumberSW OBJECT-TYPE
            SYNTAX ReadableString
            MAX-ACCESS read-only
            STATUS current
            DESCRIPTION
                "The Rohde&Schwarz identification number of the software, for example 2094.2090.02."
            ::= { nsuProductInfoEntry 8 }

        
        nsuProdInfoVersionNumberSW OBJECT-TYPE
            SYNTAX ReadableString
            MAX-ACCESS read-only
            STATUS current
            DESCRIPTION
                "The Rohde&Schwarz revision number of the software, for example 1.2.1."
            ::= { nsuProductInfoEntry 9 }

        
        nsuProdInfoIdentNumberHW OBJECT-TYPE
            SYNTAX ReadableString
            MAX-ACCESS read-only
            STATUS current
            DESCRIPTION
                "The Rohde&Schwarz identification number of the hardware, for example 2095.8007.02 (NetCCU)."
            ::= { nsuProductInfoEntry 10 }

        
        nsuProdInfoVersionNumberHW OBJECT-TYPE
            SYNTAX ReadableString
            MAX-ACCESS read-only
            STATUS current
            DESCRIPTION
                "The Rohde&Schwarz revision number (product index) of the hardware, for example 03.03."
            ::= { nsuProductInfoEntry 11 }

        
        nsuProductInfoProductDateHW OBJECT-TYPE
            SYNTAX DateAndTime
            MAX-ACCESS read-only
            STATUS current
            DESCRIPTION
                "The Rohde&Schwarz production date of the hardware,"
            ::= { nsuProductInfoEntry 12 }

        
-- *****************************************************************************
-- **          program (logical) view
-- *****************************************************************************
        program OBJECT IDENTIFIER ::= { rsXx8000FmNp1Objs 2 }

        
        programTable OBJECT-TYPE
            SYNTAX SEQUENCE OF ProgramEntry
            MAX-ACCESS not-accessible
            STATUS current
            DESCRIPTION
                "This table contents important values for programs
                (independent of which physical tx is sending out the program)."
            ::= { program 1 }

        
        programEntry OBJECT-TYPE
            SYNTAX ProgramEntry
            MAX-ACCESS not-accessible
            STATUS current
            DESCRIPTION
                "An entry for a designated program."
            INDEX { programIdx }
            ::= { programTable 1 }

        
        ProgramEntry ::=
            SEQUENCE { 
                programIdx
                    IndexProgram,
                programPriority
                    Integer32,
                programOperationMode
                    SwitchOnOff,
                programRfOn
                    TruthValue
             }

        programIdx OBJECT-TYPE
            SYNTAX IndexProgram
            MAX-ACCESS not-accessible
            STATUS current
            DESCRIPTION
                "The program index. There are max. 8 main programs, if you have 8 main transmitters.
                Additionally, there is a reserve program programRes(1)."
            ::= { programEntry 1 }

        
        programPriority OBJECT-TYPE
            SYNTAX Integer32 (0..8)
            MAX-ACCESS read-write
            STATUS current
            DESCRIPTION
                "The priority for the program. 
                The value 0 means no priority given. The value 1 means highest priority.
                You must switch on OID operationModePriority for using priorities.
                The reserve program has no priority (agent return not-accessible)."
            ::= { programEntry 2 }

        
        programOperationMode OBJECT-TYPE
            SYNTAX SwitchOnOff
            MAX-ACCESS read-write
            STATUS current
            DESCRIPTION
                "This switches the program on or off."
            ::= { programEntry 3 }

        
        programRfOn OBJECT-TYPE
            SYNTAX TruthValue
            MAX-ACCESS read-only
            STATUS current
            DESCRIPTION
                "The RF is present for the corresponding program 
                (independent of which physical tx is sending out the program)."
            ::= { programEntry 4 }

        
-- *****************************************************************************
-- **          transmitter (physical) view
-- *****************************************************************************
        transmitter OBJECT IDENTIFIER ::= { rsXx8000FmNp1Objs 3 }

        
        commandsTxTable OBJECT-TYPE
            SYNTAX SEQUENCE OF CommandsTxEntry
            MAX-ACCESS not-accessible
            STATUS current
            DESCRIPTION
                "This table contents important commands for (physical) transmitters
                (independent of which tx is sending out the program).
                The reserve transmitter (TxB) always is shown as the first line of a table."
            ::= { transmitter 1 }

        
        commandsTxEntry OBJECT-TYPE
            SYNTAX CommandsTxEntry
            MAX-ACCESS not-accessible
            STATUS current
            DESCRIPTION
                "An entry for a designated transmitter and device."
            INDEX { cmdTxIdx, cmdDeviceIdx }
            ::= { commandsTxTable 1 }

        
        CommandsTxEntry ::=
            SEQUENCE { 
                cmdTxIdx
                    IndexTransmitter,
                cmdTxName
                    IndexTransmitter,
                cmdTxResetSumFault
                    Trigger,
                cmdTxParametersetLoad
                    Integer32,
                cmdTxParametersetSave
                    Integer32,
                cmdTxParametersetReSave
                    Trigger,
                cmdTxOperationModeProgram
                    SwitchOnOff,
                cmdTxOperationModeReserve
                    SwitchOnOff,
                cmdTxOpModeExcAutomatic
                    SwitchOnOff,
                cmdTxPreselectExciter
                    IndexAB,
                cmdTxDelayTimeExcAutomatic
                    Integer32,
                cmdDeviceIdx
                    IndexAB,
                cmdExcReset
                    Trigger,
                cmdExcRFOnOff
                    SwitchOnOff,
                cmdExcNoInputSeverity
                    INTEGER,
                cmdExcNoInputFailDelay
                    Integer32,
                cmdExcInputLevelAnalog
                    FloatingPoint,
                cmdExcInputLevelMPX
                    FloatingPoint,
                cmdExcInputLevelAES
                    FloatingPoint,
                cmdExcAnalogImpedance
                    INTEGER,
                cmdExcMPXImpedance
                    INTEGER,
                cmdExcAFThreshold
                    FloatingPoint,
                cmdExcAFOnTime
                    Integer32,
                cmdExcAFOffTime
                    Integer32,
                cmdExcAFThresholddBu
                    FloatingPoint,
                cmdExcMPXThreshold
                    FloatingPoint,
                cmdExcMPXOnTime
                    Integer32,
                cmdExcMPXOffTime
                    Integer32,
                cmdExcMPXThresholddBu
                    FloatingPoint,
                cmdExcAESThreshold
                    FloatingPoint,
                cmdExcAESOnTime
                    Integer32,
                cmdExcAESOffTime
                    Integer32,
                cmdExcAESThresholddBFs
                    FloatingPoint,
                cmdExcInputLevelAUX1
                    FloatingPoint,
                cmdExcInputLevelAUX2
                    FloatingPoint,
                cmdExcInputLevelAUX3
                    FloatingPoint,
                cmdExcDeviationAUX1
                    FloatingPoint,
                cmdExcDeviationAUX2
                    FloatingPoint,
                cmdExcDeviationAUX3
                    FloatingPoint,
                cmdExcActivateAUX1
                    SwitchOnOff,
                cmdExcActivateAUX2
                    SwitchOnOff,
                cmdExcActivateAUX3
                    SwitchOnOff,
                cmdExcAUX1Threshold
                    FloatingPoint,
                cmdExcAUX1ThresholddB
                    FloatingPoint,
                cmdExcAUX1OnTime
                    Integer32,
                cmdExcAUX1OffTime
                    Integer32,
                cmdExcAUX2Threshold
                    FloatingPoint,
                cmdExcAUX2ThresholddB
                    FloatingPoint,
                cmdExcAUX2OnTime
                    Integer32,
                cmdExcAUX2OffTime
                    Integer32,
                cmdExcAUX3Threshold
                    FloatingPoint,
                cmdExcAUX3ThresholddB
                    FloatingPoint,
                cmdExcAUX3OnTime
                    Integer32,
                cmdExcAUX3OffTime
                    Integer32,
                cmdExcCH1ModType
                    INTEGER,
                cmdExcCH2ModType
                    INTEGER,
                cmdExcModSelection
                    INTEGER,
                cmdExcDeviation
                    Integer32,
                cmdExcDeviationLimit
                    Integer32,
                cmdExcActivateDeviationLimiter
                    INTEGER,
                cmdExcPreemphasis
                    INTEGER,
                cmdExcActivatePreemphasis
                    SwitchOnOff,
                cmdExcPilotDeviation
                    FloatingPoint,
                cmdExcActivatePilot
                    SwitchOnOff,
                cmdExcMPXPowerLimit
                    FloatingPoint,
                cmdExcActivateMPXPowerLimiter
                    SwitchOnOff,
                cmdExcFrequency
                    FloatingPoint,
                cmdExcRefSource
                    INTEGER,
                cmdExcTCXOTrim
                    FloatingPoint,
                cmdLpTxTransmitterId
                    ReadableString,
                cmdLpTxRfWarningThreshold
                    FloatingPoint,
                cmdLpTxRfFaultThreshold
                    FloatingPoint,
                cmdOstRefVoltage
                    FloatingPoint,
                cmdOstMaxOutletTempThreshold
                    Integer32
             }

        cmdTxIdx OBJECT-TYPE
            SYNTAX IndexTransmitter
            MAX-ACCESS not-accessible
            STATUS current
            DESCRIPTION
                "The transmitter index. There are max. 8 transmitters, if you have an 8+1 system."
            ::= { commandsTxEntry 1 }

        
        cmdTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { commandsTxEntry 2 }

        
        cmdTxResetSumFault OBJECT-TYPE
            SYNTAX Trigger
            MAX-ACCESS read-write
            STATUS current
            DESCRIPTION
                "Reset all faults (in all modules) of the transmitter.
                
                You reset a designated transmitter (NetCCU, Exciters, Outputstages).
                An equivalent would be pressing RESET at this transmitters frontpanel.
                
                A GET will always return idle(1). A SET idle(1) will return NO_ERROR without doing anything."
            ::= { commandsTxEntry 3 }

        
        cmdTxParametersetLoad OBJECT-TYPE
            SYNTAX Integer32 (1..8)
            MAX-ACCESS read-write
            STATUS current
            DESCRIPTION
                "This loads the desired parameter set."
            ::= { commandsTxEntry 4 }

        
        cmdTxParametersetSave OBJECT-TYPE
            SYNTAX Integer32 (1..8)
            MAX-ACCESS read-write
            STATUS current
            DESCRIPTION
                "This saves the current settings to a designated parameter set."
            ::= { commandsTxEntry 5 }

        
        cmdTxParametersetReSave OBJECT-TYPE
            SYNTAX Trigger
            MAX-ACCESS read-write
            STATUS obsolete
            DESCRIPTION
                "This saves the changes to the current parameter set."
            ::= { commandsTxEntry 6 }

        
        cmdTxOperationModeProgram OBJECT-TYPE
            SYNTAX SwitchOnOff
            MAX-ACCESS read-write
            STATUS current
            DESCRIPTION
                "This switches the program path of the transmitter on/off."
            ::= { commandsTxEntry 7 }

        
        cmdTxOperationModeReserve OBJECT-TYPE
            SYNTAX SwitchOnOff
            MAX-ACCESS read-write
            STATUS current
            DESCRIPTION
                "This switches the reserve path of the transmitter on/off."
            ::= { commandsTxEntry 8 }

        
        cmdTxOpModeExcAutomatic OBJECT-TYPE
            SYNTAX SwitchOnOff
            MAX-ACCESS read-write
            STATUS current
            DESCRIPTION
                "This switches the exciter automatic on/off."
            ::= { commandsTxEntry 9 }

        
        cmdTxPreselectExciter OBJECT-TYPE
            SYNTAX IndexAB
            MAX-ACCESS read-write
            STATUS current
            DESCRIPTION
                "This sets exciterA or exciterB to program path (antenna) of the transmitter."
            ::= { commandsTxEntry 11 }

        
        cmdTxDelayTimeExcAutomatic OBJECT-TYPE
            SYNTAX Integer32 (1..60)
            UNITS "seconds"
            MAX-ACCESS read-write
            STATUS current
            DESCRIPTION
                "This sets the exciter automatic delay time."
            ::= { commandsTxEntry 13 }

        
        cmdDeviceIdx OBJECT-TYPE
            SYNTAX IndexAB
            MAX-ACCESS not-accessible
            STATUS current
            DESCRIPTION
                "This column is used to show parameters for both exiters, if you have 
                dualdrive transmitters."
            ::= { commandsTxEntry 30 }

        
        cmdExcReset OBJECT-TYPE
            SYNTAX Trigger
            MAX-ACCESS read-write
            STATUS current
            DESCRIPTION
                "Reset all Exciter faults:
                idle(1)    --> ready, do nothing
                trigger(2) --> do now
                    
                A GET will always return idle(1). 
                A SET idle(1) will return NO_ERROR without doing anything.
                "
            ::= { commandsTxEntry 31 }

        
        cmdExcRFOnOff OBJECT-TYPE
            SYNTAX SwitchOnOff
            MAX-ACCESS read-write
            STATUS current
            DESCRIPTION
                "Switches the RF on/off. It has the same behaviour as the switch 
                on the front panel of the exciter. This setting is only editable, 
                if there is no NetCCU connected!"
            ::= { commandsTxEntry 32 }

        
        cmdExcNoInputSeverity OBJECT-TYPE
            SYNTAX INTEGER
                {
                warning(1),
                fail(2)
                }
            MAX-ACCESS read-write
            STATUS current
            DESCRIPTION
                "If WARNING is selected only a warning is produced when the 
                input signal is no longer present. If FAULT is selected an 
                additional sum fault is produced after the fail delay time. 
                This will cause a switchover to a reserve exciter. "
            ::= { commandsTxEntry 33 }

        
        cmdExcNoInputFailDelay OBJECT-TYPE
            SYNTAX Integer32 (0..600)
            UNITS "sec"
            MAX-ACCESS read-write
            STATUS current
            DESCRIPTION
                "Adjust the time between detecting a loss of input signal and raising a failure."
            ::= { commandsTxEntry 34 }

        
        cmdExcInputLevelAnalog OBJECT-TYPE
            SYNTAX FloatingPoint
            UNITS "dBu"
            MAX-ACCESS read-write
            STATUS current
            DESCRIPTION
                "Selects the input level for the analog audio input (-6.0 ... 12.0). 
                A 500Hz sinusoidal tone with this input level will cause the 
                reference deviation in the output signal.Note: If preemphasis 
                is on, the nominal input level is not equal to the real signal 
                level due to the preemphasis gain."
            ::= { commandsTxEntry 35 }

        
        cmdExcInputLevelMPX OBJECT-TYPE
            SYNTAX FloatingPoint
            UNITS "dBu"
            MAX-ACCESS read-write
            STATUS current
            DESCRIPTION
                "Selects the input level for MPX (composite) input (-1.0 ... 16.0). 
                This input level will cause the reference deviation in the output signal. "
            ::= { commandsTxEntry 36 }

        
        cmdExcInputLevelAES OBJECT-TYPE
            SYNTAX FloatingPoint
            UNITS "dBFS"
            MAX-ACCESS read-write
            STATUS current
            DESCRIPTION
                "Selects the input level for the AES/EBU audio input (-15.0 ... 0.0). 
                A 500Hz sinusoidal tone with this input level will cause the 
                reference deviation in the output signal.
                Note: If preemphasis is on, the nominal input level is not 
                equal to the real signal level due to the preemphasis gain."
            ::= { commandsTxEntry 37 }

        
        cmdExcAnalogImpedance OBJECT-TYPE
            SYNTAX INTEGER
                {
                ohm600(1),
                ohmGreaterThan2000(2)
                }
            MAX-ACCESS read-write
            STATUS current
            DESCRIPTION
                "Selects the input impedance for analog inputs. 
                Usually it is > 2000 Ohms."
            ::= { commandsTxEntry 38 }

        
        cmdExcMPXImpedance OBJECT-TYPE
            SYNTAX INTEGER
                {
                ohm600(1),
                ohmGreaterThan2000(2)
                }
            MAX-ACCESS read-write
            STATUS current
            DESCRIPTION
                "Selects the input impedance for MPX (composite) inputs. 
                Usually it is > 2000 Ohms. The device uses this impedance 
                even if it is modulated with MPX from input 2 or input 3."
            ::= { commandsTxEntry 39 }

        
        cmdExcAFThreshold OBJECT-TYPE
            SYNTAX FloatingPoint
            UNITS "perCent"
            MAX-ACCESS read-write
            STATUS current
            DESCRIPTION
                "Threshold for AF signal monitoring (2.0 ... 80.0). 
                This threshold can be set as a percentage of the nominal 
                level or as an absolute value in dBu. The internal logic 
                uses the percent value. If the level input was in dBu, 
                it will be rounded to the nearest integer percent value."
            ::= { commandsTxEntry 40 }

        
        cmdExcAFOnTime OBJECT-TYPE
            SYNTAX Integer32 (1..6000)
            UNITS "sec"
            MAX-ACCESS read-write
            STATUS current
            DESCRIPTION
                "The signal state is OK, if the signal level above 
                the threshold for at least this time period."
            ::= { commandsTxEntry 41 }

        
        cmdExcAFOffTime OBJECT-TYPE
            SYNTAX Integer32 (1..6000)
            UNITS "sec"
            MAX-ACCESS read-write
            STATUS current
            DESCRIPTION
                "The signal state is not OK, if the signal level below 
                the threshold for at least this time period."
            ::= { commandsTxEntry 42 }

        
        cmdExcAFThresholddBu OBJECT-TYPE
            SYNTAX FloatingPoint
            UNITS "dBu"
            MAX-ACCESS read-write
            STATUS current
            DESCRIPTION
                "Threshold for AF signal monitoring (-100.0 ... 12.0). 
                This threshold can be set as a percentage of the nominal 
                level or as an absolute value in dBu. The internal logic 
                uses the percent value. If the level input was in dBu, 
                it will be rounded to the nearest integer percent value."
            ::= { commandsTxEntry 43 }

        
        cmdExcMPXThreshold OBJECT-TYPE
            SYNTAX FloatingPoint
            UNITS "perCent"
            MAX-ACCESS read-write
            STATUS current
            DESCRIPTION
                "Threshold for MPX (composite) signal monitoring (2.0 ... 80.0). 
                This threshold can be set as a percentage of the nominal level 
                or as an absolute value in dBu. The internal logic uses the 
                percent value. If the level input was in dBu, it will be rounded 
                to the nearest integer percent value."
            ::= { commandsTxEntry 44 }

        
        cmdExcMPXOnTime OBJECT-TYPE
            SYNTAX Integer32 (1..6000)
            UNITS "sec"
            MAX-ACCESS read-write
            STATUS current
            DESCRIPTION
                "The signal state is OK, if the signal level above 
                the threshold for at least this time period."
            ::= { commandsTxEntry 45 }

        
        cmdExcMPXOffTime OBJECT-TYPE
            SYNTAX Integer32 (1..6000)
            UNITS "sec"
            MAX-ACCESS read-write
            STATUS current
            DESCRIPTION
                "The signal state is not OK, if the signal level below 
                the threshold for at least this time period."
            ::= { commandsTxEntry 46 }

        
        cmdExcMPXThresholddBu OBJECT-TYPE
            SYNTAX FloatingPoint
            UNITS "dBu"
            MAX-ACCESS read-write
            STATUS current
            DESCRIPTION
                "Threshold for MPX (composite) signal monitoring (-100.0 ... 16.0). 
                This threshold can be set as a percentage of the nominal level 
                or as an absolute value in dBu. The internal logic uses the 
                percent value. If the level input was in dBu, it will be rounded 
                to the nearest integer percent value."
            ::= { commandsTxEntry 47 }

        
        cmdExcAESThreshold OBJECT-TYPE
            SYNTAX FloatingPoint
            UNITS "perCent"
            MAX-ACCESS read-write
            STATUS current
            DESCRIPTION
                "Threshold for audio signal monitoring (2.0 ... 80.0), 
                i.e. the monitoring of the audio levels within the AES signal.
                This threshold can be set as a percentage of the nominal level or as an absolute value in dBFs. 
                The internal logic uses the percent value. If the level input was 
                in dBFs, it will be rounded to the nearest integer percent value."
            ::= { commandsTxEntry 48 }

        
        cmdExcAESOnTime OBJECT-TYPE
            SYNTAX Integer32 (1..6000)
            UNITS "sec"
            MAX-ACCESS read-write
            STATUS current
            DESCRIPTION
                "The signal state is OK, if the signal level is above 
                the threshold for at least this time period."
            ::= { commandsTxEntry 49 }

        
        cmdExcAESOffTime OBJECT-TYPE
            SYNTAX Integer32 (1..6000)
            UNITS "sec"
            MAX-ACCESS read-write
            STATUS current
            DESCRIPTION
                "The signal state is not OK, if the signal level is below 
                the threshold for at least this time period."
            ::= { commandsTxEntry 50 }

        
        cmdExcAESThresholddBFs OBJECT-TYPE
            SYNTAX FloatingPoint
            UNITS "dBFS"
            MAX-ACCESS read-write
            STATUS current
            DESCRIPTION
                "Threshold for audio signal monitoring (-100.0 ... 0.0),
                i.e. the monitoring of the audio levels within the AES signal.
                This threshold can be set as a percentage of the nominal level or as an absolute value in dBFs.
                The internal logic uses the percent value.
                If the level input was in dBFs, it will be rounded to the nearest integer percent value."
            ::= { commandsTxEntry 51 }

        
        cmdExcInputLevelAUX1 OBJECT-TYPE
            SYNTAX FloatingPoint
            UNITS "dBu"
            MAX-ACCESS read-write
            STATUS current
            DESCRIPTION
                "Selects the input level for the AUX1 input (-18.0 ... -7.0). 
                A 60 kHz sinusoidal tone with this input level will cause 
                the nominal deviation for this input in the output signal. "
            ::= { commandsTxEntry 52 }

        
        cmdExcInputLevelAUX2 OBJECT-TYPE
            SYNTAX FloatingPoint
            UNITS "dBu"
            MAX-ACCESS read-write
            STATUS current
            DESCRIPTION
                "Selects the input level for the AUX2 input (-18.0 ... -7.0). 
                A 60 kHz sinusoidal tone with this input level will cause 
                the nominal deviation for this input in the output signal. "
            ::= { commandsTxEntry 53 }

        
        cmdExcInputLevelAUX3 OBJECT-TYPE
            SYNTAX FloatingPoint
            UNITS "dBu"
            MAX-ACCESS read-write
            STATUS current
            DESCRIPTION
                "Selects the input level for the AUX3 input (-18.0 ... -7.0). 
                A 60 kHz sinusoidal tone with this input level will cause 
                the nominal deviation for this input in the output signal. "
            ::= { commandsTxEntry 54 }

        
        cmdExcDeviationAUX1 OBJECT-TYPE
            SYNTAX FloatingPoint
            UNITS "kHz"
            MAX-ACCESS read-write
            STATUS current
            DESCRIPTION
                "Selects the nominal deviation for the AUX1 input (2.0 ... 10.0). 
                A 60 kHz sinusoidal tone with the nominal input level will 
                cause this deviation in the output signal. "
            ::= { commandsTxEntry 55 }

        
        cmdExcDeviationAUX2 OBJECT-TYPE
            SYNTAX FloatingPoint
            UNITS "kHz"
            MAX-ACCESS read-write
            STATUS current
            DESCRIPTION
                "Selects the nominal deviation for AUX2 input (2.0 ... 10.0). 
                A 60 kHz sinusoidal tone with the nominal input level will cause 
                this deviation in the output signal. "
            ::= { commandsTxEntry 56 }

        
        cmdExcDeviationAUX3 OBJECT-TYPE
            SYNTAX FloatingPoint
            UNITS "kHz"
            MAX-ACCESS read-write
            STATUS current
            DESCRIPTION
                "Selects the nominal deviation for AUX3 input (2.0 ... 10.0). 
                A 60 kHz sinusoidal tone with the nominal input level 
                will cause this deviation in the output signal. "
            ::= { commandsTxEntry 57 }

        
        cmdExcActivateAUX1 OBJECT-TYPE
            SYNTAX SwitchOnOff
            MAX-ACCESS read-write
            STATUS current
            DESCRIPTION
                "Activate AUX1 input. 
                If activated, the signal on AUX1 is added to the internal MPX. 
                Undershooting of the threshold will be logged and reflected in 
                the system state."
            ::= { commandsTxEntry 58 }

        
        cmdExcActivateAUX2 OBJECT-TYPE
            SYNTAX SwitchOnOff
            MAX-ACCESS read-write
            STATUS current
            DESCRIPTION
                "Activate AUX2 input. 
                If activated, the signal on AUX2 is added to the internal MPX. 
                Undershooting of the threshold will be logged and reflected in 
                the system state."
            ::= { commandsTxEntry 59 }

        
        cmdExcActivateAUX3 OBJECT-TYPE
            SYNTAX SwitchOnOff
            MAX-ACCESS read-write
            STATUS current
            DESCRIPTION
                "Activate AUX3 input. 
                If activated, the signal on AUX3 is added to the internal MPX. 
                Undershooting of the threshold will be logged and reflected 
                in the system state."
            ::= { commandsTxEntry 60 }

        
        cmdExcAUX1Threshold OBJECT-TYPE
            SYNTAX FloatingPoint
            UNITS "perCent"
            MAX-ACCESS read-write
            STATUS current
            DESCRIPTION
                "Threshold for AUX1 input monitoring (2.0 ... 100.0). 
                This threshold can be set as a percentage of the nominal 
                level or as an absolute value in dBu. The internal logic 
                uses the percent value. If the level input was in dBu, 
                it will be rounded to the nearest integer percent value."
            ::= { commandsTxEntry 61 }

        
        cmdExcAUX1ThresholddB OBJECT-TYPE
            SYNTAX FloatingPoint
            UNITS "dBu"
            MAX-ACCESS read-write
            STATUS current
            DESCRIPTION
                "Threshold for AUX1 input monitoring (-100.0 ... -7.0). 
                This threshold can be set as a percentage of the nominal 
                level or as an absolute value in dBu. The internal logic 
                uses the percent value. If the level input was in dBu, 
                it will be rounded to the nearest integer percent value."
            ::= { commandsTxEntry 62 }

        
        cmdExcAUX1OnTime OBJECT-TYPE
            SYNTAX Integer32 (1..6000)
            UNITS "sec"
            MAX-ACCESS read-write
            STATUS current
            DESCRIPTION
                "The signal state is OK, if the signal level is above 
                the threshold for at least this time period."
            ::= { commandsTxEntry 63 }

        
        cmdExcAUX1OffTime OBJECT-TYPE
            SYNTAX Integer32 (1..6000)
            UNITS "sec"
            MAX-ACCESS read-write
            STATUS current
            DESCRIPTION
                "The signal state is not OK, if the signal level is below 
                the threshold for at least this time period."
            ::= { commandsTxEntry 64 }

        
        cmdExcAUX2Threshold OBJECT-TYPE
            SYNTAX FloatingPoint
            UNITS "perCent"
            MAX-ACCESS read-write
            STATUS current
            DESCRIPTION
                "Threshold for AUX2 input monitoring (2.0 ... 100.0). 
                This threshold can be set as a percentage of the nominal level 
                or as an absolute value in dBu. The internal logic uses the percent 
                value. If the level input was in dBu, it will be rounded to the 
                nearest integer percent value."
            ::= { commandsTxEntry 65 }

        
        cmdExcAUX2ThresholddB OBJECT-TYPE
            SYNTAX FloatingPoint
            UNITS "dBu"
            MAX-ACCESS read-write
            STATUS current
            DESCRIPTION
                "Threshold for AUX2 input monitoring (-100.0 ... -7.0). 
                This threshold can be set as a percentage of the nominal level 
                or as an absolute value in dBu. The internal logic uses the 
                percent value. If the level input was in dBu, it will be rounded 
                to the nearest integer percent value."
            ::= { commandsTxEntry 66 }

        
        cmdExcAUX2OnTime OBJECT-TYPE
            SYNTAX Integer32 (1..6000)
            UNITS "sec"
            MAX-ACCESS read-write
            STATUS current
            DESCRIPTION
                "The signal state is OK, if the signal level is above 
                the threshold for at least this time period"
            ::= { commandsTxEntry 67 }

        
        cmdExcAUX2OffTime OBJECT-TYPE
            SYNTAX Integer32 (1..6000)
            UNITS "sec"
            MAX-ACCESS read-write
            STATUS current
            DESCRIPTION
                "The signal state is not OK, if the signal level below 
                the threshold for at least this time period"
            ::= { commandsTxEntry 68 }

        
        cmdExcAUX3Threshold OBJECT-TYPE
            SYNTAX FloatingPoint
            UNITS "perCent"
            MAX-ACCESS read-write
            STATUS current
            DESCRIPTION
                "Threshold for AUX3 input monitoring (2.0 ... 100.0). 
                This threshold can be set as a percentage of the nominal level 
                or as an absolute value in dBu. The internal logic uses the 
                percent value. If the level input was in dBu, it will be rounded 
                to the nearest integer percent value."
            ::= { commandsTxEntry 69 }

        
        cmdExcAUX3ThresholddB OBJECT-TYPE
            SYNTAX FloatingPoint
            UNITS "dBu"
            MAX-ACCESS read-write
            STATUS current
            DESCRIPTION
                "Threshold for AUX1 input monitoring (-100.0 ... -7.0). 
                This threshold can be set as a percentage of the nominal level 
                or as an absolute value in dBu. The internal logic uses the 
                percent value. If the level input was in dBu, it will be rounded 
                to the nearest integer percent value."
            ::= { commandsTxEntry 70 }

        
        cmdExcAUX3OnTime OBJECT-TYPE
            SYNTAX Integer32 (1..6000)
            UNITS "sec"
            MAX-ACCESS read-write
            STATUS current
            DESCRIPTION
                "The signal state is OK, if the signal level above 
                the threshold for at least this time period."
            ::= { commandsTxEntry 71 }

        
        cmdExcAUX3OffTime OBJECT-TYPE
            SYNTAX Integer32 (1..6000)
            UNITS "sec"
            MAX-ACCESS read-write
            STATUS current
            DESCRIPTION
                "The signal state is not OK, if the signal level below 
                the threshold for at least this time period."
            ::= { commandsTxEntry 72 }

        
        cmdExcCH1ModType OBJECT-TYPE
            SYNTAX INTEGER
                {
                afMonoL(1),
                afMonoR(2),
                afMonoLR(3),
                afStereo(4),
                aesMonoL(5),
                aesMonoR(6),
                aesMonoLR(7),
                aesStereo(8),
                mpxInp2(9),
                mpxInp3(10)
                }
            MAX-ACCESS read-write
            STATUS current
            DESCRIPTION
                "Selects the audio modulation source for the primary input channel. 
                It must be a different input source from the secondary channel. 
                It can be either digital (AES/EBU) or analog (AF or Composite). 
                For AF and AES/EBU (Input 3) you can select between Mono Right (Input 1) 
                or Mono Left (Input 2), Mono Left + Right and Stereo. Composite (MPX) 
                can only selected once, either for the primary or the secondary channel. 
                For Composite (MPX) you can select between Input 2 and Input 3. 
                Note: 
                Invalid combinations for primary and secondary channel are automatically 
                masked out. If the desired mode is not available, try setting the 
                secondary channel to 'Not Used'."
            ::= { commandsTxEntry 73 }

        
        cmdExcCH2ModType OBJECT-TYPE
            SYNTAX INTEGER
                {
                afMonoL(1),
                afMonoR(2),
                afMonoLR(3),
                afStereo(4),
                aesMonoL(5),
                aesMonoR(6),
                aesMonoLR(7),
                aesStereo(8),
                mpxInp2(9),
                mpxInp3(10),
                notUsed(11)
                }
            MAX-ACCESS read-write
            STATUS current
            DESCRIPTION
                "Selects the audio modulation source for the secondary input channel. 
                If defined, it must be a different input source from the primary channel. 
                It can be either digital (AES/EBU) or analog (AF or Composite). 
                For AF and AES/EBU (Input 3) you can select between Mono Right (Input 1) 
                or Mono Left (Input 2), Mono Left + Right and Stereo. Composite (MPX) 
                can only selected once, either for the primary or the secondary channel. 
                For Composite (MPX) you can select between Input 2 and Input 3. 
                Note: 
                Invalid combinations for primary and secondary channel are 
                automatically masked out."
            ::= { commandsTxEntry 74 }

        
        cmdExcModSelection OBJECT-TYPE
            SYNTAX INTEGER
                {
                ch1(1),
                ch2(2),
                autoSelect(3)
                }
            MAX-ACCESS read-write
            STATUS current
            DESCRIPTION
                "Select the input channel for audio modulation. 
                If a second channel is defined, the option 'Auto' and 'Ch.2' is available. 
                In this mode, the device switches automatically to the primary channel 
                if it is OK, if the primary channel is not OK and if the secondary 
                channel is OK, than it switches to the secondary channel. 
                It will automatically switch back as soon as the primary channel is OK 
                again. If both channels are not OK, it switches to the primary channel."
            ::= { commandsTxEntry 75 }

        
        cmdExcDeviation OBJECT-TYPE
            SYNTAX Integer32 (40..150)
            UNITS "kHz"
            MAX-ACCESS read-write
            STATUS current
            DESCRIPTION
                "Adjusts the nominal deviation (this will be the deviation 
                for a 500Hz sinusoid with the nominal input level defined 
                for the selected modulation type).$Note1: It is not used 
                in MPX mode. 
                Note2: 
                If preemphasis is on, the nominal input level is not equal 
                to the real signal level due to the preemphasis gain."
            ::= { commandsTxEntry 76 }

        
        cmdExcDeviationLimit OBJECT-TYPE
            SYNTAX Integer32 (40..150)
            UNITS "kHz"
            MAX-ACCESS read-write
            STATUS current
            DESCRIPTION
                "Defines the threshold for the deviation limiter. 
                The limiter must be active for the threshold to take effect."
            ::= { commandsTxEntry 77 }

        
        cmdExcActivateDeviationLimiter OBJECT-TYPE
            SYNTAX INTEGER
                {
                off(1),
                on(2),
                clipperonly(3)
                }
            MAX-ACCESS read-write
            STATUS current
            DESCRIPTION
                "Switches the deviation limiter on or off."
            ::= { commandsTxEntry 78 }

        
        cmdExcPreemphasis OBJECT-TYPE
            SYNTAX INTEGER
                {
                us50(1),
                us75(2)
                }
            MAX-ACCESS read-write
            STATUS current
            DESCRIPTION
                "Selects the preemphasis, either 50 us or 75 us. 
                This setting is only effective if preemphasis is active."
            ::= { commandsTxEntry 79 }

        
        cmdExcActivatePreemphasis OBJECT-TYPE
            SYNTAX SwitchOnOff
            MAX-ACCESS read-write
            STATUS current
            DESCRIPTION
                "Switch preemphasis on or off."
            ::= { commandsTxEntry 80 }

        
        cmdExcPilotDeviation OBJECT-TYPE
            SYNTAX FloatingPoint
            UNITS "kHz"
            MAX-ACCESS read-write
            STATUS current
            DESCRIPTION
                "Adjusts the deviation of the pilot tone (0.0 ... 15.0). "
            ::= { commandsTxEntry 81 }

        
        cmdExcActivatePilot OBJECT-TYPE
            SYNTAX SwitchOnOff
            MAX-ACCESS read-write
            STATUS current
            DESCRIPTION
                "Switch the pilot tone on or off. 
                This setting is only used in stereo mode."
            ::= { commandsTxEntry 82 }

        
        cmdExcMPXPowerLimit OBJECT-TYPE
            SYNTAX FloatingPoint
            UNITS "dBr"
            MAX-ACCESS read-write
            STATUS current
            DESCRIPTION
                "Defines the threshold for the MPX Power limiter (-5.0 ... 5.0). 
                The limiter must be active for the threshold to take effect. 
                The MPX power limiter is disabled if an external MPX input is used."
            ::= { commandsTxEntry 83 }

        
        cmdExcActivateMPXPowerLimiter OBJECT-TYPE
            SYNTAX SwitchOnOff
            MAX-ACCESS read-write
            STATUS current
            DESCRIPTION
                "Switches the MPX Power limiter on or off. 
                The MPX power limiter is also disabled if an external MPX input is used."
            ::= { commandsTxEntry 84 }

        
        cmdExcFrequency OBJECT-TYPE
            SYNTAX FloatingPoint
            UNITS "MHz"
            MAX-ACCESS read-write
            STATUS current
            DESCRIPTION
                "Adjusts the RF frequency (87.50 ... 108.00)."
            ::= { commandsTxEntry 85 }

        
        cmdExcRefSource OBJECT-TYPE
            SYNTAX INTEGER
                {
                tcxo(1),
                extPPS(2),
                ext10M(3),
                extAES(4),
                intPPS(5),
                int10M(6)
                }
            MAX-ACCESS read-write
            STATUS current
            DESCRIPTION
                "Defines the clock reference for the internal clock. 
                If an external reference is selected, it will be monitored in this window and in the exciter status window."
            ::= { commandsTxEntry 86 }

        
        cmdExcTCXOTrim OBJECT-TYPE
            SYNTAX FloatingPoint
            UNITS "perCent"
            MAX-ACCESS read-write
            STATUS current
            DESCRIPTION
                "Correction value for the internal TCXO (-100.00 ... 100.00). 
                It is not used if an external reference is selected. 
                Higher values increase the frequency, lower values decrease the frequency."
            ::= { commandsTxEntry 87 }

        
        cmdLpTxTransmitterId OBJECT-TYPE
            SYNTAX ReadableString (SIZE (0..8))
            MAX-ACCESS read-write
            STATUS current
            DESCRIPTION
                "Short descriptive name for the transmitter (up to 8 characters)"
            ::= { commandsTxEntry 90 }

        
        cmdLpTxRfWarningThreshold OBJECT-TYPE
            SYNTAX FloatingPoint
            UNITS "dB"
            MAX-ACCESS read-write
            STATUS current
            DESCRIPTION
                "Warning limit for the RF control (dB)."
            ::= { commandsTxEntry 95 }

        
        cmdLpTxRfFaultThreshold OBJECT-TYPE
            SYNTAX FloatingPoint
            UNITS "dB"
            MAX-ACCESS read-write
            STATUS current
            DESCRIPTION
                "Fault limit for the RF control (dB)."
            ::= { commandsTxEntry 96 }

        
        cmdOstRefVoltage OBJECT-TYPE
            SYNTAX FloatingPoint
            UNITS "Percent"
            MAX-ACCESS read-write
            STATUS current
            DESCRIPTION
                "This adjusts the output power of the amplifier.
                This value is settable with maximal 1 position after point (example 11.2)."
            ::= { commandsTxEntry 100 }

        
        cmdOstMaxOutletTempThreshold OBJECT-TYPE
            SYNTAX Integer32 (45..65)
            UNITS "Degree Celsius"
            MAX-ACCESS read-write
            STATUS current
            DESCRIPTION
                "This sets the threshold for the outlet temperature."
            ::= { commandsTxEntry 101 }

        
        summaryInfoTxTable OBJECT-TYPE
            SYNTAX SEQUENCE OF SummaryInfoTxEntry
            MAX-ACCESS not-accessible
            STATUS current
            DESCRIPTION
                "This table shows overall information for all transmitters.
                An equivalent would be System Overview at the Switchover Unit."
            ::= { transmitter 2 }

        
        summaryInfoTxEntry OBJECT-TYPE
            SYNTAX SummaryInfoTxEntry
            MAX-ACCESS not-accessible
            STATUS current
            DESCRIPTION
                "An entry for a designated transmitter."
            INDEX { statusTxIdx }
            ::= { summaryInfoTxTable 1 }

        
        SummaryInfoTxEntry ::=
            SEQUENCE { 
                statusTxIdx
                    IndexTransmitter,
                statusTxName
                    IndexTransmitter,
                statusTxNoConnection
                    TruthValue,
                statusTxSummaryFault
                    TruthValue,
                statusTxSummaryWarning
                    TruthValue,
                statusTxLocalMode
                    TruthValue,
                statusTxRfOn
                    TruthValue,
                statusTxForwardPower
                    FloatingPoint,
                statusTxReflectedPower
                    FloatingPoint,
                statusTxSummaryFaultExcA
                    TruthValue,
                statusTxSummaryFaultOstA
                    TruthValue,
                statusTxSummaryFaultExcB
                    TruthValue,
                statusTxExciterAutomaticReady
                    TruthValue,
                statusTxExciterAutomaticChanged
                    TruthValue,
                statusTxExciterAutomaticFault
                    TruthValue,
                statusTxNoConnectionExcA
                    TruthValue,
                statusTxNoConnectionOstA
                    TruthValue,
                statusTxNoConnectionExcB
                    TruthValue,
                statusTxActiveExcA
                    TruthValue,
                statusTxActiveExcB
                    TruthValue,
                statusTxPowerSupply
                    FloatingPoint,
                statusTxAdditionalPowerSupply
                    TruthValue,
                statusTxInternalPowerSupply
                    FloatingPoint,
                statusTxExternalPowerSupply
                    FloatingPoint
             }

        statusTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { summaryInfoTxEntry 1 }

        
        statusTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { summaryInfoTxEntry 2 }

        
        statusTxNoConnection OBJECT-TYPE
            SYNTAX TruthValue
            MAX-ACCESS read-only
            STATUS current
            DESCRIPTION
                "No connection between NSU and transmitter."
            ::= { summaryInfoTxEntry 3 }

        
        statusTxSummaryFault OBJECT-TYPE
            SYNTAX TruthValue
            MAX-ACCESS read-only
            STATUS current
            DESCRIPTION
                "This indicates a summary fault of the transmitter.
                true(1)  --> summary fault
                false(2) --> no summary fault
                
                There is a fault of at least one module (e.g. Exciter) which causes this summary fault.
                
                An equivalent would be the LED Fault at the transmitters frontpanel."
            ::= { summaryInfoTxEntry 4 }

        
        statusTxSummaryWarning OBJECT-TYPE
            SYNTAX TruthValue
            MAX-ACCESS read-only
            STATUS current
            DESCRIPTION
                "This indicates a summary warning of the transmitter.
                true(1)  --> summary warning
                false(2) --> no summary warning
                
                There is a fault of at least one module (e.g. Exciter) which causes this summary warning.
                
                An equivalent would be the LED Warning at the transmitters frontpanel."
            ::= { summaryInfoTxEntry 5 }

        
        statusTxLocalMode OBJECT-TYPE
            SYNTAX TruthValue
            MAX-ACCESS read-only
            STATUS current
            DESCRIPTION
                "This indicates the local/remote-mode of the transmitter.
                true(1)  --> local
                false(2) --> remote
                
                The transmitter is eigther in local-mode or in remote-mode. 
                For security reasons it is not possible to set this value!
                
                An equivalent would the LED Local at the transmitters frontpanel."
            ::= { summaryInfoTxEntry 6 }

        
        statusTxRfOn OBJECT-TYPE
            SYNTAX TruthValue
            MAX-ACCESS read-only
            STATUS current
            DESCRIPTION
                "The RF is present for the corresponding transmitter."
            ::= { summaryInfoTxEntry 7 }

        
        statusTxForwardPower OBJECT-TYPE
            SYNTAX FloatingPoint
            UNITS "Watt"
            MAX-ACCESS read-only
            STATUS current
            DESCRIPTION
                "The measured forwarded power [W]."
            ::= { summaryInfoTxEntry 13 }

        
        statusTxReflectedPower OBJECT-TYPE
            SYNTAX FloatingPoint
            UNITS "Watt"
            MAX-ACCESS read-only
            STATUS current
            DESCRIPTION
                "The measured reflected power [W] (not available for lowpower)."
            ::= { summaryInfoTxEntry 14 }

        
        statusTxSummaryFaultExcA OBJECT-TYPE
            SYNTAX TruthValue
            MAX-ACCESS read-only
            STATUS current
            DESCRIPTION
                "This indicates a summary fault of exciter."
            ::= { summaryInfoTxEntry 15 }

        
        statusTxSummaryFaultOstA OBJECT-TYPE
            SYNTAX TruthValue
            MAX-ACCESS read-only
            STATUS current
            DESCRIPTION
                "This indicates a summary fault of outputstage."
            ::= { summaryInfoTxEntry 16 }

        
        statusTxSummaryFaultExcB OBJECT-TYPE
            SYNTAX TruthValue
            MAX-ACCESS read-only
            STATUS current
            DESCRIPTION
                "This indicates a summary fault of exciter."
            ::= { summaryInfoTxEntry 17 }

        
        statusTxExciterAutomaticReady OBJECT-TYPE
            SYNTAX TruthValue
            MAX-ACCESS read-only
            STATUS current
            DESCRIPTION
                "The Exciter Automatic is Ready. 
                In case of any fault on one exciter, there will be a switchover to the other exciter."
            ::= { summaryInfoTxEntry 19 }

        
        statusTxExciterAutomaticChanged OBJECT-TYPE
            SYNTAX TruthValue
            MAX-ACCESS read-only
            STATUS current
            DESCRIPTION
                "The Exciter Automatic has changed. 
                There was a fault on one exciter which lead to this changeover."
            ::= { summaryInfoTxEntry 20 }

        
        statusTxExciterAutomaticFault OBJECT-TYPE
            SYNTAX TruthValue
            MAX-ACCESS read-only
            STATUS current
            DESCRIPTION
                "The Exciter Automatic is faulty. 
                In case of any fault on one exciter, there will be no switchover to the other exciter,
                because of this fault."
            ::= { summaryInfoTxEntry 21 }

        
        statusTxNoConnectionExcA OBJECT-TYPE
            SYNTAX TruthValue
            MAX-ACCESS read-only
            STATUS current
            DESCRIPTION
                "No Connection between NetCCU and Exciter."
            ::= { summaryInfoTxEntry 25 }

        
        statusTxNoConnectionOstA OBJECT-TYPE
            SYNTAX TruthValue
            MAX-ACCESS read-only
            STATUS current
            DESCRIPTION
                "No Connection between NetCCU and Outputstage."
            ::= { summaryInfoTxEntry 26 }

        
        statusTxNoConnectionExcB OBJECT-TYPE
            SYNTAX TruthValue
            MAX-ACCESS read-only
            STATUS current
            DESCRIPTION
                "No Connection between NetCCU and Exciter."
            ::= { summaryInfoTxEntry 27 }

        
        statusTxActiveExcA OBJECT-TYPE
            SYNTAX TruthValue
            MAX-ACCESS read-only
            STATUS current
            DESCRIPTION
                "ExciterA is currently active."
            ::= { summaryInfoTxEntry 29 }

        
        statusTxActiveExcB OBJECT-TYPE
            SYNTAX TruthValue
            MAX-ACCESS read-only
            STATUS current
            DESCRIPTION
                "ExciterB is currently active."
            ::= { summaryInfoTxEntry 31 }

        
        statusTxPowerSupply OBJECT-TYPE
            SYNTAX FloatingPoint
            UNITS "volt"
            MAX-ACCESS read-only
            STATUS current
            DESCRIPTION
                "Monitoring value of the output voltages of the power supply."
            ::= { summaryInfoTxEntry 37 }

        
        statusTxAdditionalPowerSupply OBJECT-TYPE
            SYNTAX TruthValue
            MAX-ACCESS read-only
            STATUS current
            DESCRIPTION
                "Shows whether the NetCCU has an additional (external) power supply."
            ::= { summaryInfoTxEntry 38 }

        
        statusTxInternalPowerSupply OBJECT-TYPE
            SYNTAX FloatingPoint
            UNITS "volt"
            MAX-ACCESS read-only
            STATUS current
            DESCRIPTION
                "Monitoring value of the output voltages of the internal power supply."
            ::= { summaryInfoTxEntry 39 }

        
        statusTxExternalPowerSupply OBJECT-TYPE
            SYNTAX FloatingPoint
            UNITS "volt"
            MAX-ACCESS read-only
            STATUS current
            DESCRIPTION
                "Monitoring value of the output voltages of the external power supply."
            ::= { summaryInfoTxEntry 40 }

        
        exciterInputAnalogStatusTable OBJECT-TYPE
            SYNTAX SEQUENCE OF ExciterInputAnalogStatusEntry
            MAX-ACCESS not-accessible
            STATUS current
            DESCRIPTION
                "The table for analog measurement values."
            ::= { transmitter 20 }

        
        exciterInputAnalogStatusEntry OBJECT-TYPE
            SYNTAX ExciterInputAnalogStatusEntry
            MAX-ACCESS not-accessible
            STATUS current
            DESCRIPTION
                "A row (an entry) in the table for analog measurment values."
            INDEX { excInputAnalogStatusTxIdx, excInputAnalogStatusExcIdx, excInputArrayIdx }
            ::= { exciterInputAnalogStatusTable 1 }

        
        ExciterInputAnalogStatusEntry ::=
            SEQUENCE { 
                excInputAnalogStatusTxIdx
                    IndexTransmitter,
                excInputAnalogStatusExcIdx
                    IndexAB,
                excInputArrayIdx
                    Integer32,
                excInputAnalogStatusTxName
                    IndexTransmitter,
                excInputArrayIdxLabel
                    INTEGER,
                excInputExcNominal
                    FloatingPoint,
                excInputCurrentPercent
                    FloatingPoint,
                excInputCurrentdBu
                    FloatingPoint,
                excInputCurrentState
                    INTEGER
             }

        excInputAnalogStatusTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { exciterInputAnalogStatusEntry 1 }

        
        excInputAnalogStatusExcIdx OBJECT-TYPE
            SYNTAX IndexAB
            MAX-ACCESS not-accessible
            STATUS current
            DESCRIPTION
                "The dedicated exciter (A/B)."
            ::= { exciterInputAnalogStatusEntry 2 }

        
        excInputArrayIdx OBJECT-TYPE
            SYNTAX Integer32 (1..6)
            MAX-ACCESS not-accessible
            STATUS current
            DESCRIPTION
                "The array number (1..6).
                
                1 = AF Left
                2 = AF Right
                3 = MPX
                4 = AUX1
                5 = AUX2
                6 = AUX3
                "
            ::= { exciterInputAnalogStatusEntry 3 }

        
        excInputAnalogStatusTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { exciterInputAnalogStatusEntry 4 }

        
        excInputArrayIdxLabel OBJECT-TYPE
            SYNTAX INTEGER
                {
                afLeft(1),
                afRight(2),
                mpx(3),
                aux1(4),
                aux2(5),
                aux3(6)
                }
            MAX-ACCESS read-only
            STATUS current
            DESCRIPTION
                "This is the logical name for the index of the array."
            ::= { exciterInputAnalogStatusEntry 5 }

        
        excInputExcNominal OBJECT-TYPE
            SYNTAX FloatingPoint
            UNITS "dBu"
            MAX-ACCESS read-only
            STATUS current
            DESCRIPTION
                "The nominal input level for this input. 
                This level causes the nominal deviation."
            ::= { exciterInputAnalogStatusEntry 6 }

        
        excInputCurrentPercent OBJECT-TYPE
            SYNTAX FloatingPoint
            UNITS "perCent"
            MAX-ACCESS read-only
            STATUS current
            DESCRIPTION
                "The current input level for this input as a percentage 
                of the nominal level."
            ::= { exciterInputAnalogStatusEntry 7 }

        
        excInputCurrentdBu OBJECT-TYPE
            SYNTAX FloatingPoint
            UNITS "dBu"
            MAX-ACCESS read-only
            STATUS current
            DESCRIPTION
                "The current input level for this input in dBu."
            ::= { exciterInputAnalogStatusEntry 8 }

        
        excInputCurrentState OBJECT-TYPE
            SYNTAX INTEGER
                {
                off(1),
                ok(2),
                clipped(3),
                levelToLow(4)
                }
            MAX-ACCESS read-only
            STATUS current
            DESCRIPTION
                "Current status of this input. Select the status field and 
                press OK to view detailed state information."
            ::= { exciterInputAnalogStatusEntry 9 }

        
        exciterInputTable OBJECT-TYPE
            SYNTAX SEQUENCE OF ExciterInputEntry
            MAX-ACCESS not-accessible
            STATUS current
            DESCRIPTION
                "The table for more detailed informations about the exciter.
                These values are all read-only. For settings, refer to commands."
            ::= { transmitter 21 }

        
        exciterInputEntry OBJECT-TYPE
            SYNTAX ExciterInputEntry
            MAX-ACCESS not-accessible
            STATUS current
            DESCRIPTION
                "An entry (conceptual row) in the exciterInputTable."
            INDEX { excInputTxIdx, excInputExcIdx }
            ::= { exciterInputTable 1 }

        
        ExciterInputEntry ::=
            SEQUENCE { 
                excInputTxIdx
                    IndexTransmitter,
                excInputTxName
                    IndexTransmitter,
                excInputExcIdx
                    IndexAB,
                excInputAFThresholddBuMax
                    FloatingPoint,
                excInputAFThresholddBuMin
                    FloatingPoint,
                excInputMPXThresholddBuMax
                    FloatingPoint,
                excInputMPXThresholddBuMin
                    FloatingPoint,
                excInputAESThresholddBFsMax
                    FloatingPoint,
                excInputAESThresholddBFsMin
                    FloatingPoint,
                excInputAUX1ThresholddBMax
                    FloatingPoint,
                excInputAUX1ThresholddBMin
                    FloatingPoint,
                excInputAUX2ThresholddBMax
                    FloatingPoint,
                excInputAUX2ThresholddBMin
                    FloatingPoint,
                excInputAUX3ThresholddBMax
                    FloatingPoint,
                excInputAUX3ThresholddBMin
                    FloatingPoint,
                excInputCH1State
                    INTEGER,
                excInputCH2State
                    INTEGER,
                excInputSelectedModType
                    INTEGER,
                excInputAudioState
                    INTEGER,
                excInputNomAESLLevel
                    FloatingPoint,
                excInputAESLLevel
                    FloatingPoint,
                excInputAESLLeveldBFs
                    FloatingPoint,
                excInputAESLState
                    INTEGER,
                excInputNomAESRLevel
                    FloatingPoint,
                excInputAESRLevel
                    FloatingPoint,
                excInputAESRLeveldBFs
                    FloatingPoint,
                excInputAESRState
                    INTEGER,
                excInputAESParityERR
                    INTEGER,
                excInputAESAudioDetect
                    SwitchOnOff,
                excInputAESPreemphasisDetect
                    SwitchOnOff,
                excInputAESChannelStatusCRC
                    INTEGER,
                excInputAESChannelStatusValid
                    INTEGER,
                excInputAESNoClock
                    INTEGER,
                excInputAESNonPCM
                    INTEGER,
                excInputAESSF
                    INTEGER
             }

        excInputTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { exciterInputEntry 1 }

        
        excInputTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { exciterInputEntry 2 }

        
        excInputExcIdx OBJECT-TYPE
            SYNTAX IndexAB
            MAX-ACCESS not-accessible
            STATUS current
            DESCRIPTION
                "The dedicated exciter (A/B)."
            ::= { exciterInputEntry 3 }

        
        excInputAFThresholddBuMax OBJECT-TYPE
            SYNTAX FloatingPoint
            UNITS "dBu"
            MAX-ACCESS read-only
            STATUS current
            DESCRIPTION
                "For internal use only."
            ::= { exciterInputEntry 4 }

        
        excInputAFThresholddBuMin OBJECT-TYPE
            SYNTAX FloatingPoint
            UNITS "dBu"
            MAX-ACCESS read-only
            STATUS current
            DESCRIPTION
                "For internal use only."
            ::= { exciterInputEntry 5 }

        
        excInputMPXThresholddBuMax OBJECT-TYPE
            SYNTAX FloatingPoint
            UNITS "dBu"
            MAX-ACCESS read-only
            STATUS current
            DESCRIPTION
                "For internal use only."
            ::= { exciterInputEntry 6 }

        
        excInputMPXThresholddBuMin OBJECT-TYPE
            SYNTAX FloatingPoint
            UNITS "dBu"
            MAX-ACCESS read-only
            STATUS current
            DESCRIPTION
                "For internal use only."
            ::= { exciterInputEntry 7 }

        
        excInputAESThresholddBFsMax OBJECT-TYPE
            SYNTAX FloatingPoint
            UNITS "dBFS"
            MAX-ACCESS read-only
            STATUS current
            DESCRIPTION
                "For internal use only."
            ::= { exciterInputEntry 8 }

        
        excInputAESThresholddBFsMin OBJECT-TYPE
            SYNTAX FloatingPoint
            UNITS "dBFS"
            MAX-ACCESS read-only
            STATUS current
            DESCRIPTION
                "For internal use only."
            ::= { exciterInputEntry 9 }

        
        excInputAUX1ThresholddBMax OBJECT-TYPE
            SYNTAX FloatingPoint
            UNITS "dBu"
            MAX-ACCESS read-only
            STATUS current
            DESCRIPTION
                "For internal use only."
            ::= { exciterInputEntry 10 }

        
        excInputAUX1ThresholddBMin OBJECT-TYPE
            SYNTAX FloatingPoint
            UNITS "dBu"
            MAX-ACCESS read-only
            STATUS current
            DESCRIPTION
                "For internal use only."
            ::= { exciterInputEntry 11 }

        
        excInputAUX2ThresholddBMax OBJECT-TYPE
            SYNTAX FloatingPoint
            UNITS "dBu"
            MAX-ACCESS read-only
            STATUS current
            DESCRIPTION
                "For internal use only."
            ::= { exciterInputEntry 12 }

        
        excInputAUX2ThresholddBMin OBJECT-TYPE
            SYNTAX FloatingPoint
            UNITS "dBu"
            MAX-ACCESS read-only
            STATUS current
            DESCRIPTION
                "For internal use only."
            ::= { exciterInputEntry 13 }

        
        excInputAUX3ThresholddBMax OBJECT-TYPE
            SYNTAX FloatingPoint
            UNITS "dBu"
            MAX-ACCESS read-only
            STATUS current
            DESCRIPTION
                "For internal use only."
            ::= { exciterInputEntry 14 }

        
        excInputAUX3ThresholddBMin OBJECT-TYPE
            SYNTAX FloatingPoint
            UNITS "dBu"
            MAX-ACCESS read-only
            STATUS current
            DESCRIPTION
                "For internal use only."
            ::= { exciterInputEntry 15 }

        
        excInputCH1State OBJECT-TYPE
            SYNTAX INTEGER
                {
                ok(1),
                oneChNotOk(2),
                notOk(3)
                }
            MAX-ACCESS read-only
            STATUS current
            DESCRIPTION
                "Shows the state of the primary input channel."
            ::= { exciterInputEntry 16 }

        
        excInputCH2State OBJECT-TYPE
            SYNTAX INTEGER
                {
                ok(1),
                oneChNotOk(2),
                notOk(3),
                notUsed(4)
                }
            MAX-ACCESS read-only
            STATUS current
            DESCRIPTION
                "Shows the state of the secondary input channel."
            ::= { exciterInputEntry 17 }

        
        excInputSelectedModType OBJECT-TYPE
            SYNTAX INTEGER
                {
                afMonoL(1),
                afMonoR(2),
                afMonoLR(3),
                afStereo(4),
                aesMonoL(5),
                aesMonoR(6),
                aesMonoLR(7),
                aesStereo(8),
                mpxInp2(9),
                mpxInp3(10),
                notUsed(11)
                }
            MAX-ACCESS read-only
            STATUS current
            DESCRIPTION
                "The currently selected audio modulation source. 
                Preemphasis is not available in MPX mode. 
                Pilot is only available in stereo mode."
            ::= { exciterInputEntry 18 }

        
        excInputAudioState OBJECT-TYPE
            SYNTAX INTEGER
                {
                ok(1),
                warning(2),
                error(3)
                }
            MAX-ACCESS read-only
            STATUS current
            DESCRIPTION
                "Status of the currently selected audio input. 
                (Either Channel 1 or Channel 2)
                Dependent on the setting in menu 'Automatic Input Selection', 
                input faults are signalized as a warning or as an fault."
            ::= { exciterInputEntry 19 }

        
        excInputNomAESLLevel OBJECT-TYPE
            SYNTAX FloatingPoint
            UNITS "dB"
            MAX-ACCESS read-only
            STATUS current
            DESCRIPTION
                "The nominal input level for this input. 
                This level causes the nominal deviation."
            ::= { exciterInputEntry 20 }

        
        excInputAESLLevel OBJECT-TYPE
            SYNTAX FloatingPoint
            UNITS "perCent"
            MAX-ACCESS read-only
            STATUS current
            DESCRIPTION
                "The current input level for this input as a percentage 
                of the nominal level."
            ::= { exciterInputEntry 21 }

        
        excInputAESLLeveldBFs OBJECT-TYPE
            SYNTAX FloatingPoint
            UNITS "dB"
            MAX-ACCESS read-only
            STATUS current
            DESCRIPTION
                "The current input level for this input in dBu."
            ::= { exciterInputEntry 22 }

        
        excInputAESLState OBJECT-TYPE
            SYNTAX INTEGER
                {
                off(1),
                ok(2),
                levelToLow(3)
                }
            MAX-ACCESS read-only
            STATUS current
            DESCRIPTION
                "Current status of this input. 
                Select the status field and press OK to view detailed state information."
            ::= { exciterInputEntry 23 }

        
        excInputNomAESRLevel OBJECT-TYPE
            SYNTAX FloatingPoint
            UNITS "dB"
            MAX-ACCESS read-only
            STATUS current
            DESCRIPTION
                "The nominal input level for this input. 
                This level causes the nominal deviation."
            ::= { exciterInputEntry 24 }

        
        excInputAESRLevel OBJECT-TYPE
            SYNTAX FloatingPoint
            UNITS "perCent"
            MAX-ACCESS read-only
            STATUS current
            DESCRIPTION
                "The current input level for this input as a percentage 
                of the nominal level."
            ::= { exciterInputEntry 25 }

        
        excInputAESRLeveldBFs OBJECT-TYPE
            SYNTAX FloatingPoint
            UNITS "dB"
            MAX-ACCESS read-only
            STATUS current
            DESCRIPTION
                "The current input level for this input in dBu."
            ::= { exciterInputEntry 26 }

        
        excInputAESRState OBJECT-TYPE
            SYNTAX INTEGER
                {
                off(1),
                ok(2),
                levelToLow(3)
                }
            MAX-ACCESS read-only
            STATUS current
            DESCRIPTION
                "Current status of this input. 
                Select the status field and press OK to view detailed state information."
            ::= { exciterInputEntry 27 }

        
        excInputAESParityERR OBJECT-TYPE
            SYNTAX INTEGER
                {
                off(1),
                ok(2),
                error(3)
                }
            MAX-ACCESS read-only
            STATUS current
            DESCRIPTION
                "Indicates if a parity or biphase error has occurred."
            ::= { exciterInputEntry 28 }

        
        excInputAESAudioDetect OBJECT-TYPE
            SYNTAX SwitchOnOff
            MAX-ACCESS read-only
            STATUS current
            DESCRIPTION
                "Indicates whether the receiver has detected audio content. 
                This bit is set by encoding channel status bits."
            ::= { exciterInputEntry 29 }

        
        excInputAESPreemphasisDetect OBJECT-TYPE
            SYNTAX SwitchOnOff
            MAX-ACCESS read-only
            STATUS current
            DESCRIPTION
                "Shows if the receiver has detected preemphasis. 
                This bit is set by encoding channel status bits."
            ::= { exciterInputEntry 30 }

        
        excInputAESChannelStatusCRC OBJECT-TYPE
            SYNTAX INTEGER
                {
                off(1),
                ok(2),
                error(3)
                }
            MAX-ACCESS read-only
            STATUS current
            DESCRIPTION
                "Shows if the receiver has detected CRC errors in the channel status bits."
            ::= { exciterInputEntry 31 }

        
        excInputAESChannelStatusValid OBJECT-TYPE
            SYNTAX INTEGER
                {
                off(1),
                ok(2),
                notValid(3)
                }
            MAX-ACCESS read-only
            STATUS current
            DESCRIPTION
                "Indicates whether the detected receiver status is valid."
            ::= { exciterInputEntry 32 }

        
        excInputAESNoClock OBJECT-TYPE
            SYNTAX INTEGER
                {
                off(1),
                ok(2),
                noClock(3)
                }
            MAX-ACCESS read-only
            STATUS current
            DESCRIPTION
                "Shows the state of the receiver PLL. 
                It is unlocked if there is no incoming clock."
            ::= { exciterInputEntry 33 }

        
        excInputAESNonPCM OBJECT-TYPE
            SYNTAX INTEGER
                {
                off(1),
                ok(2),
                error(3)
                }
            MAX-ACCESS read-only
            STATUS current
            DESCRIPTION
                "Indicates if the incoming AES signal is a non-PCM bit stream. 
                In this case the data can not be processed!"
            ::= { exciterInputEntry 34 }

        
        excInputAESSF OBJECT-TYPE
            SYNTAX INTEGER
                {
                kHz44dot1(1),
                kHz48(2),
                kHz32(3),
                kHz88dot2(4),
                kHz96(5),
                kHz176dot4(6),
                kHz192(7),
                reserved(8),
                undefined(9)
                }
            MAX-ACCESS read-only
            STATUS current
            DESCRIPTION
                "Shows the detected sample rate of the incoming AES signal."
            ::= { exciterInputEntry 35 }

        
        exciterModulationStatusTable OBJECT-TYPE
            SYNTAX SEQUENCE OF ExciterModulationStatusEntry
            MAX-ACCESS not-accessible
            STATUS current
            DESCRIPTION
                "The table for modulation status values."
            ::= { transmitter 22 }

        
        exciterModulationStatusEntry OBJECT-TYPE
            SYNTAX ExciterModulationStatusEntry
            MAX-ACCESS not-accessible
            STATUS current
            DESCRIPTION
                "An entry (conceptual row) in the exciterModulationStatusTable."
            INDEX { excModStatusTxIdx, excModStatusExcIdx }
            ::= { exciterModulationStatusTable 1 }

        
        ExciterModulationStatusEntry ::=
            SEQUENCE { 
                excModStatusTxIdx
                    IndexTransmitter,
                excModStatusTxName
                    IndexTransmitter,
                excModStatusExcIdx
                    IndexAB,
                excModStatusCurrentDeviation
                    FloatingPoint,
                excModStatusCurrentMPXPower
                    FloatingPoint,
                excModStatusCurrentClipDeviation
                    FloatingPoint,
                excModStatusLimiterActivity
                    FloatingPoint
             }

        excModStatusTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { exciterModulationStatusEntry 1 }

        
        excModStatusTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { exciterModulationStatusEntry 2 }

        
        excModStatusExcIdx OBJECT-TYPE
            SYNTAX IndexAB
            MAX-ACCESS not-accessible
            STATUS current
            DESCRIPTION
                "The dedicated exciter (A/B)."
            ::= { exciterModulationStatusEntry 3 }

        
        excModStatusCurrentDeviation OBJECT-TYPE
            SYNTAX FloatingPoint
            UNITS "kHz"
            MAX-ACCESS read-only
            STATUS current
            DESCRIPTION
                "Current measured deviation."
            ::= { exciterModulationStatusEntry 4 }

        
        excModStatusCurrentMPXPower OBJECT-TYPE
            SYNTAX FloatingPoint
            UNITS "dBr"
            MAX-ACCESS read-only
            STATUS current
            DESCRIPTION
                "Current measured MPX power over the last 60 seconds."
            ::= { exciterModulationStatusEntry 5 }

        
        excModStatusCurrentClipDeviation OBJECT-TYPE
            SYNTAX FloatingPoint
            UNITS "kHz"
            MAX-ACCESS read-only
            STATUS current
            DESCRIPTION
                "Max. clipped deviation over the last second. 
                If the deviation is too high over a longer time interval the limiter 
                reduce the signal strength."
            ::= { exciterModulationStatusEntry 6 }

        
        excModStatusLimiterActivity OBJECT-TYPE
            SYNTAX FloatingPoint
            UNITS "perCent"
            MAX-ACCESS read-only
            STATUS current
            DESCRIPTION
                "Indication of the limiter activity. 0% means no limiting, 
                100% means total limiting."
            ::= { exciterModulationStatusEntry 7 }

        
        exciterDeviceStatusTable OBJECT-TYPE
            SYNTAX SEQUENCE OF ExciterDeviceStatusEntry
            MAX-ACCESS not-accessible
            STATUS current
            DESCRIPTION
                "The table for device status values."
            ::= { transmitter 23 }

        
        exciterDeviceStatusEntry OBJECT-TYPE
            SYNTAX ExciterDeviceStatusEntry
            MAX-ACCESS not-accessible
            STATUS current
            DESCRIPTION
                "An entry (conceptual row) in the exciterDeviceStatusTable."
            INDEX { excDeviceStatusTxIdx, excDeviceStatusExcIdx }
            ::= { exciterDeviceStatusTable 1 }

        
        ExciterDeviceStatusEntry ::=
            SEQUENCE { 
                excDeviceStatusTxIdx
                    IndexTransmitter,
                excDeviceStatusTxName
                    IndexTransmitter,
                excDeviceStatusExcIdx
                    IndexAB,
                excDeviceStatusCurrentTemperatur
                    FloatingPoint,
                excDeviceStatus12VRack
                    FloatingPoint,
                excDeviceStatus12VFan
                    FloatingPoint
             }

        excDeviceStatusTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { exciterDeviceStatusEntry 1 }

        
        excDeviceStatusTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { exciterDeviceStatusEntry 2 }

        
        excDeviceStatusExcIdx OBJECT-TYPE
            SYNTAX IndexAB
            MAX-ACCESS not-accessible
            STATUS current
            DESCRIPTION
                "The dedicated exciter (A/B)."
            ::= { exciterDeviceStatusEntry 3 }

        
        excDeviceStatusCurrentTemperatur OBJECT-TYPE
            SYNTAX FloatingPoint
            UNITS "celsius"
            MAX-ACCESS read-only
            STATUS current
            DESCRIPTION
                "Actual measured temperature."
            ::= { exciterDeviceStatusEntry 4 }

        
        excDeviceStatus12VRack OBJECT-TYPE
            SYNTAX FloatingPoint
            UNITS "V"
            MAX-ACCESS read-only
            STATUS current
            DESCRIPTION
                "Actual measured value."
            ::= { exciterDeviceStatusEntry 5 }

        
        excDeviceStatus12VFan OBJECT-TYPE
            SYNTAX FloatingPoint
            UNITS "V"
            MAX-ACCESS read-only
            STATUS current
            DESCRIPTION
                "Actual measured value."
            ::= { exciterDeviceStatusEntry 6 }

        
        lpOstTable OBJECT-TYPE
            SYNTAX SEQUENCE OF LpOstEntry
            MAX-ACCESS not-accessible
            STATUS current
            DESCRIPTION
                "The table for low power outputstage values."
            ::= { transmitter 24 }

        
        lpOstEntry OBJECT-TYPE
            SYNTAX LpOstEntry
            MAX-ACCESS not-accessible
            STATUS current
            DESCRIPTION
                "An entry (conceptual row) in the lpOstTable."
            INDEX { lpOstTxIdx, lpOstExcIdx }
            ::= { lpOstTable 1 }

        
        LpOstEntry ::=
            SEQUENCE { 
                lpOstTxIdx
                    IndexTransmitter,
                lpOstTxName
                    IndexTransmitter,
                lpOstExcIdx
                    IndexAB,
                lpOstOperationMode
                    INTEGER,
                lpOstForwardPowerStatus
                    INTEGER,
                lpOstVswrPowerRegulation
                    INTEGER,
                lpOstTemperatureRegulation
                    INTEGER,
                lpOstRfInStatus
                    INTEGER,
                lpOstReflectionStatus
                    INTEGER,
                lpOstTemperatureStatus
                    INTEGER,
                lpOstCommsStatus
                    INTEGER,
                lpOstForwardPower
                    FloatingPoint,
                lpOstReflectedPower
                    FloatingPoint,
                lpOstSwr
                    FloatingPoint,
                lpOstDcSupplyVoltage
                    FloatingPoint,
                lpOstDcSupplyControlVoltage
                    FloatingPoint,
                lpOstAttenuatorControlVoltage
                    FloatingPoint,
                lpOstDriverCurrent
                    FloatingPoint,
                lpOstPowerAmplifier1Current
                    FloatingPoint,
                lpOstPowerAmplifier2Current
                    FloatingPoint,
                lpOstPowerAmplifier3Current
                    FloatingPoint,
                lpOstPowerAmplifier4Current
                    FloatingPoint,
                lpOstAlcControlVoltage
                    FloatingPoint,
                lpOstAmplifierHeatsinkTemp
                    FloatingPoint,
                lpOstActualReferenceVoltage
                    FloatingPoint,
                lpOstNominalPower
                    FloatingPoint
             }

        lpOstTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { lpOstEntry 1 }

        
        lpOstTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { lpOstEntry 2 }

        
        lpOstExcIdx OBJECT-TYPE
            SYNTAX IndexAB
            MAX-ACCESS not-accessible
            STATUS current
            DESCRIPTION
                "The dedicated exciter (A/B)."
            ::= { lpOstEntry 3 }

        
        lpOstOperationMode OBJECT-TYPE
            SYNTAX INTEGER
                {
                ampOff(1),
                ampOn(2)
                }
            MAX-ACCESS read-only
            STATUS current
            DESCRIPTION
                "Outputstage Operation Mode Indicates whether the outputstage is switched on or off"
            ::= { lpOstEntry 4 }

        
        lpOstForwardPowerStatus OBJECT-TYPE
            SYNTAX INTEGER
                {
                off(1),
                fault(2),
                warning(3),
                ok(4)
                }
            MAX-ACCESS read-only
            STATUS current
            DESCRIPTION
                "Indicates the status of the RF forward power."
            ::= { lpOstEntry 5 }

        
        lpOstVswrPowerRegulation OBJECT-TYPE
            SYNTAX INTEGER
                {
                off(1),
                fault(2),
                warning(3),
                ok(4)
                }
            MAX-ACCESS read-only
            STATUS current
            DESCRIPTION
                "Indicates whether the output power is currently reduced or switched off due to high VSWR."
            ::= { lpOstEntry 6 }

        
        lpOstTemperatureRegulation OBJECT-TYPE
            SYNTAX INTEGER
                {
                inactive(1),
                active(2)
                }
            MAX-ACCESS read-only
            STATUS current
            DESCRIPTION
                "Indicates whether the output power is currently reduced due to high amplifier temperature."
            ::= { lpOstEntry 7 }

        
        lpOstRfInStatus OBJECT-TYPE
            SYNTAX INTEGER
                {
                ok(1),
                fail(2)
                }
            MAX-ACCESS read-only
            STATUS current
            DESCRIPTION
                "Amplifier RF In Status."
            ::= { lpOstEntry 8 }

        
        lpOstReflectionStatus OBJECT-TYPE
            SYNTAX INTEGER
                {
                ok(1),
                fail(2)
                }
            MAX-ACCESS read-only
            STATUS current
            DESCRIPTION
                "Amplifier Reflection Status."
            ::= { lpOstEntry 9 }

        
        lpOstTemperatureStatus OBJECT-TYPE
            SYNTAX INTEGER
                {
                ok(1),
                fail(2)
                }
            MAX-ACCESS read-only
            STATUS current
            DESCRIPTION
                "Amplifier Temperature Status."
            ::= { lpOstEntry 10 }

        
        lpOstCommsStatus OBJECT-TYPE
            SYNTAX INTEGER
                {
                notOK(1),
                ok(2)
                }
            MAX-ACCESS read-only
            STATUS current
            DESCRIPTION
                "Amplifier Communications Status."
            ::= { lpOstEntry 11 }

        
        lpOstForwardPower OBJECT-TYPE
            SYNTAX FloatingPoint
            UNITS "W"
            MAX-ACCESS read-only
            STATUS current
            DESCRIPTION
                "Amplifier Forward Power (W)."
            ::= { lpOstEntry 12 }

        
        lpOstReflectedPower OBJECT-TYPE
            SYNTAX FloatingPoint
            UNITS "W"
            MAX-ACCESS read-only
            STATUS current
            DESCRIPTION
                "Amplifier Reflectes Power (W)."
            ::= { lpOstEntry 13 }

        
        lpOstSwr OBJECT-TYPE
            SYNTAX FloatingPoint
            MAX-ACCESS read-only
            STATUS current
            DESCRIPTION
                "Amplifier Output Voltage Standing Wave Ratio."
            ::= { lpOstEntry 14 }

        
        lpOstDcSupplyVoltage OBJECT-TYPE
            SYNTAX FloatingPoint
            UNITS "V"
            MAX-ACCESS read-only
            STATUS current
            DESCRIPTION
                "DC Power Supply Output Voltage (V)."
            ::= { lpOstEntry 15 }

        
        lpOstDcSupplyControlVoltage OBJECT-TYPE
            SYNTAX FloatingPoint
            UNITS "V"
            MAX-ACCESS read-only
            STATUS current
            DESCRIPTION
                "Control Voltage for DC Power Supply (V)."
            ::= { lpOstEntry 16 }

        
        lpOstAttenuatorControlVoltage OBJECT-TYPE
            SYNTAX FloatingPoint
            UNITS "V"
            MAX-ACCESS read-only
            STATUS current
            DESCRIPTION
                "Control Voltage for PIN Diodes (V)."
            ::= { lpOstEntry 17 }

        
        lpOstDriverCurrent OBJECT-TYPE
            SYNTAX FloatingPoint
            UNITS "A"
            MAX-ACCESS read-only
            STATUS current
            DESCRIPTION
                "Driver and Predriver Transistor Current (A)."
            ::= { lpOstEntry 18 }

        
        lpOstPowerAmplifier1Current OBJECT-TYPE
            SYNTAX FloatingPoint
            UNITS "A"
            MAX-ACCESS read-only
            STATUS current
            DESCRIPTION
                "Power Amplifier Transistor 1 Current (A)."
            ::= { lpOstEntry 19 }

        
        lpOstPowerAmplifier2Current OBJECT-TYPE
            SYNTAX FloatingPoint
            UNITS "A"
            MAX-ACCESS read-only
            STATUS current
            DESCRIPTION
                "Power Amplifier Transistor 2 Current (A)."
            ::= { lpOstEntry 20 }

        
        lpOstPowerAmplifier3Current OBJECT-TYPE
            SYNTAX FloatingPoint
            UNITS "A"
            MAX-ACCESS read-only
            STATUS current
            DESCRIPTION
                "Power Amplifier Transistor 3 Current (A)."
            ::= { lpOstEntry 21 }

        
        lpOstPowerAmplifier4Current OBJECT-TYPE
            SYNTAX FloatingPoint
            UNITS "A"
            MAX-ACCESS read-only
            STATUS current
            DESCRIPTION
                "Power Amplifier Transistor 4 Current (A)."
            ::= { lpOstEntry 22 }

        
        lpOstAlcControlVoltage OBJECT-TYPE
            SYNTAX FloatingPoint
            UNITS "V"
            MAX-ACCESS read-only
            STATUS current
            DESCRIPTION
                "Output Power Control Voltage (V)."
            ::= { lpOstEntry 23 }

        
        lpOstAmplifierHeatsinkTemp OBJECT-TYPE
            SYNTAX FloatingPoint
            UNITS "C"
            MAX-ACCESS read-only
            STATUS current
            DESCRIPTION
                "Amplifier Heatsink Temperature (C)."
            ::= { lpOstEntry 24 }

        
        lpOstActualReferenceVoltage OBJECT-TYPE
            SYNTAX FloatingPoint
            UNITS "perCent"
            MAX-ACCESS read-only
            STATUS current
            DESCRIPTION
                "The actual reference voltage currently being supplied to the amplifier (%). 
                This may have been reduced from the nominal value due to a high temperature 
                or high VSWR condition."
            ::= { lpOstEntry 25 }

        
        lpOstNominalPower OBJECT-TYPE
            SYNTAX FloatingPoint
            UNITS "W"
            MAX-ACCESS read-only
            STATUS current
            DESCRIPTION
                "Outputstage Nominal Power (W)."
            ::= { lpOstEntry 26 }

        
        lpTxCuTable OBJECT-TYPE
            SYNTAX SEQUENCE OF LpTxCuEntry
            MAX-ACCESS not-accessible
            STATUS current
            DESCRIPTION
                "The table for low power Tx values."
            ::= { transmitter 25 }

        
        lpTxCuEntry OBJECT-TYPE
            SYNTAX LpTxCuEntry
            MAX-ACCESS not-accessible
            STATUS current
            DESCRIPTION
                "An entry (conceptual row) in the lpTxCuTable."
            INDEX { lpTxCuTxIdx, lpTxCuExcIdx }
            ::= { lpTxCuTable 1 }

        
        LpTxCuEntry ::=
            SEQUENCE { 
                lpTxCuTxIdx
                    IndexTransmitter,
                lpTxCuTxName
                    IndexTransmitter,
                lpTxCuExcIdx
                    IndexAB,
                lpTxCuTransmitterMode
                    INTEGER,
                lpTxCuTemperatureStatus
                    INTEGER,
                lpTxCuFanStatus
                    INTEGER
             }

        lpTxCuTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { lpTxCuEntry 1 }

        
        lpTxCuTxName OBJECT-TYPE
            SYNTAX IndexTransmitter
            MAX-ACCESS read-only
            STATUS current
            DESCRIPTION
                "This is the logical name for the transmitters.
                The reserve transmitter (TxB) always is shown as the first line of a table.
                The other (main, program) transmitters (TxA1, TxA2...) are following."
            ::= { lpTxCuEntry 2 }

        
        lpTxCuExcIdx OBJECT-TYPE
            SYNTAX IndexAB
            MAX-ACCESS not-accessible
            STATUS current
            DESCRIPTION
                "The dedicated exciter (A/B)."
            ::= { lpTxCuEntry 3 }

        
        lpTxCuTransmitterMode OBJECT-TYPE
            SYNTAX INTEGER
                {
                transmitter(1),
                tranposer(2)
                }
            MAX-ACCESS read-only
            STATUS current
            DESCRIPTION
                "Selects between 1+1, N+1, or standalone transmitter. In standalone mode 
                the rear IP address is configurable."
            ::= { lpTxCuEntry 4 }

        
        lpTxCuTemperatureStatus OBJECT-TYPE
            SYNTAX INTEGER
                {
                unknown(1),
                tempHealthy(2),
                tempWarning(3),
                tempFailure(4)
                }
            MAX-ACCESS read-only
            STATUS current
            DESCRIPTION
                "Indicates the temperature state of the transmitter."
            ::= { lpTxCuEntry 6 }

        
        lpTxCuFanStatus OBJECT-TYPE
            SYNTAX INTEGER
                {
                unknown(1),
                healthy(2),
                reducedHealth(3),
                failure(4)
                }
            MAX-ACCESS read-only
            STATUS current
            DESCRIPTION
                "Indicates whether any fans have failed."
            ::= { lpTxCuEntry 7 }

        
        rackTable OBJECT-TYPE
            SYNTAX SEQUENCE OF RackEntry
            MAX-ACCESS not-accessible
            STATUS current
            DESCRIPTION
                "This table contains important commands for the racks."
            ::= { transmitter 26 }

        
        rackEntry OBJECT-TYPE
            SYNTAX RackEntry
            MAX-ACCESS not-accessible
            STATUS current
            DESCRIPTION
                "An entry for a designated rack or rack's rf probe."
            INDEX { rackTxIdx, ostDeviceIdx, rackIdx, rackRfProbeIdx }
            ::= { rackTable 1 }

        
        RackEntry ::=
            SEQUENCE { 
                rackTxIdx
                    IndexTransmitter,
                ostDeviceIdx
                    IndexAB,
                rackIdx
                    IndexRack,
                rackRfProbeIdx
                    INTEGER,
                amplifiersPerRack
                    Integer32,
                rackRfEventSignalling
                    TruthValue,
                rackReferenceVoltage
                    FloatingPoint,
                amplifiersPowerSupply
                    FloatingPoint,
                rackGeneralPurposeInput
                    INTEGER,
                rackOnOff
                    SwitchOnOff,
                rfProbePresent
                    TruthValue,
                rfProbeConfigurationLabel
                    ReadableString,
                rfProbeConfigurationNominalValue
                    Integer32,
                rfProbeThresholdRfFailLimit
                    FloatingPoint,
                rfProbeThresholdTimeoutRfFailCtr
                    Integer32,
                rfProbeThresholdWarningLimit
                    FloatingPoint,
                rfProbeCalibrationGain
                    FloatingPoint,
                rfProbeCalibrationOffset
                    FloatingPoint,
                rfProbeCalibrationSetGain
                    Trigger,
                rfProbeCalibrationSetOffset
                    Trigger,
                rfProbeMeasuredValue
                    FloatingPoint
             }

        rackTxIdx OBJECT-TYPE
            SYNTAX IndexTransmitter
            MAX-ACCESS not-accessible
            STATUS current
            DESCRIPTION
                "The index to address the transmitter."
            ::= { rackEntry 1 }

        
        ostDeviceIdx OBJECT-TYPE
            SYNTAX IndexAB
            MAX-ACCESS not-accessible
            STATUS current
            DESCRIPTION
                "The index to address outputstageA and outputstageB."
            ::= { rackEntry 2 }

        
        rackIdx OBJECT-TYPE
            SYNTAX IndexRack
            MAX-ACCESS not-accessible
            STATUS current
            DESCRIPTION
                "The index to address the racks."
            ::= { rackEntry 3 }

        
        rackRfProbeIdx OBJECT-TYPE
            SYNTAX INTEGER
                {
                forward(1),
                reflected(2)
                }
            MAX-ACCESS not-accessible
            STATUS current
            DESCRIPTION
                "The index to address forward and reflected RF probes.
                For not RF probe parameters this index is always 1."
            ::= { rackEntry 4 }

        
        amplifiersPerRack OBJECT-TYPE
            SYNTAX Integer32 (1..10)
            MAX-ACCESS read-only
            STATUS current
            DESCRIPTION
                "The number of amplifiers of a rack."
            ::= { rackEntry 6 }

        
        rackRfEventSignalling OBJECT-TYPE
            SYNTAX TruthValue
            MAX-ACCESS read-write
            STATUS current
            DESCRIPTION
                "This configures whether to signal rf events or not."
            ::= { rackEntry 7 }

        
        rackReferenceVoltage OBJECT-TYPE
            SYNTAX FloatingPoint
            UNITS "percent"
            MAX-ACCESS read-write
            STATUS current
            DESCRIPTION
                "This parameter controls the reference voltage (31.0 ... 100.0)."
            ::= { rackEntry 8 }

        
        amplifiersPowerSupply OBJECT-TYPE
            SYNTAX FloatingPoint
            UNITS "percent"
            MAX-ACCESS read-write
            STATUS current
            DESCRIPTION
                "This parameter controls the power supplies of the amplifier 
                within the rack (31.0 ... 100.0)."
            ::= { rackEntry 9 }

        
        rackGeneralPurposeInput OBJECT-TYPE
            SYNTAX INTEGER
                {
                unused(1),
                doorOpen(2),
                extCoolingWarning(3),
                extCoolingFault(4)
                }
            MAX-ACCESS read-write
            STATUS current
            DESCRIPTION
                "Setting of the general purpose input behaviour."
            ::= { rackEntry 10 }

        
        rackOnOff OBJECT-TYPE
            SYNTAX SwitchOnOff
            MAX-ACCESS read-write
            STATUS current
            DESCRIPTION
                "This switches the rack on/off."
            ::= { rackEntry 20 }

        
        rfProbePresent OBJECT-TYPE
            SYNTAX TruthValue
            MAX-ACCESS read-only
            STATUS current
            DESCRIPTION
                "If the RF probe of this rack is present."
            ::= { rackEntry 50 }

        
        rfProbeConfigurationLabel OBJECT-TYPE
            SYNTAX ReadableString (SIZE (0..12))
            MAX-ACCESS read-write
            STATUS obsolete
            DESCRIPTION
                "Name for the measured signal on RF Probe."
            ::= { rackEntry 51 }

        
        rfProbeConfigurationNominalValue OBJECT-TYPE
            SYNTAX Integer32 (0..100000)
            UNITS "W"
            MAX-ACCESS read-write
            STATUS current
            DESCRIPTION
                "The nominal value of the measured signal."
            ::= { rackEntry 52 }

        
        rfProbeThresholdRfFailLimit OBJECT-TYPE
            SYNTAX FloatingPoint
            UNITS "dB"
            MAX-ACCESS read-write
            STATUS current
            DESCRIPTION
                "Fault limit for the RF control (-20.0 ... 0.0)."
            ::= { rackEntry 55 }

        
        rfProbeThresholdTimeoutRfFailCtr OBJECT-TYPE
            SYNTAX Integer32 (1..20)
            UNITS "s"
            MAX-ACCESS read-write
            STATUS current
            DESCRIPTION
                "Timeout for RF Fail Control."
            ::= { rackEntry 56 }

        
        rfProbeThresholdWarningLimit OBJECT-TYPE
            SYNTAX FloatingPoint
            UNITS "dB"
            MAX-ACCESS read-write
            STATUS current
            DESCRIPTION
                "Warning limit for the RF control (-20.0 ... 0.0).
                
                For reflected probes:
                Warning limit for the reflection control. This limit is added to the 
                fault limit to generate the real warning limit; e.g. the fault limit 
                is -17.0dB and the warning limit is -3.0dB, so the warning is active 
                on a reflected power higher than -20.0 dB."
            ::= { rackEntry 57 }

        
        rfProbeCalibrationGain OBJECT-TYPE
            SYNTAX FloatingPoint
            UNITS "V"
            MAX-ACCESS read-only
            STATUS current
            DESCRIPTION
                "Measured value of gain calibration."
            ::= { rackEntry 60 }

        
        rfProbeCalibrationOffset OBJECT-TYPE
            SYNTAX FloatingPoint
            UNITS "V"
            MAX-ACCESS read-only
            STATUS current
            DESCRIPTION
                "Measured value of offset calibration."
            ::= { rackEntry 61 }

        
        rfProbeCalibrationSetGain OBJECT-TYPE
            SYNTAX Trigger
            MAX-ACCESS read-write
            STATUS current
            DESCRIPTION
                "Sets the gain calibration."
            ::= { rackEntry 62 }

        
        rfProbeCalibrationSetOffset OBJECT-TYPE
            SYNTAX Trigger
            MAX-ACCESS read-write
            STATUS current
            DESCRIPTION
                "Sets the offset calibration."
            ::= { rackEntry 63 }

        
        rfProbeMeasuredValue OBJECT-TYPE
            SYNTAX FloatingPoint
            UNITS "W"
            MAX-ACCESS read-only
            STATUS current
            DESCRIPTION
                "Measured forward/reflected power of antenna signal."
            ::= { rackEntry 65 }

        
        amplifierTable OBJECT-TYPE
            SYNTAX SEQUENCE OF AmplifierEntry
            MAX-ACCESS not-accessible
            STATUS current
            DESCRIPTION
                "The table for amplifier values."
            ::= { transmitter 27 }

        
        amplifierEntry OBJECT-TYPE
            SYNTAX AmplifierEntry
            MAX-ACCESS not-accessible
            STATUS current
            DESCRIPTION
                "An entry for a designated amplifier."
            INDEX { rackTxIdx, rackIdx, ampIdx }
            ::= { amplifierTable 1 }

        
        AmplifierEntry ::=
            SEQUENCE { 
                ampIdx
                    IndexAmplifier,
                ampI1A
                    FloatingPoint,
                ampI2A
                    FloatingPoint,
                ampI3A
                    FloatingPoint,
                ampI4A
                    FloatingPoint,
                ampI1B
                    FloatingPoint,
                ampI2B
                    FloatingPoint,
                ampI3B
                    FloatingPoint,
                ampI4B
                    FloatingPoint,
                ampIDrv
                    FloatingPoint,
                ampUDc
                    FloatingPoint,
                ampIDc
                    FloatingPoint,
                ampUDcControl
                    FloatingPoint,
                ampUReg
                    FloatingPoint,
                ampPowerA
                    FloatingPoint,
                ampPowerB
                    FloatingPoint,
                ampPowerOut
                    FloatingPoint,
                ampPowerReflection
                    FloatingPoint,
                ampPowerReference
                    FloatingPoint,
                ampDeltaPhase
                    FloatingPoint,
                ampCmdDeltaPhase
                    FloatingPoint
             }

        ampIdx OBJECT-TYPE
            SYNTAX IndexAmplifier
            MAX-ACCESS not-accessible
            STATUS current
            DESCRIPTION
                "Amplifier Index"
            ::= { amplifierEntry 400 }

        
        ampI1A OBJECT-TYPE
            SYNTAX FloatingPoint
            UNITS "Ampere"
            MAX-ACCESS read-only
            STATUS current
            DESCRIPTION
                "The power amplifier module current (I_1A)."
            ::= { amplifierEntry 401 }

        
        ampI2A OBJECT-TYPE
            SYNTAX FloatingPoint
            UNITS "Ampere"
            MAX-ACCESS read-only
            STATUS current
            DESCRIPTION
                "The power amplifier module current (I_2A)."
            ::= { amplifierEntry 402 }

        
        ampI3A OBJECT-TYPE
            SYNTAX FloatingPoint
            UNITS "Ampere"
            MAX-ACCESS read-only
            STATUS current
            DESCRIPTION
                "The power amplifier module current (I_3A)."
            ::= { amplifierEntry 403 }

        
        ampI4A OBJECT-TYPE
            SYNTAX FloatingPoint
            UNITS "Ampere"
            MAX-ACCESS read-only
            STATUS current
            DESCRIPTION
                "The power amplifier module current (I_4A)."
            ::= { amplifierEntry 404 }

        
        ampI1B OBJECT-TYPE
            SYNTAX FloatingPoint
            UNITS "Ampere"
            MAX-ACCESS read-only
            STATUS current
            DESCRIPTION
                "The power amplifier module current (I_1B)."
            ::= { amplifierEntry 405 }

        
        ampI2B OBJECT-TYPE
            SYNTAX FloatingPoint
            UNITS "Ampere"
            MAX-ACCESS read-only
            STATUS current
            DESCRIPTION
                "The power amplifier module current (I_2B)."
            ::= { amplifierEntry 406 }

        
        ampI3B OBJECT-TYPE
            SYNTAX FloatingPoint
            UNITS "Ampere"
            MAX-ACCESS read-only
            STATUS current
            DESCRIPTION
                "The power amplifier module current (I_3B)."
            ::= { amplifierEntry 407 }

        
        ampI4B OBJECT-TYPE
            SYNTAX FloatingPoint
            UNITS "Ampere"
            MAX-ACCESS read-only
            STATUS current
            DESCRIPTION
                "The power amplifier module current (I_4B)."
            ::= { amplifierEntry 408 }

        
        ampIDrv OBJECT-TYPE
            SYNTAX FloatingPoint
            UNITS "Ampere"
            MAX-ACCESS read-only
            STATUS current
            DESCRIPTION
                "The driver module current (I_DRV)."
            ::= { amplifierEntry 409 }

        
        ampUDc OBJECT-TYPE
            SYNTAX FloatingPoint
            UNITS "Volt"
            MAX-ACCESS read-only
            STATUS current
            DESCRIPTION
                "The power amplifier supply voltage."
            ::= { amplifierEntry 410 }

        
        ampIDc OBJECT-TYPE
            SYNTAX FloatingPoint
            UNITS "Ampere"
            MAX-ACCESS read-only
            STATUS current
            DESCRIPTION
                "The power amplifier supply current."
            ::= { amplifierEntry 411 }

        
        ampUDcControl OBJECT-TYPE
            SYNTAX FloatingPoint
            UNITS "Volt"
            MAX-ACCESS read-only
            STATUS current
            DESCRIPTION
                "The power supply control voltage."
            ::= { amplifierEntry 412 }

        
        ampUReg OBJECT-TYPE
            SYNTAX FloatingPoint
            UNITS "Volt"
            MAX-ACCESS read-only
            STATUS current
            DESCRIPTION
                "The power amplifier AGC voltage."
            ::= { amplifierEntry 413 }

        
        ampPowerA OBJECT-TYPE
            SYNTAX FloatingPoint
            UNITS "Volt"
            MAX-ACCESS read-only
            STATUS current
            DESCRIPTION
                "The voltage power detector A."
            ::= { amplifierEntry 414 }

        
        ampPowerB OBJECT-TYPE
            SYNTAX FloatingPoint
            UNITS "Volt"
            MAX-ACCESS read-only
            STATUS current
            DESCRIPTION
                "The voltage power detector B."
            ::= { amplifierEntry 415 }

        
        ampPowerOut OBJECT-TYPE
            SYNTAX FloatingPoint
            UNITS "Volt"
            MAX-ACCESS read-only
            STATUS current
            DESCRIPTION
                "The voltage forward power detector."
            ::= { amplifierEntry 416 }

        
        ampPowerReflection OBJECT-TYPE
            SYNTAX FloatingPoint
            UNITS "Volt"
            MAX-ACCESS read-only
            STATUS current
            DESCRIPTION
                "The voltage reflected power detector."
            ::= { amplifierEntry 417 }

        
        ampPowerReference OBJECT-TYPE
            SYNTAX FloatingPoint
            UNITS "Volt"
            MAX-ACCESS read-only
            STATUS current
            DESCRIPTION
                "The reference voltage for output power."
            ::= { amplifierEntry 418 }

        
        ampDeltaPhase OBJECT-TYPE
            SYNTAX FloatingPoint
            UNITS "Percent"
            MAX-ACCESS read-only
            STATUS current
            DESCRIPTION
                "The measured phase delta for output power."
            ::= { amplifierEntry 419 }

        
        ampCmdDeltaPhase OBJECT-TYPE
            SYNTAX FloatingPoint
            UNITS "Percent"
            MAX-ACCESS read-write
            STATUS current
            DESCRIPTION
                "The phase delta setting for output power.
                The range is -50.0% to 50.0%."
            ::= { amplifierEntry 420 }

        
        rfProbesTable OBJECT-TYPE
            SYNTAX SEQUENCE OF RfProbesEntry
            MAX-ACCESS not-accessible
            STATUS current
            DESCRIPTION
                "This table contains all commands for the RF probes."
            ::= { transmitter 28 }

        
        rfProbesEntry OBJECT-TYPE
            SYNTAX RfProbesEntry
            MAX-ACCESS not-accessible
            STATUS current
            DESCRIPTION
                "An entry for a designated transmitter and device."
            INDEX { cmdTxIdx }
            ::= { rfProbesTable 1 }

        
        RfProbesEntry ::=
            SEQUENCE { 
                rfProbesNetCCURfProbe1
                    FloatingPoint,
                rfProbesNetCCURfProbe2
                    FloatingPoint,
                rfProbesAntFwdNominal
                    FloatingPoint,
                rfProbesAntFwdWarningLimit
                    FloatingPoint,
                rfProbesAntFwdFailLimit
                    FloatingPoint,
                rfProbesAntFwdDelayTimeRfFail
                    Integer32,
                rfProbesAntFwdSetOffset
                    Trigger,
                rfProbesAntFwdSetGain
                    Trigger,
                rfProbesAntReflWarningLimit
                    FloatingPoint,
                rfProbesAntReflSetOffset
                    Trigger,
                rfProbesAntReflSetGain
                    Trigger,
                rfProbesDLFwdNominal
                    FloatingPoint,
                rfProbesDLFwdWarningLimit
                    FloatingPoint,
                rfProbesDLFwdFailLimit
                    FloatingPoint,
                rfProbesDLFwdDelayTimeRfFail
                    Integer32,
                rfProbesDLFwdSetOffset
                    Trigger,
                rfProbesDLFwdSetGain
                    Trigger,
                rfProbesDLReflWarningLimit
                    FloatingPoint,
                rfProbesDLReflSetOffset
                    Trigger,
                rfProbesDLReflSetGain
                    Trigger
             }

        rfProbesNetCCURfProbe1 OBJECT-TYPE
            SYNTAX FloatingPoint
            UNITS "Volt"
            MAX-ACCESS read-only
            STATUS current
            DESCRIPTION
                "Current voltage on RF Probe 1."
            ::= { rfProbesEntry 1 }

        
        rfProbesNetCCURfProbe2 OBJECT-TYPE
            SYNTAX FloatingPoint
            UNITS "Volt"
            MAX-ACCESS read-only
            STATUS current
            DESCRIPTION
                "Current voltage on RF Probe 2."
            ::= { rfProbesEntry 2 }

        
        rfProbesAntFwdNominal OBJECT-TYPE
            SYNTAX FloatingPoint
            UNITS "Watt"
            MAX-ACCESS read-write
            STATUS current
            DESCRIPTION
                "This sets the nominal value [W] of the transmitter (to antenna)."
            ::= { rfProbesEntry 3 }

        
        rfProbesAntFwdWarningLimit OBJECT-TYPE
            SYNTAX FloatingPoint
            UNITS "dB"
            MAX-ACCESS read-write
            STATUS current
            DESCRIPTION
                "This sets the warning limit for the transmitters RF control (to antenna)."
            ::= { rfProbesEntry 4 }

        
        rfProbesAntFwdFailLimit OBJECT-TYPE
            SYNTAX FloatingPoint
            UNITS "dB"
            MAX-ACCESS read-write
            STATUS current
            DESCRIPTION
                "This sets the fault limit for the transmitters RF control (to antenna)."
            ::= { rfProbesEntry 5 }

        
        rfProbesAntFwdDelayTimeRfFail OBJECT-TYPE
            SYNTAX Integer32 (1..20)
            UNITS "seconds"
            MAX-ACCESS read-write
            STATUS current
            DESCRIPTION
                "This sets the delay time for the RF Fail control (to antenna)."
            ::= { rfProbesEntry 6 }

        
        rfProbesAntFwdSetOffset OBJECT-TYPE
            SYNTAX Trigger
            MAX-ACCESS read-write
            STATUS current
            DESCRIPTION
                "This triggers Set Offset."
            ::= { rfProbesEntry 7 }

        
        rfProbesAntFwdSetGain OBJECT-TYPE
            SYNTAX Trigger
            MAX-ACCESS read-write
            STATUS current
            DESCRIPTION
                "This triggers Set Gain."
            ::= { rfProbesEntry 8 }

        
        rfProbesAntReflWarningLimit OBJECT-TYPE
            SYNTAX FloatingPoint
            UNITS "dB"
            MAX-ACCESS read-write
            STATUS current
            DESCRIPTION
                "This sets the warning limit for the transmitters reflection control (to antenna)."
            ::= { rfProbesEntry 9 }

        
        rfProbesAntReflSetOffset OBJECT-TYPE
            SYNTAX Trigger
            MAX-ACCESS read-write
            STATUS current
            DESCRIPTION
                "This triggers Set Offset."
            ::= { rfProbesEntry 10 }

        
        rfProbesAntReflSetGain OBJECT-TYPE
            SYNTAX Trigger
            MAX-ACCESS read-write
            STATUS current
            DESCRIPTION
                "This triggers Set Gain."
            ::= { rfProbesEntry 11 }

        
        rfProbesDLFwdNominal OBJECT-TYPE
            SYNTAX FloatingPoint
            UNITS "Watt"
            MAX-ACCESS read-write
            STATUS current
            DESCRIPTION
                "This sets the nominal value [W] of the transmitter (to dummyload)."
            ::= { rfProbesEntry 12 }

        
        rfProbesDLFwdWarningLimit OBJECT-TYPE
            SYNTAX FloatingPoint
            UNITS "dB"
            MAX-ACCESS read-write
            STATUS current
            DESCRIPTION
                "This sets the warning limit for the transmitters RF control (to dummyload)."
            ::= { rfProbesEntry 13 }

        
        rfProbesDLFwdFailLimit OBJECT-TYPE
            SYNTAX FloatingPoint
            UNITS "dB"
            MAX-ACCESS read-write
            STATUS current
            DESCRIPTION
                "This sets the fault limit for the transmitters RF control (to dummyload)."
            ::= { rfProbesEntry 14 }

        
        rfProbesDLFwdDelayTimeRfFail OBJECT-TYPE
            SYNTAX Integer32 (1..20)
            UNITS "seconds"
            MAX-ACCESS read-write
            STATUS current
            DESCRIPTION
                "This sets the delay time for the RF Fail control (to dummyload)."
            ::= { rfProbesEntry 15 }

        
        rfProbesDLFwdSetOffset OBJECT-TYPE
            SYNTAX Trigger
            MAX-ACCESS read-write
            STATUS current
            DESCRIPTION
                "This triggers Set Offset."
            ::= { rfProbesEntry 16 }

        
        rfProbesDLFwdSetGain OBJECT-TYPE
            SYNTAX Trigger
            MAX-ACCESS read-write
            STATUS current
            DESCRIPTION
                "This triggers Set Gain."
            ::= { rfProbesEntry 17 }

        
        rfProbesDLReflWarningLimit OBJECT-TYPE
            SYNTAX FloatingPoint
            UNITS "dB"
            MAX-ACCESS read-write
            STATUS current
            DESCRIPTION
                "This sets the warning limit for the transmitters reflection control (to dummyload)."
            ::= { rfProbesEntry 18 }

        
        rfProbesDLReflSetOffset OBJECT-TYPE
            SYNTAX Trigger
            MAX-ACCESS read-write
            STATUS current
            DESCRIPTION
                "This triggers Set Offset."
            ::= { rfProbesEntry 19 }

        
        rfProbesDLReflSetGain OBJECT-TYPE
            SYNTAX Trigger
            MAX-ACCESS read-write
            STATUS current
            DESCRIPTION
                "This triggers Set Gain."
            ::= { rfProbesEntry 20 }

        
-- *****************************************************************************
-- **          statusTxB
-- *****************************************************************************
        txB OBJECT IDENTIFIER ::= { transmitter 40 }

        
        logbookTxB OBJECT IDENTIFIER ::= { txB 1 }

        
        txBNetCCUNumberOfEntries OBJECT-TYPE
            SYNTAX LogbookMaxEntryNumber
            MAX-ACCESS read-only
            STATUS current
            DESCRIPTION
                "The number of entries in logbook."
            ::= { logbookTxB 1 }

        
        txBNetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxB 2 }

        
        txBNetCCULogbookTable OBJECT-TYPE
            SYNTAX SEQUENCE OF TxBNetCCULogbookEntry
            MAX-ACCESS not-accessible
            STATUS current
            DESCRIPTION
                "NetCCU logbook table."
            ::= { logbookTxB 3 }

        
        txBNetCCULogbookEntry OBJECT-TYPE
            SYNTAX TxBNetCCULogbookEntry
            MAX-ACCESS not-accessible
            STATUS current
            DESCRIPTION
                "This is a entry in the logbook."
            INDEX { txBNetCCULogbookEntryIdx }
            ::= { txBNetCCULogbookTable 1 }

        
        TxBNetCCULogbookEntry ::=
            SEQUENCE { 
                txBNetCCULogbookEntryIdx
                    LogbookMaxEntryNumber,
                txBNetCCULogbookEntryNbr
                    LogbookMaxEntryNumber,
                txBNetCCULogbookType
                    EventClass,
                txBNetCCULogbookSlope
                    LogbookEntrySlope,
                txBNetCCULogbookMessage
                    LogbookEntryMessagesNetCCU,
                txBNetCCULogbookDateTime
                    DateAndTime
             }

        txBNetCCULogbookEntryIdx OBJECT-TYPE
            SYNTAX LogbookMaxEntryNumber
            MAX-ACCESS not-accessible
            STATUS current
            DESCRIPTION
                "This is an increasing number from 1 to 128. It is used as an index column for SNMP."
            ::= { txBNetCCULogbookEntry 1 }

        
        txBNetCCULogbookEntryNbr OBJECT-TYPE
            SYNTAX LogbookMaxEntryNumber
            MAX-ACCESS read-only
            STATUS current
            DESCRIPTION
                "This is the number of the logbook entry. It is an decreasing number from max 128 down to 1."
            ::= { txBNetCCULogbookEntry 2 }

        
        txBNetCCULogbookType OBJECT-TYPE
            SYNTAX EventClass
            MAX-ACCESS read-only
            STATUS current
            DESCRIPTION
                "Can either be Fault, Warning or State."
            ::= { txBNetCCULogbookEntry 3 }

        
        txBNetCCULogbookSlope OBJECT-TYPE
            SYNTAX LogbookEntrySlope
            MAX-ACCESS read-only
            STATUS current
            DESCRIPTION
                "Either set (event raises) or reset (event disappears)"
            ::= { txBNetCCULogbookEntry 4 }

        
        txBNetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txBNetCCULogbookEntry 5 }

        
        txBNetCCULogbookDateTime OBJECT-TYPE
            SYNTAX DateAndTime
            MAX-ACCESS read-only
            STATUS current
            DESCRIPTION
                "The time of the logbook entry."
            ::= { txBNetCCULogbookEntry 6 }

        
        txBExciterANumberOfEntries OBJECT-TYPE
            SYNTAX LogbookMaxEntryNumber
            MAX-ACCESS read-only
            STATUS current
            DESCRIPTION
                "The number of entries in logbook."
            ::= { logbookTxB 4 }

        
        txBExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxB 5 }

        
        txBExciterALogbookTable OBJECT-TYPE
            SYNTAX SEQUENCE OF TxBExciterALogbookEntry
            MAX-ACCESS not-accessible
            STATUS current
            DESCRIPTION
                "ExciterA logbook table."
            ::= { logbookTxB 6 }

        
        txBExciterALogbookEntry OBJECT-TYPE
            SYNTAX TxBExciterALogbookEntry
            MAX-ACCESS not-accessible
            STATUS current
            DESCRIPTION
                "This is a entry in the logbook."
            INDEX { txBExcALogbookEntryIdx }
            ::= { txBExciterALogbookTable 1 }

        
        TxBExciterALogbookEntry ::=
            SEQUENCE { 
                txBExcALogbookEntryIdx
                    LogbookMaxEntryNumber,
                txBExcALogbookEntryNbr
                    LogbookMaxEntryNumber,
                txBExcALogbookType
                    EventClass,
                txBExcALogbookSlope
                    LogbookEntrySlope,
                txBExcALogbookMessage
                    LogbookEntryMessagesExcFM,
                txBExcALogbookDateTime
                    DateAndTime
             }

        txBExcALogbookEntryIdx OBJECT-TYPE
            SYNTAX LogbookMaxEntryNumber
            MAX-ACCESS not-accessible
            STATUS current
            DESCRIPTION
                "This is an increasing number from 1 to 128. It is used as an index column for SNMP."
            ::= { txBExciterALogbookEntry 1 }

        
        txBExcALogbookEntryNbr OBJECT-TYPE
            SYNTAX LogbookMaxEntryNumber
            MAX-ACCESS read-only
            STATUS current
            DESCRIPTION
                "This is the number of the logbook entry. It is an decreasing number from max 128 down to 1."
            ::= { txBExciterALogbookEntry 2 }

        
        txBExcALogbookType OBJECT-TYPE
            SYNTAX EventClass
            MAX-ACCESS read-only
            STATUS current
            DESCRIPTION
                "Can either be Fault, Warning or State."
            ::= { txBExciterALogbookEntry 3 }

        
        txBExcALogbookSlope OBJECT-TYPE
            SYNTAX LogbookEntrySlope
            MAX-ACCESS read-only
            STATUS current
            DESCRIPTION
                "Either set (event raises) or reset (event disappears)"
            ::= { txBExciterALogbookEntry 4 }

        
        txBExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txBExciterALogbookEntry 5 }

        
        txBExcALogbookDateTime OBJECT-TYPE
            SYNTAX DateAndTime
            MAX-ACCESS read-only
            STATUS current
            DESCRIPTION
                "The time of the logbook entry."
            ::= { txBExciterALogbookEntry 6 }

        
        txBOutputstageANumberOfEntries OBJECT-TYPE
            SYNTAX LogbookMaxEntryNumber
            MAX-ACCESS read-only
            STATUS current
            DESCRIPTION
                "The number of entries in logbook."
            ::= { logbookTxB 7 }

        
        txBOutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxB 8 }

        
        txBOutputstageALogbookTable OBJECT-TYPE
            SYNTAX SEQUENCE OF TxBOutputstageALogbookEntry
            MAX-ACCESS not-accessible
            STATUS current
            DESCRIPTION
                "OutputstageA logbook table."
            ::= { logbookTxB 9 }

        
        txBOutputstageALogbookEntry OBJECT-TYPE
            SYNTAX TxBOutputstageALogbookEntry
            MAX-ACCESS not-accessible
            STATUS current
            DESCRIPTION
                "This is a entry in the logbook."
            INDEX { txBOstALogbookEntryIdx }
            ::= { txBOutputstageALogbookTable 1 }

        
        TxBOutputstageALogbookEntry ::=
            SEQUENCE { 
                txBOstALogbookEntryIdx
                    LogbookMaxEntryNumber,
                txBOstALogbookEntryNbr
                    LogbookMaxEntryNumber,
                txBOstALogbookType
                    EventClass,
                txBOstALogbookSlope
                    LogbookEntrySlope,
                txBOstALogbookMessage
                    LogbookEntryMessagesOST,
                txBOstALogbookDateTime
                    DateAndTime
             }

        txBOstALogbookEntryIdx OBJECT-TYPE
            SYNTAX LogbookMaxEntryNumber
            MAX-ACCESS not-accessible
            STATUS current
            DESCRIPTION
                "This is an increasing number from 1 to 128. It is used as an index column for SNMP."
            ::= { txBOutputstageALogbookEntry 1 }

        
        txBOstALogbookEntryNbr OBJECT-TYPE
            SYNTAX LogbookMaxEntryNumber
            MAX-ACCESS read-only
            STATUS current
            DESCRIPTION
                "This is the number of the logbook entry. It is an decreasing number from max 128 down to 1."
            ::= { txBOutputstageALogbookEntry 2 }

        
        txBOstALogbookType OBJECT-TYPE
            SYNTAX EventClass
            MAX-ACCESS read-only
            STATUS current
            DESCRIPTION
                "Can either be Fault, Warning or State."
            ::= { txBOutputstageALogbookEntry 3 }

        
        txBOstALogbookSlope OBJECT-TYPE
            SYNTAX LogbookEntrySlope
            MAX-ACCESS read-only
            STATUS current
            DESCRIPTION
                "Either set (event raises) or reset (event disappears)"
            ::= { txBOutputstageALogbookEntry 4 }

        
        txBOstALogbookMessage OBJECT-TYPE
            SYNTAX LogbookEntryMessagesOST
            MAX-ACCESS read-only
            STATUS current
            DESCRIPTION
                "See RS-XX8000-COMMON-MIB - TextualConvention for details."
            ::= { txBOutputstageALogbookEntry 5 }

        
        txBOstALogbookDateTime OBJECT-TYPE
            SYNTAX DateAndTime
            MAX-ACCESS read-only
            STATUS current
            DESCRIPTION
                "The time of the logbook entry."
            ::= { txBOutputstageALogbookEntry 6 }

        
        txBExciterBNumberOfEntries OBJECT-TYPE
            SYNTAX LogbookMaxEntryNumber
            MAX-ACCESS read-only
            STATUS current
            DESCRIPTION
                "The number of entries in logbook."
            ::= { logbookTxB 13 }

        
        txBExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxB 14 }

        
        txBExciterBLogbookTable OBJECT-TYPE
            SYNTAX SEQUENCE OF TxBExciterBLogbookEntry
            MAX-ACCESS not-accessible
            STATUS current
            DESCRIPTION
                "ExciterA logbook table."
            ::= { logbookTxB 15 }

        
        txBExciterBLogbookEntry OBJECT-TYPE
            SYNTAX TxBExciterBLogbookEntry
            MAX-ACCESS not-accessible
            STATUS current
            DESCRIPTION
                "This is a entry in the logbook."
            INDEX { txBExcBLogbookEntryIdx }
            ::= { txBExciterBLogbookTable 1 }

        
        TxBExciterBLogbookEntry ::=
            SEQUENCE { 
                txBExcBLogbookEntryIdx
                    LogbookMaxEntryNumber,
                txBExcBLogbookEntryNbr
                    LogbookMaxEntryNumber,
                txBExcBLogbookType
                    EventClass,
                txBExcBLogbookSlope
                    LogbookEntrySlope,
                txBExcBLogbookMessage
                    LogbookEntryMessagesExcFM,
                txBExcBLogbookDateTime
                    DateAndTime
             }

        txBExcBLogbookEntryIdx OBJECT-TYPE
            SYNTAX LogbookMaxEntryNumber
            MAX-ACCESS not-accessible
            STATUS current
            DESCRIPTION
                "This is an increasing number from 1 to 128. It is used as an index column for SNMP."
            ::= { txBExciterBLogbookEntry 1 }

        
        txBExcBLogbookEntryNbr OBJECT-TYPE
            SYNTAX LogbookMaxEntryNumber
            MAX-ACCESS read-only
            STATUS current
            DESCRIPTION
                "This is the number of the logbook entry. It is an decreasing number from max 128 down to 1."
            ::= { txBExciterBLogbookEntry 2 }

        
        txBExcBLogbookType OBJECT-TYPE
            SYNTAX EventClass
            MAX-ACCESS read-only
            STATUS current
            DESCRIPTION
                "Can either be Fault, Warning or State."
            ::= { txBExciterBLogbookEntry 3 }

        
        txBExcBLogbookSlope OBJECT-TYPE
            SYNTAX LogbookEntrySlope
            MAX-ACCESS read-only
            STATUS current
            DESCRIPTION
                "Either set (event raises) or reset (event disappears)"
            ::= { txBExciterBLogbookEntry 4 }

        
        txBExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txBExciterBLogbookEntry 5 }

        
        txBExcBLogbookDateTime OBJECT-TYPE
            SYNTAX DateAndTime
            MAX-ACCESS read-only
            STATUS current
            DESCRIPTION
                "The time of the logbook entry."
            ::= { txBExciterBLogbookEntry 6 }

        
        outputstageATxB OBJECT IDENTIFIER ::= { txB 2 }

        
        txBOstARackTable OBJECT-TYPE
            SYNTAX SEQUENCE OF TxBOstARackEntry
            MAX-ACCESS not-accessible
            STATUS current
            DESCRIPTION
                "The table of racks."
            ::= { outputstageATxB 1 }

        
--  Hue nur die ersten 3 Werte
        txBOstARackEntry OBJECT-TYPE
            SYNTAX TxBOstARackEntry
            MAX-ACCESS not-accessible
            STATUS current
            DESCRIPTION
                "A row (an entry) for one rack."
            INDEX { txBOstARackIdx }
            ::= { txBOstARackTable 1 }

        
        TxBOstARackEntry ::=
            SEQUENCE { 
                txBOstARackIdx
                    IndexRack,
                txBOstARackInletTemperature
                    FloatingPoint,
                txBOstARackOutletTemperature
                    FloatingPoint,
                txBOstARackAuxPowerSupply
                    FloatingPoint
             }

        txBOstARackIdx OBJECT-TYPE
            SYNTAX IndexRack
            MAX-ACCESS not-accessible
            STATUS current
            DESCRIPTION
                "The rack number (1..10)."
            ::= { txBOstARackEntry 1 }

        
        txBOstARackInletTemperature OBJECT-TYPE
            SYNTAX FloatingPoint
            UNITS "Degree Celsius"
            MAX-ACCESS read-only
            STATUS current
            DESCRIPTION
                "The inlet temperature."
            ::= { txBOstARackEntry 2 }

        
        txBOstARackOutletTemperature OBJECT-TYPE
            SYNTAX FloatingPoint
            UNITS "Degree Celsius"
            MAX-ACCESS read-only
            STATUS current
            DESCRIPTION
                "The outlet temperature."
            ::= { txBOstARackEntry 3 }

        
        txBOstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txBOstARackEntry 4 }

        
        txA1 OBJECT IDENTIFIER ::= { transmitter 41 }

        
        logbookTxA1 OBJECT IDENTIFIER ::= { txA1 1 }

        
        txA1NetCCUNumberOfEntries OBJECT-TYPE
            SYNTAX LogbookMaxEntryNumber
            MAX-ACCESS read-only
            STATUS current
            DESCRIPTION
                "The number of entries in logbook."
            ::= { logbookTxA1 1 }

        
        txA1NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 2 }

        
        txA1NetCCULogbookTable OBJECT-TYPE
            SYNTAX SEQUENCE OF TxA1NetCCULogbookEntry
            MAX-ACCESS not-accessible
            STATUS current
            DESCRIPTION
                "NetCCU logbook table."
            ::= { logbookTxA1 3 }

        
        txA1NetCCULogbookEntry OBJECT-TYPE
            SYNTAX TxA1NetCCULogbookEntry
            MAX-ACCESS not-accessible
            STATUS current
            DESCRIPTION
                "This is a entry in the logbook."
            INDEX { txA1NetCCULogbookEntryIdx }
            ::= { txA1NetCCULogbookTable 1 }

        
        TxA1NetCCULogbookEntry ::=
            SEQUENCE { 
                txA1NetCCULogbookEntryIdx
                    LogbookMaxEntryNumber,
                txA1NetCCULogbookEntryNbr
                    LogbookMaxEntryNumber,
                txA1NetCCULogbookType
                    EventClass,
                txA1NetCCULogbookSlope
                    LogbookEntrySlope,
                txA1NetCCULogbookMessage
                    LogbookEntryMessagesNetCCU,
                txA1NetCCULogbookDateTime
                    DateAndTime
             }

        txA1NetCCULogbookEntryIdx OBJECT-TYPE
            SYNTAX LogbookMaxEntryNumber
            MAX-ACCESS not-accessible
            STATUS current
            DESCRIPTION
                "This is an increasing number from 1 to 128. It is used as an index column for SNMP."
            ::= { txA1NetCCULogbookEntry 1 }

        
        txA1NetCCULogbookEntryNbr OBJECT-TYPE
            SYNTAX LogbookMaxEntryNumber
            MAX-ACCESS read-only
            STATUS current
            DESCRIPTION
                "This is the number of the logbook entry. It is an decreasing number from max 128 down to 1."
            ::= { txA1NetCCULogbookEntry 2 }

        
        txA1NetCCULogbookType OBJECT-TYPE
            SYNTAX EventClass
            MAX-ACCESS read-only
            STATUS current
            DESCRIPTION
                "Can either be Fault, Warning or State."
            ::= { txA1NetCCULogbookEntry 3 }

        
        txA1NetCCULogbookSlope OBJECT-TYPE
            SYNTAX LogbookEntrySlope
            MAX-ACCESS read-only
            STATUS current
            DESCRIPTION
                "Either set (event raises) or reset (event disappears)"
            ::= { txA1NetCCULogbookEntry 4 }

        
        txA1NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA1NetCCULogbookEntry 5 }

        
        txA1NetCCULogbookDateTime OBJECT-TYPE
            SYNTAX DateAndTime
            MAX-ACCESS read-only
            STATUS current
            DESCRIPTION
                "The time of the logbook entry."
            ::= { txA1NetCCULogbookEntry 6 }

        
        txA1ExciterANumberOfEntries OBJECT-TYPE
            SYNTAX LogbookMaxEntryNumber
            MAX-ACCESS read-only
            STATUS current
            DESCRIPTION
                "The number of entries in logbook."
            ::= { logbookTxA1 4 }

        
        txA1ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 5 }

        
        txA1ExciterALogbookTable OBJECT-TYPE
            SYNTAX SEQUENCE OF TxA1ExciterALogbookEntry
            MAX-ACCESS not-accessible
            STATUS current
            DESCRIPTION
                "ExciterA logbook table."
            ::= { logbookTxA1 6 }

        
        txA1ExciterALogbookEntry OBJECT-TYPE
            SYNTAX TxA1ExciterALogbookEntry
            MAX-ACCESS not-accessible
            STATUS current
            DESCRIPTION
                "This is a entry in the logbook."
            INDEX { txA1ExcALogbookEntryIdx }
            ::= { txA1ExciterALogbookTable 1 }

        
        TxA1ExciterALogbookEntry ::=
            SEQUENCE { 
                txA1ExcALogbookEntryIdx
                    LogbookMaxEntryNumber,
                txA1ExcALogbookEntryNbr
                    LogbookMaxEntryNumber,
                txA1ExcALogbookType
                    EventClass,
                txA1ExcALogbookSlope
                    LogbookEntrySlope,
                txA1ExcALogbookMessage
                    LogbookEntryMessagesExcFM,
                txA1ExcALogbookDateTime
                    DateAndTime
             }

        txA1ExcALogbookEntryIdx OBJECT-TYPE
            SYNTAX LogbookMaxEntryNumber
            MAX-ACCESS not-accessible
            STATUS current
            DESCRIPTION
                "This is an increasing number from 1 to 128. It is used as an index column for SNMP."
            ::= { txA1ExciterALogbookEntry 1 }

        
        txA1ExcALogbookEntryNbr OBJECT-TYPE
            SYNTAX LogbookMaxEntryNumber
            MAX-ACCESS read-only
            STATUS current
            DESCRIPTION
                "This is the number of the logbook entry. It is an decreasing number from max 128 down to 1."
            ::= { txA1ExciterALogbookEntry 2 }

        
        txA1ExcALogbookType OBJECT-TYPE
            SYNTAX EventClass
            MAX-ACCESS read-only
            STATUS current
            DESCRIPTION
                "Can either be Fault, Warning or State."
            ::= { txA1ExciterALogbookEntry 3 }

        
        txA1ExcALogbookSlope OBJECT-TYPE
            SYNTAX LogbookEntrySlope
            MAX-ACCESS read-only
            STATUS current
            DESCRIPTION
                "Either set (event raises) or reset (event disappears)"
            ::= { txA1ExciterALogbookEntry 4 }

        
        txA1ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA1ExciterALogbookEntry 5 }

        
        txA1ExcALogbookDateTime OBJECT-TYPE
            SYNTAX DateAndTime
            MAX-ACCESS read-only
            STATUS current
            DESCRIPTION
                "The time of the logbook entry."
            ::= { txA1ExciterALogbookEntry 6 }

        
        txA1OutputstageANumberOfEntries OBJECT-TYPE
            SYNTAX LogbookMaxEntryNumber
            MAX-ACCESS read-only
            STATUS current
            DESCRIPTION
                "The number of entries in logbook."
            ::= { logbookTxA1 7 }

        
        txA1OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 8 }

        
        txA1OutputstageALogbookTable OBJECT-TYPE
            SYNTAX SEQUENCE OF TxA1OutputstageALogbookEntry
            MAX-ACCESS not-accessible
            STATUS current
            DESCRIPTION
                "OutputstageA logbook table."
            ::= { logbookTxA1 9 }

        
        txA1OutputstageALogbookEntry OBJECT-TYPE
            SYNTAX TxA1OutputstageALogbookEntry
            MAX-ACCESS not-accessible
            STATUS current
            DESCRIPTION
                "This is a entry in the logbook."
            INDEX { txA1OstALogbookEntryIdx }
            ::= { txA1OutputstageALogbookTable 1 }

        
        TxA1OutputstageALogbookEntry ::=
            SEQUENCE { 
                txA1OstALogbookEntryIdx
                    LogbookMaxEntryNumber,
                txA1OstALogbookEntryNbr
                    LogbookMaxEntryNumber,
                txA1OstALogbookType
                    EventClass,
                txA1OstALogbookSlope
                    LogbookEntrySlope,
                txA1OstALogbookMessage
                    LogbookEntryMessagesOST,
                txA1OstALogbookDateTime
                    DateAndTime
             }

        txA1OstALogbookEntryIdx OBJECT-TYPE
            SYNTAX LogbookMaxEntryNumber
            MAX-ACCESS not-accessible
            STATUS current
            DESCRIPTION
                "This is an increasing number from 1 to 128. It is used as an index column for SNMP."
            ::= { txA1OutputstageALogbookEntry 1 }

        
        txA1OstALogbookEntryNbr OBJECT-TYPE
            SYNTAX LogbookMaxEntryNumber
            MAX-ACCESS read-only
            STATUS current
            DESCRIPTION
                "This is the number of the logbook entry. It is an decreasing number from max 128 down to 1."
            ::= { txA1OutputstageALogbookEntry 2 }

        
        txA1OstALogbookType OBJECT-TYPE
            SYNTAX EventClass
            MAX-ACCESS read-only
            STATUS current
            DESCRIPTION
                "Can either be Fault, Warning or State."
            ::= { txA1OutputstageALogbookEntry 3 }

        
        txA1OstALogbookSlope OBJECT-TYPE
            SYNTAX LogbookEntrySlope
            MAX-ACCESS read-only
            STATUS current
            DESCRIPTION
                "Either set (event raises) or reset (event disappears)"
            ::= { txA1OutputstageALogbookEntry 4 }

        
        txA1OstALogbookMessage OBJECT-TYPE
            SYNTAX LogbookEntryMessagesOST
            MAX-ACCESS read-only
            STATUS current
            DESCRIPTION
                "See RS-XX8000-COMMON-MIB - TextualConvention for details."
            ::= { txA1OutputstageALogbookEntry 5 }

        
        txA1OstALogbookDateTime OBJECT-TYPE
            SYNTAX DateAndTime
            MAX-ACCESS read-only
            STATUS current
            DESCRIPTION
                "The time of the logbook entry."
            ::= { txA1OutputstageALogbookEntry 6 }

        
        txA1ExciterBNumberOfEntries OBJECT-TYPE
            SYNTAX LogbookMaxEntryNumber
            MAX-ACCESS read-only
            STATUS current
            DESCRIPTION
                "The number of entries in logbook."
            ::= { logbookTxA1 13 }

        
        txA1ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA1 14 }

        
        txA1ExciterBLogbookTable OBJECT-TYPE
            SYNTAX SEQUENCE OF TxA1ExciterBLogbookEntry
            MAX-ACCESS not-accessible
            STATUS current
            DESCRIPTION
                "ExciterA logbook table."
            ::= { logbookTxA1 15 }

        
        txA1ExciterBLogbookEntry OBJECT-TYPE
            SYNTAX TxA1ExciterBLogbookEntry
            MAX-ACCESS not-accessible
            STATUS current
            DESCRIPTION
                "This is a entry in the logbook."
            INDEX { txA1ExcBLogbookEntryIdx }
            ::= { txA1ExciterBLogbookTable 1 }

        
        TxA1ExciterBLogbookEntry ::=
            SEQUENCE { 
                txA1ExcBLogbookEntryIdx
                    LogbookMaxEntryNumber,
                txA1ExcBLogbookEntryNbr
                    LogbookMaxEntryNumber,
                txA1ExcBLogbookType
                    EventClass,
                txA1ExcBLogbookSlope
                    LogbookEntrySlope,
                txA1ExcBLogbookMessage
                    LogbookEntryMessagesExcFM,
                txA1ExcBLogbookDateTime
                    DateAndTime
             }

        txA1ExcBLogbookEntryIdx OBJECT-TYPE
            SYNTAX LogbookMaxEntryNumber
            MAX-ACCESS not-accessible
            STATUS current
            DESCRIPTION
                "This is an increasing number from 1 to 128. It is used as an index column for SNMP."
            ::= { txA1ExciterBLogbookEntry 1 }

        
        txA1ExcBLogbookEntryNbr OBJECT-TYPE
            SYNTAX LogbookMaxEntryNumber
            MAX-ACCESS read-only
            STATUS current
            DESCRIPTION
                "This is the number of the logbook entry. It is an decreasing number from max 128 down to 1."
            ::= { txA1ExciterBLogbookEntry 2 }

        
        txA1ExcBLogbookType OBJECT-TYPE
            SYNTAX EventClass
            MAX-ACCESS read-only
            STATUS current
            DESCRIPTION
                "Can either be Fault, Warning or State."
            ::= { txA1ExciterBLogbookEntry 3 }

        
        txA1ExcBLogbookSlope OBJECT-TYPE
            SYNTAX LogbookEntrySlope
            MAX-ACCESS read-only
            STATUS current
            DESCRIPTION
                "Either set (event raises) or reset (event disappears)"
            ::= { txA1ExciterBLogbookEntry 4 }

        
        txA1ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA1ExciterBLogbookEntry 5 }

        
        txA1ExcBLogbookDateTime OBJECT-TYPE
            SYNTAX DateAndTime
            MAX-ACCESS read-only
            STATUS current
            DESCRIPTION
                "The time of the logbook entry."
            ::= { txA1ExciterBLogbookEntry 6 }

        
        outputstageATxA1 OBJECT IDENTIFIER ::= { txA1 2 }

        
        txA1OstARackTable OBJECT-TYPE
            SYNTAX SEQUENCE OF TxA1OstARackEntry
            MAX-ACCESS not-accessible
            STATUS current
            DESCRIPTION
                "The table of racks."
            ::= { outputstageATxA1 1 }

        
        txA1OstARackEntry OBJECT-TYPE
            SYNTAX TxA1OstARackEntry
            MAX-ACCESS not-accessible
            STATUS current
            DESCRIPTION
                "A row (an entry) for one rack."
            INDEX { txA1OstARackIdx }
            ::= { txA1OstARackTable 1 }

        
        TxA1OstARackEntry ::=
            SEQUENCE { 
                txA1OstARackIdx
                    IndexRack,
                txA1OstARackInletTemperature
                    FloatingPoint,
                txA1OstARackOutletTemperature
                    FloatingPoint,
                txA1OstARackAuxPowerSupply
                    FloatingPoint
             }

        txA1OstARackIdx OBJECT-TYPE
            SYNTAX IndexRack
            MAX-ACCESS not-accessible
            STATUS current
            DESCRIPTION
                "The rack number (1..10)."
            ::= { txA1OstARackEntry 1 }

        
        txA1OstARackInletTemperature OBJECT-TYPE
            SYNTAX FloatingPoint
            UNITS "Degree Celsius"
            MAX-ACCESS read-only
            STATUS current
            DESCRIPTION
                "The inlet temperature."
            ::= { txA1OstARackEntry 2 }

        
        txA1OstARackOutletTemperature OBJECT-TYPE
            SYNTAX FloatingPoint
            UNITS "Degree Celsius"
            MAX-ACCESS read-only
            STATUS current
            DESCRIPTION
                "The outlet temperature."
            ::= { txA1OstARackEntry 3 }

        
        txA1OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA1OstARackEntry 4 }

        
        txA2 OBJECT IDENTIFIER ::= { transmitter 42 }

        
        logbookTxA2 OBJECT IDENTIFIER ::= { txA2 1 }

        
        txA2NetCCUNumberOfEntries OBJECT-TYPE
            SYNTAX LogbookMaxEntryNumber
            MAX-ACCESS read-only
            STATUS current
            DESCRIPTION
                "The number of entries in logbook."
            ::= { logbookTxA2 1 }

        
        txA2NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 2 }

        
        txA2NetCCULogbookTable OBJECT-TYPE
            SYNTAX SEQUENCE OF TxA2NetCCULogbookEntry
            MAX-ACCESS not-accessible
            STATUS current
            DESCRIPTION
                "NetCCU logbook table."
            ::= { logbookTxA2 3 }

        
        txA2NetCCULogbookEntry OBJECT-TYPE
            SYNTAX TxA2NetCCULogbookEntry
            MAX-ACCESS not-accessible
            STATUS current
            DESCRIPTION
                "This is a entry in the logbook."
            INDEX { txA2NetCCULogbookEntryIdx }
            ::= { txA2NetCCULogbookTable 1 }

        
        TxA2NetCCULogbookEntry ::=
            SEQUENCE { 
                txA2NetCCULogbookEntryIdx
                    LogbookMaxEntryNumber,
                txA2NetCCULogbookEntryNbr
                    LogbookMaxEntryNumber,
                txA2NetCCULogbookType
                    EventClass,
                txA2NetCCULogbookSlope
                    LogbookEntrySlope,
                txA2NetCCULogbookMessage
                    LogbookEntryMessagesNetCCU,
                txA2NetCCULogbookDateTime
                    DateAndTime
             }

        txA2NetCCULogbookEntryIdx OBJECT-TYPE
            SYNTAX LogbookMaxEntryNumber
            MAX-ACCESS not-accessible
            STATUS current
            DESCRIPTION
                "This is an increasing number from 1 to 128. It is used as an index column for SNMP."
            ::= { txA2NetCCULogbookEntry 1 }

        
        txA2NetCCULogbookEntryNbr OBJECT-TYPE
            SYNTAX LogbookMaxEntryNumber
            MAX-ACCESS read-only
            STATUS current
            DESCRIPTION
                "This is the number of the logbook entry. It is an decreasing number from max 128 down to 1."
            ::= { txA2NetCCULogbookEntry 2 }

        
        txA2NetCCULogbookType OBJECT-TYPE
            SYNTAX EventClass
            MAX-ACCESS read-only
            STATUS current
            DESCRIPTION
                "Can either be Fault, Warning or State."
            ::= { txA2NetCCULogbookEntry 3 }

        
        txA2NetCCULogbookSlope OBJECT-TYPE
            SYNTAX LogbookEntrySlope
            MAX-ACCESS read-only
            STATUS current
            DESCRIPTION
                "Either set (event raises) or reset (event disappears)"
            ::= { txA2NetCCULogbookEntry 4 }

        
        txA2NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA2NetCCULogbookEntry 5 }

        
        txA2NetCCULogbookDateTime OBJECT-TYPE
            SYNTAX DateAndTime
            MAX-ACCESS read-only
            STATUS current
            DESCRIPTION
                "The time of the logbook entry."
            ::= { txA2NetCCULogbookEntry 6 }

        
        txA2ExciterANumberOfEntries OBJECT-TYPE
            SYNTAX LogbookMaxEntryNumber
            MAX-ACCESS read-only
            STATUS current
            DESCRIPTION
                "The number of entries in logbook."
            ::= { logbookTxA2 4 }

        
        txA2ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 5 }

        
        txA2ExciterALogbookTable OBJECT-TYPE
            SYNTAX SEQUENCE OF TxA2ExciterALogbookEntry
            MAX-ACCESS not-accessible
            STATUS current
            DESCRIPTION
                "ExciterA logbook table."
            ::= { logbookTxA2 6 }

        
        txA2ExciterALogbookEntry OBJECT-TYPE
            SYNTAX TxA2ExciterALogbookEntry
            MAX-ACCESS not-accessible
            STATUS current
            DESCRIPTION
                "This is a entry in the logbook."
            INDEX { txA2ExcALogbookEntryIdx }
            ::= { txA2ExciterALogbookTable 1 }

        
        TxA2ExciterALogbookEntry ::=
            SEQUENCE { 
                txA2ExcALogbookEntryIdx
                    LogbookMaxEntryNumber,
                txA2ExcALogbookEntryNbr
                    LogbookMaxEntryNumber,
                txA2ExcALogbookType
                    EventClass,
                txA2ExcALogbookSlope
                    LogbookEntrySlope,
                txA2ExcALogbookMessage
                    LogbookEntryMessagesExcFM,
                txA2ExcALogbookDateTime
                    DateAndTime
             }

        txA2ExcALogbookEntryIdx OBJECT-TYPE
            SYNTAX LogbookMaxEntryNumber
            MAX-ACCESS not-accessible
            STATUS current
            DESCRIPTION
                "This is an increasing number from 1 to 128. It is used as an index column for SNMP."
            ::= { txA2ExciterALogbookEntry 1 }

        
        txA2ExcALogbookEntryNbr OBJECT-TYPE
            SYNTAX LogbookMaxEntryNumber
            MAX-ACCESS read-only
            STATUS current
            DESCRIPTION
                "This is the number of the logbook entry. It is an decreasing number from max 128 down to 1."
            ::= { txA2ExciterALogbookEntry 2 }

        
        txA2ExcALogbookType OBJECT-TYPE
            SYNTAX EventClass
            MAX-ACCESS read-only
            STATUS current
            DESCRIPTION
                "Can either be Fault, Warning or State."
            ::= { txA2ExciterALogbookEntry 3 }

        
        txA2ExcALogbookSlope OBJECT-TYPE
            SYNTAX LogbookEntrySlope
            MAX-ACCESS read-only
            STATUS current
            DESCRIPTION
                "Either set (event raises) or reset (event disappears)"
            ::= { txA2ExciterALogbookEntry 4 }

        
        txA2ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA2ExciterALogbookEntry 5 }

        
        txA2ExcALogbookDateTime OBJECT-TYPE
            SYNTAX DateAndTime
            MAX-ACCESS read-only
            STATUS current
            DESCRIPTION
                "The time of the logbook entry."
            ::= { txA2ExciterALogbookEntry 6 }

        
        txA2OutputstageANumberOfEntries OBJECT-TYPE
            SYNTAX LogbookMaxEntryNumber
            MAX-ACCESS read-only
            STATUS current
            DESCRIPTION
                "The number of entries in logbook."
            ::= { logbookTxA2 7 }

        
        txA2OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 8 }

        
        txA2OutputstageALogbookTable OBJECT-TYPE
            SYNTAX SEQUENCE OF TxA2OutputstageALogbookEntry
            MAX-ACCESS not-accessible
            STATUS current
            DESCRIPTION
                "OutputstageA logbook table."
            ::= { logbookTxA2 9 }

        
        txA2OutputstageALogbookEntry OBJECT-TYPE
            SYNTAX TxA2OutputstageALogbookEntry
            MAX-ACCESS not-accessible
            STATUS current
            DESCRIPTION
                "This is a entry in the logbook."
            INDEX { txA2OstALogbookEntryIdx }
            ::= { txA2OutputstageALogbookTable 1 }

        
        TxA2OutputstageALogbookEntry ::=
            SEQUENCE { 
                txA2OstALogbookEntryIdx
                    LogbookMaxEntryNumber,
                txA2OstALogbookEntryNbr
                    LogbookMaxEntryNumber,
                txA2OstALogbookType
                    EventClass,
                txA2OstALogbookSlope
                    LogbookEntrySlope,
                txA2OstALogbookMessage
                    LogbookEntryMessagesOST,
                txA2OstALogbookDateTime
                    DateAndTime
             }

        txA2OstALogbookEntryIdx OBJECT-TYPE
            SYNTAX LogbookMaxEntryNumber
            MAX-ACCESS not-accessible
            STATUS current
            DESCRIPTION
                "This is an increasing number from 1 to 128. It is used as an index column for SNMP."
            ::= { txA2OutputstageALogbookEntry 1 }

        
        txA2OstALogbookEntryNbr OBJECT-TYPE
            SYNTAX LogbookMaxEntryNumber
            MAX-ACCESS read-only
            STATUS current
            DESCRIPTION
                "This is the number of the logbook entry. It is an decreasing number from max 128 down to 1."
            ::= { txA2OutputstageALogbookEntry 2 }

        
        txA2OstALogbookType OBJECT-TYPE
            SYNTAX EventClass
            MAX-ACCESS read-only
            STATUS current
            DESCRIPTION
                "Can either be Fault, Warning or State."
            ::= { txA2OutputstageALogbookEntry 3 }

        
        txA2OstALogbookSlope OBJECT-TYPE
            SYNTAX LogbookEntrySlope
            MAX-ACCESS read-only
            STATUS current
            DESCRIPTION
                "Either set (event raises) or reset (event disappears)"
            ::= { txA2OutputstageALogbookEntry 4 }

        
        txA2OstALogbookMessage OBJECT-TYPE
            SYNTAX LogbookEntryMessagesOST
            MAX-ACCESS read-only
            STATUS current
            DESCRIPTION
                "See RS-XX8000-COMMON-MIB - TextualConvention for details."
            ::= { txA2OutputstageALogbookEntry 5 }

        
        txA2OstALogbookDateTime OBJECT-TYPE
            SYNTAX DateAndTime
            MAX-ACCESS read-only
            STATUS current
            DESCRIPTION
                "The time of the logbook entry."
            ::= { txA2OutputstageALogbookEntry 6 }

        
        txA2ExciterBNumberOfEntries OBJECT-TYPE
            SYNTAX LogbookMaxEntryNumber
            MAX-ACCESS read-only
            STATUS current
            DESCRIPTION
                "The number of entries in logbook."
            ::= { logbookTxA2 13 }

        
        txA2ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA2 14 }

        
        txA2ExciterBLogbookTable OBJECT-TYPE
            SYNTAX SEQUENCE OF TxA2ExciterBLogbookEntry
            MAX-ACCESS not-accessible
            STATUS current
            DESCRIPTION
                "ExciterA logbook table."
            ::= { logbookTxA2 15 }

        
        txA2ExciterBLogbookEntry OBJECT-TYPE
            SYNTAX TxA2ExciterBLogbookEntry
            MAX-ACCESS not-accessible
            STATUS current
            DESCRIPTION
                "This is a entry in the logbook."
            INDEX { txA2ExcBLogbookEntryIdx }
            ::= { txA2ExciterBLogbookTable 1 }

        
        TxA2ExciterBLogbookEntry ::=
            SEQUENCE { 
                txA2ExcBLogbookEntryIdx
                    LogbookMaxEntryNumber,
                txA2ExcBLogbookEntryNbr
                    LogbookMaxEntryNumber,
                txA2ExcBLogbookType
                    EventClass,
                txA2ExcBLogbookSlope
                    LogbookEntrySlope,
                txA2ExcBLogbookMessage
                    LogbookEntryMessagesExcFM,
                txA2ExcBLogbookDateTime
                    DateAndTime
             }

        txA2ExcBLogbookEntryIdx OBJECT-TYPE
            SYNTAX LogbookMaxEntryNumber
            MAX-ACCESS not-accessible
            STATUS current
            DESCRIPTION
                "This is an increasing number from 1 to 128. It is used as an index column for SNMP."
            ::= { txA2ExciterBLogbookEntry 1 }

        
        txA2ExcBLogbookEntryNbr OBJECT-TYPE
            SYNTAX LogbookMaxEntryNumber
            MAX-ACCESS read-only
            STATUS current
            DESCRIPTION
                "This is the number of the logbook entry. It is an decreasing number from max 128 down to 1."
            ::= { txA2ExciterBLogbookEntry 2 }

        
        txA2ExcBLogbookType OBJECT-TYPE
            SYNTAX EventClass
            MAX-ACCESS read-only
            STATUS current
            DESCRIPTION
                "Can either be Fault, Warning or State."
            ::= { txA2ExciterBLogbookEntry 3 }

        
        txA2ExcBLogbookSlope OBJECT-TYPE
            SYNTAX LogbookEntrySlope
            MAX-ACCESS read-only
            STATUS current
            DESCRIPTION
                "Either set (event raises) or reset (event disappears)"
            ::= { txA2ExciterBLogbookEntry 4 }

        
        txA2ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA2ExciterBLogbookEntry 5 }

        
        txA2ExcBLogbookDateTime OBJECT-TYPE
            SYNTAX DateAndTime
            MAX-ACCESS read-only
            STATUS current
            DESCRIPTION
                "The time of the logbook entry."
            ::= { txA2ExciterBLogbookEntry 6 }

        
        outputstageATxA2 OBJECT IDENTIFIER ::= { txA2 2 }

        
        txA2OstARackTable OBJECT-TYPE
            SYNTAX SEQUENCE OF TxA2OstARackEntry
            MAX-ACCESS not-accessible
            STATUS current
            DESCRIPTION
                "The table of racks."
            ::= { outputstageATxA2 1 }

        
        txA2OstARackEntry OBJECT-TYPE
            SYNTAX TxA2OstARackEntry
            MAX-ACCESS not-accessible
            STATUS current
            DESCRIPTION
                "A row (an entry) for one rack."
            INDEX { txA2OstARackIdx }
            ::= { txA2OstARackTable 1 }

        
        TxA2OstARackEntry ::=
            SEQUENCE { 
                txA2OstARackIdx
                    IndexRack,
                txA2OstARackInletTemperature
                    FloatingPoint,
                txA2OstARackOutletTemperature
                    FloatingPoint,
                txA2OstARackAuxPowerSupply
                    FloatingPoint
             }

        txA2OstARackIdx OBJECT-TYPE
            SYNTAX IndexRack
            MAX-ACCESS not-accessible
            STATUS current
            DESCRIPTION
                "The rack number (1..10)."
            ::= { txA2OstARackEntry 1 }

        
        txA2OstARackInletTemperature OBJECT-TYPE
            SYNTAX FloatingPoint
            UNITS "Degree Celsius"
            MAX-ACCESS read-only
            STATUS current
            DESCRIPTION
                "The inlet temperature."
            ::= { txA2OstARackEntry 2 }

        
        txA2OstARackOutletTemperature OBJECT-TYPE
            SYNTAX FloatingPoint
            UNITS "Degree Celsius"
            MAX-ACCESS read-only
            STATUS current
            DESCRIPTION
                "The outlet temperature."
            ::= { txA2OstARackEntry 3 }

        
        txA2OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA2OstARackEntry 4 }

        
        txA3 OBJECT IDENTIFIER ::= { transmitter 43 }

        
        logbookTxA3 OBJECT IDENTIFIER ::= { txA3 1 }

        
        txA3NetCCUNumberOfEntries OBJECT-TYPE
            SYNTAX LogbookMaxEntryNumber
            MAX-ACCESS read-only
            STATUS current
            DESCRIPTION
                "The number of entries in logbook."
            ::= { logbookTxA3 1 }

        
        txA3NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 2 }

        
        txA3NetCCULogbookTable OBJECT-TYPE
            SYNTAX SEQUENCE OF TxA3NetCCULogbookEntry
            MAX-ACCESS not-accessible
            STATUS current
            DESCRIPTION
                "NetCCU logbook table."
            ::= { logbookTxA3 3 }

        
        txA3NetCCULogbookEntry OBJECT-TYPE
            SYNTAX TxA3NetCCULogbookEntry
            MAX-ACCESS not-accessible
            STATUS current
            DESCRIPTION
                "This is a entry in the logbook."
            INDEX { txA3NetCCULogbookEntryIdx }
            ::= { txA3NetCCULogbookTable 1 }

        
        TxA3NetCCULogbookEntry ::=
            SEQUENCE { 
                txA3NetCCULogbookEntryIdx
                    LogbookMaxEntryNumber,
                txA3NetCCULogbookEntryNbr
                    LogbookMaxEntryNumber,
                txA3NetCCULogbookType
                    EventClass,
                txA3NetCCULogbookSlope
                    LogbookEntrySlope,
                txA3NetCCULogbookMessage
                    LogbookEntryMessagesNetCCU,
                txA3NetCCULogbookDateTime
                    DateAndTime
             }

        txA3NetCCULogbookEntryIdx OBJECT-TYPE
            SYNTAX LogbookMaxEntryNumber
            MAX-ACCESS not-accessible
            STATUS current
            DESCRIPTION
                "This is an increasing number from 1 to 128. It is used as an index column for SNMP."
            ::= { txA3NetCCULogbookEntry 1 }

        
        txA3NetCCULogbookEntryNbr OBJECT-TYPE
            SYNTAX LogbookMaxEntryNumber
            MAX-ACCESS read-only
            STATUS current
            DESCRIPTION
                "This is the number of the logbook entry. It is an decreasing number from max 128 down to 1."
            ::= { txA3NetCCULogbookEntry 2 }

        
        txA3NetCCULogbookType OBJECT-TYPE
            SYNTAX EventClass
            MAX-ACCESS read-only
            STATUS current
            DESCRIPTION
                "Can either be Fault, Warning or State."
            ::= { txA3NetCCULogbookEntry 3 }

        
        txA3NetCCULogbookSlope OBJECT-TYPE
            SYNTAX LogbookEntrySlope
            MAX-ACCESS read-only
            STATUS current
            DESCRIPTION
                "Either set (event raises) or reset (event disappears)"
            ::= { txA3NetCCULogbookEntry 4 }

        
        txA3NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA3NetCCULogbookEntry 5 }

        
        txA3NetCCULogbookDateTime OBJECT-TYPE
            SYNTAX DateAndTime
            MAX-ACCESS read-only
            STATUS current
            DESCRIPTION
                "The time of the logbook entry."
            ::= { txA3NetCCULogbookEntry 6 }

        
        txA3ExciterANumberOfEntries OBJECT-TYPE
            SYNTAX LogbookMaxEntryNumber
            MAX-ACCESS read-only
            STATUS current
            DESCRIPTION
                "The number of entries in logbook."
            ::= { logbookTxA3 4 }

        
        txA3ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 5 }

        
        txA3ExciterALogbookTable OBJECT-TYPE
            SYNTAX SEQUENCE OF TxA3ExciterALogbookEntry
            MAX-ACCESS not-accessible
            STATUS current
            DESCRIPTION
                "ExciterA logbook table."
            ::= { logbookTxA3 6 }

        
        txA3ExciterALogbookEntry OBJECT-TYPE
            SYNTAX TxA3ExciterALogbookEntry
            MAX-ACCESS not-accessible
            STATUS current
            DESCRIPTION
                "This is a entry in the logbook."
            INDEX { txA3ExcALogbookEntryIdx }
            ::= { txA3ExciterALogbookTable 1 }

        
        TxA3ExciterALogbookEntry ::=
            SEQUENCE { 
                txA3ExcALogbookEntryIdx
                    LogbookMaxEntryNumber,
                txA3ExcALogbookEntryNbr
                    LogbookMaxEntryNumber,
                txA3ExcALogbookType
                    EventClass,
                txA3ExcALogbookSlope
                    LogbookEntrySlope,
                txA3ExcALogbookMessage
                    LogbookEntryMessagesExcFM,
                txA3ExcALogbookDateTime
                    DateAndTime
             }

        txA3ExcALogbookEntryIdx OBJECT-TYPE
            SYNTAX LogbookMaxEntryNumber
            MAX-ACCESS not-accessible
            STATUS current
            DESCRIPTION
                "This is an increasing number from 1 to 128. It is used as an index column for SNMP."
            ::= { txA3ExciterALogbookEntry 1 }

        
        txA3ExcALogbookEntryNbr OBJECT-TYPE
            SYNTAX LogbookMaxEntryNumber
            MAX-ACCESS read-only
            STATUS current
            DESCRIPTION
                "This is the number of the logbook entry. It is an decreasing number from max 128 down to 1."
            ::= { txA3ExciterALogbookEntry 2 }

        
        txA3ExcALogbookType OBJECT-TYPE
            SYNTAX EventClass
            MAX-ACCESS read-only
            STATUS current
            DESCRIPTION
                "Can either be Fault, Warning or State."
            ::= { txA3ExciterALogbookEntry 3 }

        
        txA3ExcALogbookSlope OBJECT-TYPE
            SYNTAX LogbookEntrySlope
            MAX-ACCESS read-only
            STATUS current
            DESCRIPTION
                "Either set (event raises) or reset (event disappears)"
            ::= { txA3ExciterALogbookEntry 4 }

        
        txA3ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA3ExciterALogbookEntry 5 }

        
        txA3ExcALogbookDateTime OBJECT-TYPE
            SYNTAX DateAndTime
            MAX-ACCESS read-only
            STATUS current
            DESCRIPTION
                "The time of the logbook entry."
            ::= { txA3ExciterALogbookEntry 6 }

        
        txA3OutputstageANumberOfEntries OBJECT-TYPE
            SYNTAX LogbookMaxEntryNumber
            MAX-ACCESS read-only
            STATUS current
            DESCRIPTION
                "The number of entries in logbook."
            ::= { logbookTxA3 7 }

        
        txA3OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 8 }

        
        txA3OutputstageALogbookTable OBJECT-TYPE
            SYNTAX SEQUENCE OF TxA3OutputstageALogbookEntry
            MAX-ACCESS not-accessible
            STATUS current
            DESCRIPTION
                "OutputstageA logbook table."
            ::= { logbookTxA3 9 }

        
        txA3OutputstageALogbookEntry OBJECT-TYPE
            SYNTAX TxA3OutputstageALogbookEntry
            MAX-ACCESS not-accessible
            STATUS current
            DESCRIPTION
                "This is a entry in the logbook."
            INDEX { txA3OstALogbookEntryIdx }
            ::= { txA3OutputstageALogbookTable 1 }

        
        TxA3OutputstageALogbookEntry ::=
            SEQUENCE { 
                txA3OstALogbookEntryIdx
                    LogbookMaxEntryNumber,
                txA3OstALogbookEntryNbr
                    LogbookMaxEntryNumber,
                txA3OstALogbookType
                    EventClass,
                txA3OstALogbookSlope
                    LogbookEntrySlope,
                txA3OstALogbookMessage
                    LogbookEntryMessagesOST,
                txA3OstALogbookDateTime
                    DateAndTime
             }

        txA3OstALogbookEntryIdx OBJECT-TYPE
            SYNTAX LogbookMaxEntryNumber
            MAX-ACCESS not-accessible
            STATUS current
            DESCRIPTION
                "This is an increasing number from 1 to 128. It is used as an index column for SNMP."
            ::= { txA3OutputstageALogbookEntry 1 }

        
        txA3OstALogbookEntryNbr OBJECT-TYPE
            SYNTAX LogbookMaxEntryNumber
            MAX-ACCESS read-only
            STATUS current
            DESCRIPTION
                "This is the number of the logbook entry. It is an decreasing number from max 128 down to 1."
            ::= { txA3OutputstageALogbookEntry 2 }

        
        txA3OstALogbookType OBJECT-TYPE
            SYNTAX EventClass
            MAX-ACCESS read-only
            STATUS current
            DESCRIPTION
                "Can either be Fault, Warning or State."
            ::= { txA3OutputstageALogbookEntry 3 }

        
        txA3OstALogbookSlope OBJECT-TYPE
            SYNTAX LogbookEntrySlope
            MAX-ACCESS read-only
            STATUS current
            DESCRIPTION
                "Either set (event raises) or reset (event disappears)"
            ::= { txA3OutputstageALogbookEntry 4 }

        
        txA3OstALogbookMessage OBJECT-TYPE
            SYNTAX LogbookEntryMessagesOST
            MAX-ACCESS read-only
            STATUS current
            DESCRIPTION
                "See RS-XX8000-COMMON-MIB - TextualConvention for details."
            ::= { txA3OutputstageALogbookEntry 5 }

        
        txA3OstALogbookDateTime OBJECT-TYPE
            SYNTAX DateAndTime
            MAX-ACCESS read-only
            STATUS current
            DESCRIPTION
                "The time of the logbook entry."
            ::= { txA3OutputstageALogbookEntry 6 }

        
        txA3ExciterBNumberOfEntries OBJECT-TYPE
            SYNTAX LogbookMaxEntryNumber
            MAX-ACCESS read-only
            STATUS current
            DESCRIPTION
                "The number of entries in logbook."
            ::= { logbookTxA3 13 }

        
        txA3ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA3 14 }

        
        txA3ExciterBLogbookTable OBJECT-TYPE
            SYNTAX SEQUENCE OF TxA3ExciterBLogbookEntry
            MAX-ACCESS not-accessible
            STATUS current
            DESCRIPTION
                "ExciterA logbook table."
            ::= { logbookTxA3 15 }

        
        txA3ExciterBLogbookEntry OBJECT-TYPE
            SYNTAX TxA3ExciterBLogbookEntry
            MAX-ACCESS not-accessible
            STATUS current
            DESCRIPTION
                "This is a entry in the logbook."
            INDEX { txA3ExcBLogbookEntryIdx }
            ::= { txA3ExciterBLogbookTable 1 }

        
        TxA3ExciterBLogbookEntry ::=
            SEQUENCE { 
                txA3ExcBLogbookEntryIdx
                    LogbookMaxEntryNumber,
                txA3ExcBLogbookEntryNbr
                    LogbookMaxEntryNumber,
                txA3ExcBLogbookType
                    EventClass,
                txA3ExcBLogbookSlope
                    LogbookEntrySlope,
                txA3ExcBLogbookMessage
                    LogbookEntryMessagesExcFM,
                txA3ExcBLogbookDateTime
                    DateAndTime
             }

        txA3ExcBLogbookEntryIdx OBJECT-TYPE
            SYNTAX LogbookMaxEntryNumber
            MAX-ACCESS not-accessible
            STATUS current
            DESCRIPTION
                "This is an increasing number from 1 to 128. It is used as an index column for SNMP."
            ::= { txA3ExciterBLogbookEntry 1 }

        
        txA3ExcBLogbookEntryNbr OBJECT-TYPE
            SYNTAX LogbookMaxEntryNumber
            MAX-ACCESS read-only
            STATUS current
            DESCRIPTION
                "This is the number of the logbook entry. It is an decreasing number from max 128 down to 1."
            ::= { txA3ExciterBLogbookEntry 2 }

        
        txA3ExcBLogbookType OBJECT-TYPE
            SYNTAX EventClass
            MAX-ACCESS read-only
            STATUS current
            DESCRIPTION
                "Can either be Fault, Warning or State."
            ::= { txA3ExciterBLogbookEntry 3 }

        
        txA3ExcBLogbookSlope OBJECT-TYPE
            SYNTAX LogbookEntrySlope
            MAX-ACCESS read-only
            STATUS current
            DESCRIPTION
                "Either set (event raises) or reset (event disappears)"
            ::= { txA3ExciterBLogbookEntry 4 }

        
        txA3ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA3ExciterBLogbookEntry 5 }

        
        txA3ExcBLogbookDateTime OBJECT-TYPE
            SYNTAX DateAndTime
            MAX-ACCESS read-only
            STATUS current
            DESCRIPTION
                "The time of the logbook entry."
            ::= { txA3ExciterBLogbookEntry 6 }

        
        outputstageATxA3 OBJECT IDENTIFIER ::= { txA3 2 }

        
        txA3OstARackTable OBJECT-TYPE
            SYNTAX SEQUENCE OF TxA3OstARackEntry
            MAX-ACCESS not-accessible
            STATUS current
            DESCRIPTION
                "The table of racks."
            ::= { outputstageATxA3 1 }

        
        txA3OstARackEntry OBJECT-TYPE
            SYNTAX TxA3OstARackEntry
            MAX-ACCESS not-accessible
            STATUS current
            DESCRIPTION
                "A row (an entry) for one rack."
            INDEX { txA3OstARackIdx }
            ::= { txA3OstARackTable 1 }

        
        TxA3OstARackEntry ::=
            SEQUENCE { 
                txA3OstARackIdx
                    IndexRack,
                txA3OstARackInletTemperature
                    FloatingPoint,
                txA3OstARackOutletTemperature
                    FloatingPoint,
                txA3OstARackAuxPowerSupply
                    FloatingPoint
             }

        txA3OstARackIdx OBJECT-TYPE
            SYNTAX IndexRack
            MAX-ACCESS not-accessible
            STATUS current
            DESCRIPTION
                "The rack number (1..10)."
            ::= { txA3OstARackEntry 1 }

        
        txA3OstARackInletTemperature OBJECT-TYPE
            SYNTAX FloatingPoint
            UNITS "Degree Celsius"
            MAX-ACCESS read-only
            STATUS current
            DESCRIPTION
                "The inlet temperature."
            ::= { txA3OstARackEntry 2 }

        
        txA3OstARackOutletTemperature OBJECT-TYPE
            SYNTAX FloatingPoint
            UNITS "Degree Celsius"
            MAX-ACCESS read-only
            STATUS current
            DESCRIPTION
                "The outlet temperature."
            ::= { txA3OstARackEntry 3 }

        
        txA3OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA3OstARackEntry 4 }

        
        txA4 OBJECT IDENTIFIER ::= { transmitter 44 }

        
        logbookTxA4 OBJECT IDENTIFIER ::= { txA4 1 }

        
        txA4NetCCUNumberOfEntries OBJECT-TYPE
            SYNTAX LogbookMaxEntryNumber
            MAX-ACCESS read-only
            STATUS current
            DESCRIPTION
                "The number of entries in logbook."
            ::= { logbookTxA4 1 }

        
        txA4NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 2 }

        
        txA4NetCCULogbookTable OBJECT-TYPE
            SYNTAX SEQUENCE OF TxA4NetCCULogbookEntry
            MAX-ACCESS not-accessible
            STATUS current
            DESCRIPTION
                "NetCCU logbook table."
            ::= { logbookTxA4 3 }

        
        txA4NetCCULogbookEntry OBJECT-TYPE
            SYNTAX TxA4NetCCULogbookEntry
            MAX-ACCESS not-accessible
            STATUS current
            DESCRIPTION
                "This is a entry in the logbook."
            INDEX { txA4NetCCULogbookEntryIdx }
            ::= { txA4NetCCULogbookTable 1 }

        
        TxA4NetCCULogbookEntry ::=
            SEQUENCE { 
                txA4NetCCULogbookEntryIdx
                    LogbookMaxEntryNumber,
                txA4NetCCULogbookEntryNbr
                    LogbookMaxEntryNumber,
                txA4NetCCULogbookType
                    EventClass,
                txA4NetCCULogbookSlope
                    LogbookEntrySlope,
                txA4NetCCULogbookMessage
                    LogbookEntryMessagesNetCCU,
                txA4NetCCULogbookDateTime
                    DateAndTime
             }

        txA4NetCCULogbookEntryIdx OBJECT-TYPE
            SYNTAX LogbookMaxEntryNumber
            MAX-ACCESS not-accessible
            STATUS current
            DESCRIPTION
                "This is an increasing number from 1 to 128. It is used as an index column for SNMP."
            ::= { txA4NetCCULogbookEntry 1 }

        
        txA4NetCCULogbookEntryNbr OBJECT-TYPE
            SYNTAX LogbookMaxEntryNumber
            MAX-ACCESS read-only
            STATUS current
            DESCRIPTION
                "This is the number of the logbook entry. It is an decreasing number from max 128 down to 1."
            ::= { txA4NetCCULogbookEntry 2 }

        
        txA4NetCCULogbookType OBJECT-TYPE
            SYNTAX EventClass
            MAX-ACCESS read-only
            STATUS current
            DESCRIPTION
                "Can either be Fault, Warning or State."
            ::= { txA4NetCCULogbookEntry 3 }

        
        txA4NetCCULogbookSlope OBJECT-TYPE
            SYNTAX LogbookEntrySlope
            MAX-ACCESS read-only
            STATUS current
            DESCRIPTION
                "Either set (event raises) or reset (event disappears)"
            ::= { txA4NetCCULogbookEntry 4 }

        
        txA4NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA4NetCCULogbookEntry 5 }

        
        txA4NetCCULogbookDateTime OBJECT-TYPE
            SYNTAX DateAndTime
            MAX-ACCESS read-only
            STATUS current
            DESCRIPTION
                "The time of the logbook entry."
            ::= { txA4NetCCULogbookEntry 6 }

        
        txA4ExciterANumberOfEntries OBJECT-TYPE
            SYNTAX LogbookMaxEntryNumber
            MAX-ACCESS read-only
            STATUS current
            DESCRIPTION
                "The number of entries in logbook."
            ::= { logbookTxA4 4 }

        
        txA4ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 5 }

        
        txA4ExciterALogbookTable OBJECT-TYPE
            SYNTAX SEQUENCE OF TxA4ExciterALogbookEntry
            MAX-ACCESS not-accessible
            STATUS current
            DESCRIPTION
                "ExciterA logbook table."
            ::= { logbookTxA4 6 }

        
        txA4ExciterALogbookEntry OBJECT-TYPE
            SYNTAX TxA4ExciterALogbookEntry
            MAX-ACCESS not-accessible
            STATUS current
            DESCRIPTION
                "This is a entry in the logbook."
            INDEX { txA4ExcALogbookEntryIdx }
            ::= { txA4ExciterALogbookTable 1 }

        
        TxA4ExciterALogbookEntry ::=
            SEQUENCE { 
                txA4ExcALogbookEntryIdx
                    LogbookMaxEntryNumber,
                txA4ExcALogbookEntryNbr
                    LogbookMaxEntryNumber,
                txA4ExcALogbookType
                    EventClass,
                txA4ExcALogbookSlope
                    LogbookEntrySlope,
                txA4ExcALogbookMessage
                    LogbookEntryMessagesExcFM,
                txA4ExcALogbookDateTime
                    DateAndTime
             }

        txA4ExcALogbookEntryIdx OBJECT-TYPE
            SYNTAX LogbookMaxEntryNumber
            MAX-ACCESS not-accessible
            STATUS current
            DESCRIPTION
                "This is an increasing number from 1 to 128. It is used as an index column for SNMP."
            ::= { txA4ExciterALogbookEntry 1 }

        
        txA4ExcALogbookEntryNbr OBJECT-TYPE
            SYNTAX LogbookMaxEntryNumber
            MAX-ACCESS read-only
            STATUS current
            DESCRIPTION
                "This is the number of the logbook entry. It is an decreasing number from max 128 down to 1."
            ::= { txA4ExciterALogbookEntry 2 }

        
        txA4ExcALogbookType OBJECT-TYPE
            SYNTAX EventClass
            MAX-ACCESS read-only
            STATUS current
            DESCRIPTION
                "Can either be Fault, Warning or State."
            ::= { txA4ExciterALogbookEntry 3 }

        
        txA4ExcALogbookSlope OBJECT-TYPE
            SYNTAX LogbookEntrySlope
            MAX-ACCESS read-only
            STATUS current
            DESCRIPTION
                "Either set (event raises) or reset (event disappears)"
            ::= { txA4ExciterALogbookEntry 4 }

        
        txA4ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA4ExciterALogbookEntry 5 }

        
        txA4ExcALogbookDateTime OBJECT-TYPE
            SYNTAX DateAndTime
            MAX-ACCESS read-only
            STATUS current
            DESCRIPTION
                "The time of the logbook entry."
            ::= { txA4ExciterALogbookEntry 6 }

        
        txA4OutputstageANumberOfEntries OBJECT-TYPE
            SYNTAX LogbookMaxEntryNumber
            MAX-ACCESS read-only
            STATUS current
            DESCRIPTION
                "The number of entries in logbook."
            ::= { logbookTxA4 7 }

        
        txA4OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 8 }

        
        txA4OutputstageALogbookTable OBJECT-TYPE
            SYNTAX SEQUENCE OF TxA4OutputstageALogbookEntry
            MAX-ACCESS not-accessible
            STATUS current
            DESCRIPTION
                "OutputstageA logbook table."
            ::= { logbookTxA4 9 }

        
        txA4OutputstageALogbookEntry OBJECT-TYPE
            SYNTAX TxA4OutputstageALogbookEntry
            MAX-ACCESS not-accessible
            STATUS current
            DESCRIPTION
                "This is a entry in the logbook."
            INDEX { txA4OstALogbookEntryIdx }
            ::= { txA4OutputstageALogbookTable 1 }

        
        TxA4OutputstageALogbookEntry ::=
            SEQUENCE { 
                txA4OstALogbookEntryIdx
                    LogbookMaxEntryNumber,
                txA4OstALogbookEntryNbr
                    LogbookMaxEntryNumber,
                txA4OstALogbookType
                    EventClass,
                txA4OstALogbookSlope
                    LogbookEntrySlope,
                txA4OstALogbookMessage
                    LogbookEntryMessagesOST,
                txA4OstALogbookDateTime
                    DateAndTime
             }

        txA4OstALogbookEntryIdx OBJECT-TYPE
            SYNTAX LogbookMaxEntryNumber
            MAX-ACCESS not-accessible
            STATUS current
            DESCRIPTION
                "This is an increasing number from 1 to 128. It is used as an index column for SNMP."
            ::= { txA4OutputstageALogbookEntry 1 }

        
        txA4OstALogbookEntryNbr OBJECT-TYPE
            SYNTAX LogbookMaxEntryNumber
            MAX-ACCESS read-only
            STATUS current
            DESCRIPTION
                "This is the number of the logbook entry. It is an decreasing number from max 128 down to 1."
            ::= { txA4OutputstageALogbookEntry 2 }

        
        txA4OstALogbookType OBJECT-TYPE
            SYNTAX EventClass
            MAX-ACCESS read-only
            STATUS current
            DESCRIPTION
                "Can either be Fault, Warning or State."
            ::= { txA4OutputstageALogbookEntry 3 }

        
        txA4OstALogbookSlope OBJECT-TYPE
            SYNTAX LogbookEntrySlope
            MAX-ACCESS read-only
            STATUS current
            DESCRIPTION
                "Either set (event raises) or reset (event disappears)"
            ::= { txA4OutputstageALogbookEntry 4 }

        
        txA4OstALogbookMessage OBJECT-TYPE
            SYNTAX LogbookEntryMessagesOST
            MAX-ACCESS read-only
            STATUS current
            DESCRIPTION
                "See RS-XX8000-COMMON-MIB - TextualConvention for details."
            ::= { txA4OutputstageALogbookEntry 5 }

        
        txA4OstALogbookDateTime OBJECT-TYPE
            SYNTAX DateAndTime
            MAX-ACCESS read-only
            STATUS current
            DESCRIPTION
                "The time of the logbook entry."
            ::= { txA4OutputstageALogbookEntry 6 }

        
        txA4ExciterBNumberOfEntries OBJECT-TYPE
            SYNTAX LogbookMaxEntryNumber
            MAX-ACCESS read-only
            STATUS current
            DESCRIPTION
                "The number of entries in logbook."
            ::= { logbookTxA4 13 }

        
        txA4ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA4 14 }

        
        txA4ExciterBLogbookTable OBJECT-TYPE
            SYNTAX SEQUENCE OF TxA4ExciterBLogbookEntry
            MAX-ACCESS not-accessible
            STATUS current
            DESCRIPTION
                "ExciterA logbook table."
            ::= { logbookTxA4 15 }

        
        txA4ExciterBLogbookEntry OBJECT-TYPE
            SYNTAX TxA4ExciterBLogbookEntry
            MAX-ACCESS not-accessible
            STATUS current
            DESCRIPTION
                "This is a entry in the logbook."
            INDEX { txA4ExcBLogbookEntryIdx }
            ::= { txA4ExciterBLogbookTable 1 }

        
        TxA4ExciterBLogbookEntry ::=
            SEQUENCE { 
                txA4ExcBLogbookEntryIdx
                    LogbookMaxEntryNumber,
                txA4ExcBLogbookEntryNbr
                    LogbookMaxEntryNumber,
                txA4ExcBLogbookType
                    EventClass,
                txA4ExcBLogbookSlope
                    LogbookEntrySlope,
                txA4ExcBLogbookMessage
                    LogbookEntryMessagesExcFM,
                txA4ExcBLogbookDateTime
                    DateAndTime
             }

        txA4ExcBLogbookEntryIdx OBJECT-TYPE
            SYNTAX LogbookMaxEntryNumber
            MAX-ACCESS not-accessible
            STATUS current
            DESCRIPTION
                "This is an increasing number from 1 to 128. It is used as an index column for SNMP."
            ::= { txA4ExciterBLogbookEntry 1 }

        
        txA4ExcBLogbookEntryNbr OBJECT-TYPE
            SYNTAX LogbookMaxEntryNumber
            MAX-ACCESS read-only
            STATUS current
            DESCRIPTION
                "This is the number of the logbook entry. It is an decreasing number from max 128 down to 1."
            ::= { txA4ExciterBLogbookEntry 2 }

        
        txA4ExcBLogbookType OBJECT-TYPE
            SYNTAX EventClass
            MAX-ACCESS read-only
            STATUS current
            DESCRIPTION
                "Can either be Fault, Warning or State."
            ::= { txA4ExciterBLogbookEntry 3 }

        
        txA4ExcBLogbookSlope OBJECT-TYPE
            SYNTAX LogbookEntrySlope
            MAX-ACCESS read-only
            STATUS current
            DESCRIPTION
                "Either set (event raises) or reset (event disappears)"
            ::= { txA4ExciterBLogbookEntry 4 }

        
        txA4ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA4ExciterBLogbookEntry 5 }

        
        txA4ExcBLogbookDateTime OBJECT-TYPE
            SYNTAX DateAndTime
            MAX-ACCESS read-only
            STATUS current
            DESCRIPTION
                "The time of the logbook entry."
            ::= { txA4ExciterBLogbookEntry 6 }

        
        outputstageATxA4 OBJECT IDENTIFIER ::= { txA4 2 }

        
        txA4OstARackTable OBJECT-TYPE
            SYNTAX SEQUENCE OF TxA4OstARackEntry
            MAX-ACCESS not-accessible
            STATUS current
            DESCRIPTION
                "The table of racks."
            ::= { outputstageATxA4 1 }

        
        txA4OstARackEntry OBJECT-TYPE
            SYNTAX TxA4OstARackEntry
            MAX-ACCESS not-accessible
            STATUS current
            DESCRIPTION
                "A row (an entry) for one rack."
            INDEX { txA4OstARackIdx }
            ::= { txA4OstARackTable 1 }

        
        TxA4OstARackEntry ::=
            SEQUENCE { 
                txA4OstARackIdx
                    IndexRack,
                txA4OstARackInletTemperature
                    FloatingPoint,
                txA4OstARackOutletTemperature
                    FloatingPoint,
                txA4OstARackAuxPowerSupply
                    FloatingPoint
             }

        txA4OstARackIdx OBJECT-TYPE
            SYNTAX IndexRack
            MAX-ACCESS not-accessible
            STATUS current
            DESCRIPTION
                "The rack number (1..10)."
            ::= { txA4OstARackEntry 1 }

        
        txA4OstARackInletTemperature OBJECT-TYPE
            SYNTAX FloatingPoint
            UNITS "Degree Celsius"
            MAX-ACCESS read-only
            STATUS current
            DESCRIPTION
                "The inlet temperature."
            ::= { txA4OstARackEntry 2 }

        
        txA4OstARackOutletTemperature OBJECT-TYPE
            SYNTAX FloatingPoint
            UNITS "Degree Celsius"
            MAX-ACCESS read-only
            STATUS current
            DESCRIPTION
                "The outlet temperature."
            ::= { txA4OstARackEntry 3 }

        
        txA4OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA4OstARackEntry 4 }

        
        txA5 OBJECT IDENTIFIER ::= { transmitter 45 }

        
        logbookTxA5 OBJECT IDENTIFIER ::= { txA5 1 }

        
        txA5NetCCUNumberOfEntries OBJECT-TYPE
            SYNTAX LogbookMaxEntryNumber
            MAX-ACCESS read-only
            STATUS current
            DESCRIPTION
                "The number of entries in logbook."
            ::= { logbookTxA5 1 }

        
        txA5NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 2 }

        
        txA5NetCCULogbookTable OBJECT-TYPE
            SYNTAX SEQUENCE OF TxA5NetCCULogbookEntry
            MAX-ACCESS not-accessible
            STATUS current
            DESCRIPTION
                "NetCCU logbook table."
            ::= { logbookTxA5 3 }

        
        txA5NetCCULogbookEntry OBJECT-TYPE
            SYNTAX TxA5NetCCULogbookEntry
            MAX-ACCESS not-accessible
            STATUS current
            DESCRIPTION
                "This is a entry in the logbook."
            INDEX { txA5NetCCULogbookEntryIdx }
            ::= { txA5NetCCULogbookTable 1 }

        
        TxA5NetCCULogbookEntry ::=
            SEQUENCE { 
                txA5NetCCULogbookEntryIdx
                    LogbookMaxEntryNumber,
                txA5NetCCULogbookEntryNbr
                    LogbookMaxEntryNumber,
                txA5NetCCULogbookType
                    EventClass,
                txA5NetCCULogbookSlope
                    LogbookEntrySlope,
                txA5NetCCULogbookMessage
                    LogbookEntryMessagesNetCCU,
                txA5NetCCULogbookDateTime
                    DateAndTime
             }

        txA5NetCCULogbookEntryIdx OBJECT-TYPE
            SYNTAX LogbookMaxEntryNumber
            MAX-ACCESS not-accessible
            STATUS current
            DESCRIPTION
                "This is an increasing number from 1 to 128. It is used as an index column for SNMP."
            ::= { txA5NetCCULogbookEntry 1 }

        
        txA5NetCCULogbookEntryNbr OBJECT-TYPE
            SYNTAX LogbookMaxEntryNumber
            MAX-ACCESS read-only
            STATUS current
            DESCRIPTION
                "This is the number of the logbook entry. It is an decreasing number from max 128 down to 1."
            ::= { txA5NetCCULogbookEntry 2 }

        
        txA5NetCCULogbookType OBJECT-TYPE
            SYNTAX EventClass
            MAX-ACCESS read-only
            STATUS current
            DESCRIPTION
                "Can either be Fault, Warning or State."
            ::= { txA5NetCCULogbookEntry 3 }

        
        txA5NetCCULogbookSlope OBJECT-TYPE
            SYNTAX LogbookEntrySlope
            MAX-ACCESS read-only
            STATUS current
            DESCRIPTION
                "Either set (event raises) or reset (event disappears)"
            ::= { txA5NetCCULogbookEntry 4 }

        
        txA5NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA5NetCCULogbookEntry 5 }

        
        txA5NetCCULogbookDateTime OBJECT-TYPE
            SYNTAX DateAndTime
            MAX-ACCESS read-only
            STATUS current
            DESCRIPTION
                "The time of the logbook entry."
            ::= { txA5NetCCULogbookEntry 6 }

        
        txA5ExciterANumberOfEntries OBJECT-TYPE
            SYNTAX LogbookMaxEntryNumber
            MAX-ACCESS read-only
            STATUS current
            DESCRIPTION
                "The number of entries in logbook."
            ::= { logbookTxA5 4 }

        
        txA5ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 5 }

        
        txA5ExciterALogbookTable OBJECT-TYPE
            SYNTAX SEQUENCE OF TxA5ExciterALogbookEntry
            MAX-ACCESS not-accessible
            STATUS current
            DESCRIPTION
                "ExciterA logbook table."
            ::= { logbookTxA5 6 }

        
        txA5ExciterALogbookEntry OBJECT-TYPE
            SYNTAX TxA5ExciterALogbookEntry
            MAX-ACCESS not-accessible
            STATUS current
            DESCRIPTION
                "This is a entry in the logbook."
            INDEX { txA5ExcALogbookEntryIdx }
            ::= { txA5ExciterALogbookTable 1 }

        
        TxA5ExciterALogbookEntry ::=
            SEQUENCE { 
                txA5ExcALogbookEntryIdx
                    LogbookMaxEntryNumber,
                txA5ExcALogbookEntryNbr
                    LogbookMaxEntryNumber,
                txA5ExcALogbookType
                    EventClass,
                txA5ExcALogbookSlope
                    LogbookEntrySlope,
                txA5ExcALogbookMessage
                    LogbookEntryMessagesExcFM,
                txA5ExcALogbookDateTime
                    DateAndTime
             }

        txA5ExcALogbookEntryIdx OBJECT-TYPE
            SYNTAX LogbookMaxEntryNumber
            MAX-ACCESS not-accessible
            STATUS current
            DESCRIPTION
                "This is an increasing number from 1 to 128. It is used as an index column for SNMP."
            ::= { txA5ExciterALogbookEntry 1 }

        
        txA5ExcALogbookEntryNbr OBJECT-TYPE
            SYNTAX LogbookMaxEntryNumber
            MAX-ACCESS read-only
            STATUS current
            DESCRIPTION
                "This is the number of the logbook entry. It is an decreasing number from max 128 down to 1."
            ::= { txA5ExciterALogbookEntry 2 }

        
        txA5ExcALogbookType OBJECT-TYPE
            SYNTAX EventClass
            MAX-ACCESS read-only
            STATUS current
            DESCRIPTION
                "Can either be Fault, Warning or State."
            ::= { txA5ExciterALogbookEntry 3 }

        
        txA5ExcALogbookSlope OBJECT-TYPE
            SYNTAX LogbookEntrySlope
            MAX-ACCESS read-only
            STATUS current
            DESCRIPTION
                "Either set (event raises) or reset (event disappears)"
            ::= { txA5ExciterALogbookEntry 4 }

        
        txA5ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA5ExciterALogbookEntry 5 }

        
        txA5ExcALogbookDateTime OBJECT-TYPE
            SYNTAX DateAndTime
            MAX-ACCESS read-only
            STATUS current
            DESCRIPTION
                "The time of the logbook entry."
            ::= { txA5ExciterALogbookEntry 6 }

        
        txA5OutputstageANumberOfEntries OBJECT-TYPE
            SYNTAX LogbookMaxEntryNumber
            MAX-ACCESS read-only
            STATUS current
            DESCRIPTION
                "The number of entries in logbook."
            ::= { logbookTxA5 7 }

        
        txA5OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 8 }

        
        txA5OutputstageALogbookTable OBJECT-TYPE
            SYNTAX SEQUENCE OF TxA5OutputstageALogbookEntry
            MAX-ACCESS not-accessible
            STATUS current
            DESCRIPTION
                "OutputstageA logbook table."
            ::= { logbookTxA5 9 }

        
        txA5OutputstageALogbookEntry OBJECT-TYPE
            SYNTAX TxA5OutputstageALogbookEntry
            MAX-ACCESS not-accessible
            STATUS current
            DESCRIPTION
                "This is a entry in the logbook."
            INDEX { txA5OstALogbookEntryIdx }
            ::= { txA5OutputstageALogbookTable 1 }

        
        TxA5OutputstageALogbookEntry ::=
            SEQUENCE { 
                txA5OstALogbookEntryIdx
                    LogbookMaxEntryNumber,
                txA5OstALogbookEntryNbr
                    LogbookMaxEntryNumber,
                txA5OstALogbookType
                    EventClass,
                txA5OstALogbookSlope
                    LogbookEntrySlope,
                txA5OstALogbookMessage
                    LogbookEntryMessagesOST,
                txA5OstALogbookDateTime
                    DateAndTime
             }

        txA5OstALogbookEntryIdx OBJECT-TYPE
            SYNTAX LogbookMaxEntryNumber
            MAX-ACCESS not-accessible
            STATUS current
            DESCRIPTION
                "This is an increasing number from 1 to 128. It is used as an index column for SNMP."
            ::= { txA5OutputstageALogbookEntry 1 }

        
        txA5OstALogbookEntryNbr OBJECT-TYPE
            SYNTAX LogbookMaxEntryNumber
            MAX-ACCESS read-only
            STATUS current
            DESCRIPTION
                "This is the number of the logbook entry. It is an decreasing number from max 128 down to 1."
            ::= { txA5OutputstageALogbookEntry 2 }

        
        txA5OstALogbookType OBJECT-TYPE
            SYNTAX EventClass
            MAX-ACCESS read-only
            STATUS current
            DESCRIPTION
                "Can either be Fault, Warning or State."
            ::= { txA5OutputstageALogbookEntry 3 }

        
        txA5OstALogbookSlope OBJECT-TYPE
            SYNTAX LogbookEntrySlope
            MAX-ACCESS read-only
            STATUS current
            DESCRIPTION
                "Either set (event raises) or reset (event disappears)"
            ::= { txA5OutputstageALogbookEntry 4 }

        
        txA5OstALogbookMessage OBJECT-TYPE
            SYNTAX LogbookEntryMessagesOST
            MAX-ACCESS read-only
            STATUS current
            DESCRIPTION
                "See RS-XX8000-COMMON-MIB - TextualConvention for details."
            ::= { txA5OutputstageALogbookEntry 5 }

        
        txA5OstALogbookDateTime OBJECT-TYPE
            SYNTAX DateAndTime
            MAX-ACCESS read-only
            STATUS current
            DESCRIPTION
                "The time of the logbook entry."
            ::= { txA5OutputstageALogbookEntry 6 }

        
        txA5ExciterBNumberOfEntries OBJECT-TYPE
            SYNTAX LogbookMaxEntryNumber
            MAX-ACCESS read-only
            STATUS current
            DESCRIPTION
                "The number of entries in logbook."
            ::= { logbookTxA5 13 }

        
        txA5ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA5 14 }

        
        txA5ExciterBLogbookTable OBJECT-TYPE
            SYNTAX SEQUENCE OF TxA5ExciterBLogbookEntry
            MAX-ACCESS not-accessible
            STATUS current
            DESCRIPTION
                "ExciterA logbook table."
            ::= { logbookTxA5 15 }

        
        txA5ExciterBLogbookEntry OBJECT-TYPE
            SYNTAX TxA5ExciterBLogbookEntry
            MAX-ACCESS not-accessible
            STATUS current
            DESCRIPTION
                "This is a entry in the logbook."
            INDEX { txA5ExcBLogbookEntryIdx }
            ::= { txA5ExciterBLogbookTable 1 }

        
        TxA5ExciterBLogbookEntry ::=
            SEQUENCE { 
                txA5ExcBLogbookEntryIdx
                    LogbookMaxEntryNumber,
                txA5ExcBLogbookEntryNbr
                    LogbookMaxEntryNumber,
                txA5ExcBLogbookType
                    EventClass,
                txA5ExcBLogbookSlope
                    LogbookEntrySlope,
                txA5ExcBLogbookMessage
                    LogbookEntryMessagesExcFM,
                txA5ExcBLogbookDateTime
                    DateAndTime
             }

        txA5ExcBLogbookEntryIdx OBJECT-TYPE
            SYNTAX LogbookMaxEntryNumber
            MAX-ACCESS not-accessible
            STATUS current
            DESCRIPTION
                "This is an increasing number from 1 to 128. It is used as an index column for SNMP."
            ::= { txA5ExciterBLogbookEntry 1 }

        
        txA5ExcBLogbookEntryNbr OBJECT-TYPE
            SYNTAX LogbookMaxEntryNumber
            MAX-ACCESS read-only
            STATUS current
            DESCRIPTION
                "This is the number of the logbook entry. It is an decreasing number from max 128 down to 1."
            ::= { txA5ExciterBLogbookEntry 2 }

        
        txA5ExcBLogbookType OBJECT-TYPE
            SYNTAX EventClass
            MAX-ACCESS read-only
            STATUS current
            DESCRIPTION
                "Can either be Fault, Warning or State."
            ::= { txA5ExciterBLogbookEntry 3 }

        
        txA5ExcBLogbookSlope OBJECT-TYPE
            SYNTAX LogbookEntrySlope
            MAX-ACCESS read-only
            STATUS current
            DESCRIPTION
                "Either set (event raises) or reset (event disappears)"
            ::= { txA5ExciterBLogbookEntry 4 }

        
        txA5ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA5ExciterBLogbookEntry 5 }

        
        txA5ExcBLogbookDateTime OBJECT-TYPE
            SYNTAX DateAndTime
            MAX-ACCESS read-only
            STATUS current
            DESCRIPTION
                "The time of the logbook entry."
            ::= { txA5ExciterBLogbookEntry 6 }

        
        outputstageATxA5 OBJECT IDENTIFIER ::= { txA5 2 }

        
        txA5OstARackTable OBJECT-TYPE
            SYNTAX SEQUENCE OF TxA5OstARackEntry
            MAX-ACCESS not-accessible
            STATUS current
            DESCRIPTION
                "The table of racks."
            ::= { outputstageATxA5 1 }

        
        txA5OstARackEntry OBJECT-TYPE
            SYNTAX TxA5OstARackEntry
            MAX-ACCESS not-accessible
            STATUS current
            DESCRIPTION
                "A row (an entry) for one rack."
            INDEX { txA5OstARackIdx }
            ::= { txA5OstARackTable 1 }

        
        TxA5OstARackEntry ::=
            SEQUENCE { 
                txA5OstARackIdx
                    IndexRack,
                txA5OstARackInletTemperature
                    FloatingPoint,
                txA5OstARackOutletTemperature
                    FloatingPoint,
                txA5OstARackAuxPowerSupply
                    FloatingPoint
             }

        txA5OstARackIdx OBJECT-TYPE
            SYNTAX IndexRack
            MAX-ACCESS not-accessible
            STATUS current
            DESCRIPTION
                "The rack number (1..10)."
            ::= { txA5OstARackEntry 1 }

        
        txA5OstARackInletTemperature OBJECT-TYPE
            SYNTAX FloatingPoint
            UNITS "Degree Celsius"
            MAX-ACCESS read-only
            STATUS current
            DESCRIPTION
                "The inlet temperature."
            ::= { txA5OstARackEntry 2 }

        
        txA5OstARackOutletTemperature OBJECT-TYPE
            SYNTAX FloatingPoint
            UNITS "Degree Celsius"
            MAX-ACCESS read-only
            STATUS current
            DESCRIPTION
                "The outlet temperature."
            ::= { txA5OstARackEntry 3 }

        
        txA5OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA5OstARackEntry 4 }

        
        txA6 OBJECT IDENTIFIER ::= { transmitter 46 }

        
        logbookTxA6 OBJECT IDENTIFIER ::= { txA6 1 }

        
        txA6NetCCUNumberOfEntries OBJECT-TYPE
            SYNTAX LogbookMaxEntryNumber
            MAX-ACCESS read-only
            STATUS current
            DESCRIPTION
                "The number of entries in logbook."
            ::= { logbookTxA6 1 }

        
        txA6NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 2 }

        
        txA6NetCCULogbookTable OBJECT-TYPE
            SYNTAX SEQUENCE OF TxA6NetCCULogbookEntry
            MAX-ACCESS not-accessible
            STATUS current
            DESCRIPTION
                "NetCCU logbook table."
            ::= { logbookTxA6 3 }

        
        txA6NetCCULogbookEntry OBJECT-TYPE
            SYNTAX TxA6NetCCULogbookEntry
            MAX-ACCESS not-accessible
            STATUS current
            DESCRIPTION
                "This is a entry in the logbook."
            INDEX { txA6NetCCULogbookEntryIdx }
            ::= { txA6NetCCULogbookTable 1 }

        
        TxA6NetCCULogbookEntry ::=
            SEQUENCE { 
                txA6NetCCULogbookEntryIdx
                    LogbookMaxEntryNumber,
                txA6NetCCULogbookEntryNbr
                    LogbookMaxEntryNumber,
                txA6NetCCULogbookType
                    EventClass,
                txA6NetCCULogbookSlope
                    LogbookEntrySlope,
                txA6NetCCULogbookMessage
                    LogbookEntryMessagesNetCCU,
                txA6NetCCULogbookDateTime
                    DateAndTime
             }

        txA6NetCCULogbookEntryIdx OBJECT-TYPE
            SYNTAX LogbookMaxEntryNumber
            MAX-ACCESS not-accessible
            STATUS current
            DESCRIPTION
                "This is an increasing number from 1 to 128. It is used as an index column for SNMP."
            ::= { txA6NetCCULogbookEntry 1 }

        
        txA6NetCCULogbookEntryNbr OBJECT-TYPE
            SYNTAX LogbookMaxEntryNumber
            MAX-ACCESS read-only
            STATUS current
            DESCRIPTION
                "This is the number of the logbook entry. It is an decreasing number from max 128 down to 1."
            ::= { txA6NetCCULogbookEntry 2 }

        
        txA6NetCCULogbookType OBJECT-TYPE
            SYNTAX EventClass
            MAX-ACCESS read-only
            STATUS current
            DESCRIPTION
                "Can either be Fault, Warning or State."
            ::= { txA6NetCCULogbookEntry 3 }

        
        txA6NetCCULogbookSlope OBJECT-TYPE
            SYNTAX LogbookEntrySlope
            MAX-ACCESS read-only
            STATUS current
            DESCRIPTION
                "Either set (event raises) or reset (event disappears)"
            ::= { txA6NetCCULogbookEntry 4 }

        
        txA6NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA6NetCCULogbookEntry 5 }

        
        txA6NetCCULogbookDateTime OBJECT-TYPE
            SYNTAX DateAndTime
            MAX-ACCESS read-only
            STATUS current
            DESCRIPTION
                "The time of the logbook entry."
            ::= { txA6NetCCULogbookEntry 6 }

        
        txA6ExciterANumberOfEntries OBJECT-TYPE
            SYNTAX LogbookMaxEntryNumber
            MAX-ACCESS read-only
            STATUS current
            DESCRIPTION
                "The number of entries in logbook."
            ::= { logbookTxA6 4 }

        
        txA6ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 5 }

        
        txA6ExciterALogbookTable OBJECT-TYPE
            SYNTAX SEQUENCE OF TxA6ExciterALogbookEntry
            MAX-ACCESS not-accessible
            STATUS current
            DESCRIPTION
                "ExciterA logbook table."
            ::= { logbookTxA6 6 }

        
        txA6ExciterALogbookEntry OBJECT-TYPE
            SYNTAX TxA6ExciterALogbookEntry
            MAX-ACCESS not-accessible
            STATUS current
            DESCRIPTION
                "This is a entry in the logbook."
            INDEX { txA6ExcALogbookEntryIdx }
            ::= { txA6ExciterALogbookTable 1 }

        
        TxA6ExciterALogbookEntry ::=
            SEQUENCE { 
                txA6ExcALogbookEntryIdx
                    LogbookMaxEntryNumber,
                txA6ExcALogbookEntryNbr
                    LogbookMaxEntryNumber,
                txA6ExcALogbookType
                    EventClass,
                txA6ExcALogbookSlope
                    LogbookEntrySlope,
                txA6ExcALogbookMessage
                    LogbookEntryMessagesExcFM,
                txA6ExcALogbookDateTime
                    DateAndTime
             }

        txA6ExcALogbookEntryIdx OBJECT-TYPE
            SYNTAX LogbookMaxEntryNumber
            MAX-ACCESS not-accessible
            STATUS current
            DESCRIPTION
                "This is an increasing number from 1 to 128. It is used as an index column for SNMP."
            ::= { txA6ExciterALogbookEntry 1 }

        
        txA6ExcALogbookEntryNbr OBJECT-TYPE
            SYNTAX LogbookMaxEntryNumber
            MAX-ACCESS read-only
            STATUS current
            DESCRIPTION
                "This is the number of the logbook entry. It is an decreasing number from max 128 down to 1."
            ::= { txA6ExciterALogbookEntry 2 }

        
        txA6ExcALogbookType OBJECT-TYPE
            SYNTAX EventClass
            MAX-ACCESS read-only
            STATUS current
            DESCRIPTION
                "Can either be Fault, Warning or State."
            ::= { txA6ExciterALogbookEntry 3 }

        
        txA6ExcALogbookSlope OBJECT-TYPE
            SYNTAX LogbookEntrySlope
            MAX-ACCESS read-only
            STATUS current
            DESCRIPTION
                "Either set (event raises) or reset (event disappears)"
            ::= { txA6ExciterALogbookEntry 4 }

        
        txA6ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA6ExciterALogbookEntry 5 }

        
        txA6ExcALogbookDateTime OBJECT-TYPE
            SYNTAX DateAndTime
            MAX-ACCESS read-only
            STATUS current
            DESCRIPTION
                "The time of the logbook entry."
            ::= { txA6ExciterALogbookEntry 6 }

        
        txA6OutputstageANumberOfEntries OBJECT-TYPE
            SYNTAX LogbookMaxEntryNumber
            MAX-ACCESS read-only
            STATUS current
            DESCRIPTION
                "The number of entries in logbook."
            ::= { logbookTxA6 7 }

        
        txA6OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 8 }

        
        txA6OutputstageALogbookTable OBJECT-TYPE
            SYNTAX SEQUENCE OF TxA6OutputstageALogbookEntry
            MAX-ACCESS not-accessible
            STATUS current
            DESCRIPTION
                "OutputstageA logbook table."
            ::= { logbookTxA6 9 }

        
        txA6OutputstageALogbookEntry OBJECT-TYPE
            SYNTAX TxA6OutputstageALogbookEntry
            MAX-ACCESS not-accessible
            STATUS current
            DESCRIPTION
                "This is a entry in the logbook."
            INDEX { txA6OstALogbookEntryIdx }
            ::= { txA6OutputstageALogbookTable 1 }

        
        TxA6OutputstageALogbookEntry ::=
            SEQUENCE { 
                txA6OstALogbookEntryIdx
                    LogbookMaxEntryNumber,
                txA6OstALogbookEntryNbr
                    LogbookMaxEntryNumber,
                txA6OstALogbookType
                    EventClass,
                txA6OstALogbookSlope
                    LogbookEntrySlope,
                txA6OstALogbookMessage
                    LogbookEntryMessagesOST,
                txA6OstALogbookDateTime
                    DateAndTime
             }

        txA6OstALogbookEntryIdx OBJECT-TYPE
            SYNTAX LogbookMaxEntryNumber
            MAX-ACCESS not-accessible
            STATUS current
            DESCRIPTION
                "This is an increasing number from 1 to 128. It is used as an index column for SNMP."
            ::= { txA6OutputstageALogbookEntry 1 }

        
        txA6OstALogbookEntryNbr OBJECT-TYPE
            SYNTAX LogbookMaxEntryNumber
            MAX-ACCESS read-only
            STATUS current
            DESCRIPTION
                "This is the number of the logbook entry. It is an decreasing number from max 128 down to 1."
            ::= { txA6OutputstageALogbookEntry 2 }

        
        txA6OstALogbookType OBJECT-TYPE
            SYNTAX EventClass
            MAX-ACCESS read-only
            STATUS current
            DESCRIPTION
                "Can either be Fault, Warning or State."
            ::= { txA6OutputstageALogbookEntry 3 }

        
        txA6OstALogbookSlope OBJECT-TYPE
            SYNTAX LogbookEntrySlope
            MAX-ACCESS read-only
            STATUS current
            DESCRIPTION
                "Either set (event raises) or reset (event disappears)"
            ::= { txA6OutputstageALogbookEntry 4 }

        
        txA6OstALogbookMessage OBJECT-TYPE
            SYNTAX LogbookEntryMessagesOST
            MAX-ACCESS read-only
            STATUS current
            DESCRIPTION
                "See RS-XX8000-COMMON-MIB - TextualConvention for details."
            ::= { txA6OutputstageALogbookEntry 5 }

        
        txA6OstALogbookDateTime OBJECT-TYPE
            SYNTAX DateAndTime
            MAX-ACCESS read-only
            STATUS current
            DESCRIPTION
                "The time of the logbook entry."
            ::= { txA6OutputstageALogbookEntry 6 }

        
        txA6ExciterBNumberOfEntries OBJECT-TYPE
            SYNTAX LogbookMaxEntryNumber
            MAX-ACCESS read-only
            STATUS current
            DESCRIPTION
                "The number of entries in logbook."
            ::= { logbookTxA6 13 }

        
        txA6ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA6 14 }

        
        txA6ExciterBLogbookTable OBJECT-TYPE
            SYNTAX SEQUENCE OF TxA6ExciterBLogbookEntry
            MAX-ACCESS not-accessible
            STATUS current
            DESCRIPTION
                "ExciterA logbook table."
            ::= { logbookTxA6 15 }

        
        txA6ExciterBLogbookEntry OBJECT-TYPE
            SYNTAX TxA6ExciterBLogbookEntry
            MAX-ACCESS not-accessible
            STATUS current
            DESCRIPTION
                "This is a entry in the logbook."
            INDEX { txA6ExcBLogbookEntryIdx }
            ::= { txA6ExciterBLogbookTable 1 }

        
        TxA6ExciterBLogbookEntry ::=
            SEQUENCE { 
                txA6ExcBLogbookEntryIdx
                    LogbookMaxEntryNumber,
                txA6ExcBLogbookEntryNbr
                    LogbookMaxEntryNumber,
                txA6ExcBLogbookType
                    EventClass,
                txA6ExcBLogbookSlope
                    LogbookEntrySlope,
                txA6ExcBLogbookMessage
                    LogbookEntryMessagesExcFM,
                txA6ExcBLogbookDateTime
                    DateAndTime
             }

        txA6ExcBLogbookEntryIdx OBJECT-TYPE
            SYNTAX LogbookMaxEntryNumber
            MAX-ACCESS not-accessible
            STATUS current
            DESCRIPTION
                "This is an increasing number from 1 to 128. It is used as an index column for SNMP."
            ::= { txA6ExciterBLogbookEntry 1 }

        
        txA6ExcBLogbookEntryNbr OBJECT-TYPE
            SYNTAX LogbookMaxEntryNumber
            MAX-ACCESS read-only
            STATUS current
            DESCRIPTION
                "This is the number of the logbook entry. It is an decreasing number from max 128 down to 1."
            ::= { txA6ExciterBLogbookEntry 2 }

        
        txA6ExcBLogbookType OBJECT-TYPE
            SYNTAX EventClass
            MAX-ACCESS read-only
            STATUS current
            DESCRIPTION
                "Can either be Fault, Warning or State."
            ::= { txA6ExciterBLogbookEntry 3 }

        
        txA6ExcBLogbookSlope OBJECT-TYPE
            SYNTAX LogbookEntrySlope
            MAX-ACCESS read-only
            STATUS current
            DESCRIPTION
                "Either set (event raises) or reset (event disappears)"
            ::= { txA6ExciterBLogbookEntry 4 }

        
        txA6ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA6ExciterBLogbookEntry 5 }

        
        txA6ExcBLogbookDateTime OBJECT-TYPE
            SYNTAX DateAndTime
            MAX-ACCESS read-only
            STATUS current
            DESCRIPTION
                "The time of the logbook entry."
            ::= { txA6ExciterBLogbookEntry 6 }

        
        outputstageATxA6 OBJECT IDENTIFIER ::= { txA6 2 }

        
        txA6OstARackTable OBJECT-TYPE
            SYNTAX SEQUENCE OF TxA6OstARackEntry
            MAX-ACCESS not-accessible
            STATUS current
            DESCRIPTION
                "The table of racks."
            ::= { outputstageATxA6 1 }

        
        txA6OstARackEntry OBJECT-TYPE
            SYNTAX TxA6OstARackEntry
            MAX-ACCESS not-accessible
            STATUS current
            DESCRIPTION
                "A row (an entry) for one rack."
            INDEX { txA6OstARackIdx }
            ::= { txA6OstARackTable 1 }

        
        TxA6OstARackEntry ::=
            SEQUENCE { 
                txA6OstARackIdx
                    IndexRack,
                txA6OstARackInletTemperature
                    FloatingPoint,
                txA6OstARackOutletTemperature
                    FloatingPoint,
                txA6OstARackAuxPowerSupply
                    FloatingPoint
             }

        txA6OstARackIdx OBJECT-TYPE
            SYNTAX IndexRack
            MAX-ACCESS not-accessible
            STATUS current
            DESCRIPTION
                "The rack number (1..10)."
            ::= { txA6OstARackEntry 1 }

        
        txA6OstARackInletTemperature OBJECT-TYPE
            SYNTAX FloatingPoint
            UNITS "Degree Celsius"
            MAX-ACCESS read-only
            STATUS current
            DESCRIPTION
                "The inlet temperature."
            ::= { txA6OstARackEntry 2 }

        
        txA6OstARackOutletTemperature OBJECT-TYPE
            SYNTAX FloatingPoint
            UNITS "Degree Celsius"
            MAX-ACCESS read-only
            STATUS current
            DESCRIPTION
                "The outlet temperature."
            ::= { txA6OstARackEntry 3 }

        
        txA6OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA6OstARackEntry 4 }

        
        txA7 OBJECT IDENTIFIER ::= { transmitter 47 }

        
        logbookTxA7 OBJECT IDENTIFIER ::= { txA7 1 }

        
        txA7NetCCUNumberOfEntries OBJECT-TYPE
            SYNTAX LogbookMaxEntryNumber
            MAX-ACCESS read-only
            STATUS current
            DESCRIPTION
                "The number of entries in logbook."
            ::= { logbookTxA7 1 }

        
        txA7NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 2 }

        
        txA7NetCCULogbookTable OBJECT-TYPE
            SYNTAX SEQUENCE OF TxA7NetCCULogbookEntry
            MAX-ACCESS not-accessible
            STATUS current
            DESCRIPTION
                "NetCCU logbook table."
            ::= { logbookTxA7 3 }

        
        txA7NetCCULogbookEntry OBJECT-TYPE
            SYNTAX TxA7NetCCULogbookEntry
            MAX-ACCESS not-accessible
            STATUS current
            DESCRIPTION
                "This is a entry in the logbook."
            INDEX { txA7NetCCULogbookEntryIdx }
            ::= { txA7NetCCULogbookTable 1 }

        
        TxA7NetCCULogbookEntry ::=
            SEQUENCE { 
                txA7NetCCULogbookEntryIdx
                    LogbookMaxEntryNumber,
                txA7NetCCULogbookEntryNbr
                    LogbookMaxEntryNumber,
                txA7NetCCULogbookType
                    EventClass,
                txA7NetCCULogbookSlope
                    LogbookEntrySlope,
                txA7NetCCULogbookMessage
                    LogbookEntryMessagesNetCCU,
                txA7NetCCULogbookDateTime
                    DateAndTime
             }

        txA7NetCCULogbookEntryIdx OBJECT-TYPE
            SYNTAX LogbookMaxEntryNumber
            MAX-ACCESS not-accessible
            STATUS current
            DESCRIPTION
                "This is an increasing number from 1 to 128. It is used as an index column for SNMP."
            ::= { txA7NetCCULogbookEntry 1 }

        
        txA7NetCCULogbookEntryNbr OBJECT-TYPE
            SYNTAX LogbookMaxEntryNumber
            MAX-ACCESS read-only
            STATUS current
            DESCRIPTION
                "This is the number of the logbook entry. It is an decreasing number from max 128 down to 1."
            ::= { txA7NetCCULogbookEntry 2 }

        
        txA7NetCCULogbookType OBJECT-TYPE
            SYNTAX EventClass
            MAX-ACCESS read-only
            STATUS current
            DESCRIPTION
                "Can either be Fault, Warning or State."
            ::= { txA7NetCCULogbookEntry 3 }

        
        txA7NetCCULogbookSlope OBJECT-TYPE
            SYNTAX LogbookEntrySlope
            MAX-ACCESS read-only
            STATUS current
            DESCRIPTION
                "Either set (event raises) or reset (event disappears)"
            ::= { txA7NetCCULogbookEntry 4 }

        
        txA7NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA7NetCCULogbookEntry 5 }

        
        txA7NetCCULogbookDateTime OBJECT-TYPE
            SYNTAX DateAndTime
            MAX-ACCESS read-only
            STATUS current
            DESCRIPTION
                "The time of the logbook entry."
            ::= { txA7NetCCULogbookEntry 6 }

        
        txA7ExciterANumberOfEntries OBJECT-TYPE
            SYNTAX LogbookMaxEntryNumber
            MAX-ACCESS read-only
            STATUS current
            DESCRIPTION
                "The number of entries in logbook."
            ::= { logbookTxA7 4 }

        
        txA7ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 5 }

        
        txA7ExciterALogbookTable OBJECT-TYPE
            SYNTAX SEQUENCE OF TxA7ExciterALogbookEntry
            MAX-ACCESS not-accessible
            STATUS current
            DESCRIPTION
                "ExciterA logbook table."
            ::= { logbookTxA7 6 }

        
        txA7ExciterALogbookEntry OBJECT-TYPE
            SYNTAX TxA7ExciterALogbookEntry
            MAX-ACCESS not-accessible
            STATUS current
            DESCRIPTION
                "This is a entry in the logbook."
            INDEX { txA7ExcALogbookEntryIdx }
            ::= { txA7ExciterALogbookTable 1 }

        
        TxA7ExciterALogbookEntry ::=
            SEQUENCE { 
                txA7ExcALogbookEntryIdx
                    LogbookMaxEntryNumber,
                txA7ExcALogbookEntryNbr
                    LogbookMaxEntryNumber,
                txA7ExcALogbookType
                    EventClass,
                txA7ExcALogbookSlope
                    LogbookEntrySlope,
                txA7ExcALogbookMessage
                    LogbookEntryMessagesExcFM,
                txA7ExcALogbookDateTime
                    DateAndTime
             }

        txA7ExcALogbookEntryIdx OBJECT-TYPE
            SYNTAX LogbookMaxEntryNumber
            MAX-ACCESS not-accessible
            STATUS current
            DESCRIPTION
                "This is an increasing number from 1 to 128. It is used as an index column for SNMP."
            ::= { txA7ExciterALogbookEntry 1 }

        
        txA7ExcALogbookEntryNbr OBJECT-TYPE
            SYNTAX LogbookMaxEntryNumber
            MAX-ACCESS read-only
            STATUS current
            DESCRIPTION
                "This is the number of the logbook entry. It is an decreasing number from max 128 down to 1."
            ::= { txA7ExciterALogbookEntry 2 }

        
        txA7ExcALogbookType OBJECT-TYPE
            SYNTAX EventClass
            MAX-ACCESS read-only
            STATUS current
            DESCRIPTION
                "Can either be Fault, Warning or State."
            ::= { txA7ExciterALogbookEntry 3 }

        
        txA7ExcALogbookSlope OBJECT-TYPE
            SYNTAX LogbookEntrySlope
            MAX-ACCESS read-only
            STATUS current
            DESCRIPTION
                "Either set (event raises) or reset (event disappears)"
            ::= { txA7ExciterALogbookEntry 4 }

        
        txA7ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA7ExciterALogbookEntry 5 }

        
        txA7ExcALogbookDateTime OBJECT-TYPE
            SYNTAX DateAndTime
            MAX-ACCESS read-only
            STATUS current
            DESCRIPTION
                "The time of the logbook entry."
            ::= { txA7ExciterALogbookEntry 6 }

        
        txA7OutputstageANumberOfEntries OBJECT-TYPE
            SYNTAX LogbookMaxEntryNumber
            MAX-ACCESS read-only
            STATUS current
            DESCRIPTION
                "The number of entries in logbook."
            ::= { logbookTxA7 7 }

        
        txA7OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 8 }

        
        txA7OutputstageALogbookTable OBJECT-TYPE
            SYNTAX SEQUENCE OF TxA7OutputstageALogbookEntry
            MAX-ACCESS not-accessible
            STATUS current
            DESCRIPTION
                "OutputstageA logbook table."
            ::= { logbookTxA7 9 }

        
        txA7OutputstageALogbookEntry OBJECT-TYPE
            SYNTAX TxA7OutputstageALogbookEntry
            MAX-ACCESS not-accessible
            STATUS current
            DESCRIPTION
                "This is a entry in the logbook."
            INDEX { txA7OstALogbookEntryIdx }
            ::= { txA7OutputstageALogbookTable 1 }

        
        TxA7OutputstageALogbookEntry ::=
            SEQUENCE { 
                txA7OstALogbookEntryIdx
                    LogbookMaxEntryNumber,
                txA7OstALogbookEntryNbr
                    LogbookMaxEntryNumber,
                txA7OstALogbookType
                    EventClass,
                txA7OstALogbookSlope
                    LogbookEntrySlope,
                txA7OstALogbookMessage
                    LogbookEntryMessagesOST,
                txA7OstALogbookDateTime
                    DateAndTime
             }

        txA7OstALogbookEntryIdx OBJECT-TYPE
            SYNTAX LogbookMaxEntryNumber
            MAX-ACCESS not-accessible
            STATUS current
            DESCRIPTION
                "This is an increasing number from 1 to 128. It is used as an index column for SNMP."
            ::= { txA7OutputstageALogbookEntry 1 }

        
        txA7OstALogbookEntryNbr OBJECT-TYPE
            SYNTAX LogbookMaxEntryNumber
            MAX-ACCESS read-only
            STATUS current
            DESCRIPTION
                "This is the number of the logbook entry. It is an decreasing number from max 128 down to 1."
            ::= { txA7OutputstageALogbookEntry 2 }

        
        txA7OstALogbookType OBJECT-TYPE
            SYNTAX EventClass
            MAX-ACCESS read-only
            STATUS current
            DESCRIPTION
                "Can either be Fault, Warning or State."
            ::= { txA7OutputstageALogbookEntry 3 }

        
        txA7OstALogbookSlope OBJECT-TYPE
            SYNTAX LogbookEntrySlope
            MAX-ACCESS read-only
            STATUS current
            DESCRIPTION
                "Either set (event raises) or reset (event disappears)"
            ::= { txA7OutputstageALogbookEntry 4 }

        
        txA7OstALogbookMessage OBJECT-TYPE
            SYNTAX LogbookEntryMessagesOST
            MAX-ACCESS read-only
            STATUS current
            DESCRIPTION
                "See RS-XX8000-COMMON-MIB - TextualConvention for details."
            ::= { txA7OutputstageALogbookEntry 5 }

        
        txA7OstALogbookDateTime OBJECT-TYPE
            SYNTAX DateAndTime
            MAX-ACCESS read-only
            STATUS current
            DESCRIPTION
                "The time of the logbook entry."
            ::= { txA7OutputstageALogbookEntry 6 }

        
        txA7ExciterBNumberOfEntries OBJECT-TYPE
            SYNTAX LogbookMaxEntryNumber
            MAX-ACCESS read-only
            STATUS current
            DESCRIPTION
                "The number of entries in logbook."
            ::= { logbookTxA7 13 }

        
        txA7ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA7 14 }

        
        txA7ExciterBLogbookTable OBJECT-TYPE
            SYNTAX SEQUENCE OF TxA7ExciterBLogbookEntry
            MAX-ACCESS not-accessible
            STATUS current
            DESCRIPTION
                "ExciterA logbook table."
            ::= { logbookTxA7 15 }

        
        txA7ExciterBLogbookEntry OBJECT-TYPE
            SYNTAX TxA7ExciterBLogbookEntry
            MAX-ACCESS not-accessible
            STATUS current
            DESCRIPTION
                "This is a entry in the logbook."
            INDEX { txA7ExcBLogbookEntryIdx }
            ::= { txA7ExciterBLogbookTable 1 }

        
        TxA7ExciterBLogbookEntry ::=
            SEQUENCE { 
                txA7ExcBLogbookEntryIdx
                    LogbookMaxEntryNumber,
                txA7ExcBLogbookEntryNbr
                    LogbookMaxEntryNumber,
                txA7ExcBLogbookType
                    EventClass,
                txA7ExcBLogbookSlope
                    LogbookEntrySlope,
                txA7ExcBLogbookMessage
                    LogbookEntryMessagesExcFM,
                txA7ExcBLogbookDateTime
                    DateAndTime
             }

        txA7ExcBLogbookEntryIdx OBJECT-TYPE
            SYNTAX LogbookMaxEntryNumber
            MAX-ACCESS not-accessible
            STATUS current
            DESCRIPTION
                "This is an increasing number from 1 to 128. It is used as an index column for SNMP."
            ::= { txA7ExciterBLogbookEntry 1 }

        
        txA7ExcBLogbookEntryNbr OBJECT-TYPE
            SYNTAX LogbookMaxEntryNumber
            MAX-ACCESS read-only
            STATUS current
            DESCRIPTION
                "This is the number of the logbook entry. It is an decreasing number from max 128 down to 1."
            ::= { txA7ExciterBLogbookEntry 2 }

        
        txA7ExcBLogbookType OBJECT-TYPE
            SYNTAX EventClass
            MAX-ACCESS read-only
            STATUS current
            DESCRIPTION
                "Can either be Fault, Warning or State."
            ::= { txA7ExciterBLogbookEntry 3 }

        
        txA7ExcBLogbookSlope OBJECT-TYPE
            SYNTAX LogbookEntrySlope
            MAX-ACCESS read-only
            STATUS current
            DESCRIPTION
                "Either set (event raises) or reset (event disappears)"
            ::= { txA7ExciterBLogbookEntry 4 }

        
        txA7ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA7ExciterBLogbookEntry 5 }

        
        txA7ExcBLogbookDateTime OBJECT-TYPE
            SYNTAX DateAndTime
            MAX-ACCESS read-only
            STATUS current
            DESCRIPTION
                "The time of the logbook entry."
            ::= { txA7ExciterBLogbookEntry 6 }

        
        outputstageATxA7 OBJECT IDENTIFIER ::= { txA7 2 }

        
        txA7OstARackTable OBJECT-TYPE
            SYNTAX SEQUENCE OF TxA7OstARackEntry
            MAX-ACCESS not-accessible
            STATUS current
            DESCRIPTION
                "The table of racks."
            ::= { outputstageATxA7 1 }

        
        txA7OstARackEntry OBJECT-TYPE
            SYNTAX TxA7OstARackEntry
            MAX-ACCESS not-accessible
            STATUS current
            DESCRIPTION
                "A row (an entry) for one rack."
            INDEX { txA7OstARackIdx }
            ::= { txA7OstARackTable 1 }

        
        TxA7OstARackEntry ::=
            SEQUENCE { 
                txA7OstARackIdx
                    IndexRack,
                txA7OstARackInletTemperature
                    FloatingPoint,
                txA7OstARackOutletTemperature
                    FloatingPoint,
                txA7OstARackAuxPowerSupply
                    FloatingPoint
             }

        txA7OstARackIdx OBJECT-TYPE
            SYNTAX IndexRack
            MAX-ACCESS not-accessible
            STATUS current
            DESCRIPTION
                "The rack number (1..10)."
            ::= { txA7OstARackEntry 1 }

        
        txA7OstARackInletTemperature OBJECT-TYPE
            SYNTAX FloatingPoint
            UNITS "Degree Celsius"
            MAX-ACCESS read-only
            STATUS current
            DESCRIPTION
                "The inlet temperature."
            ::= { txA7OstARackEntry 2 }

        
        txA7OstARackOutletTemperature OBJECT-TYPE
            SYNTAX FloatingPoint
            UNITS "Degree Celsius"
            MAX-ACCESS read-only
            STATUS current
            DESCRIPTION
                "The outlet temperature."
            ::= { txA7OstARackEntry 3 }

        
        txA7OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA7OstARackEntry 4 }

        
        txA8 OBJECT IDENTIFIER ::= { transmitter 48 }

        
        logbookTxA8 OBJECT IDENTIFIER ::= { txA8 1 }

        
        txA8NetCCUNumberOfEntries OBJECT-TYPE
            SYNTAX LogbookMaxEntryNumber
            MAX-ACCESS read-only
            STATUS current
            DESCRIPTION
                "The number of entries in logbook."
            ::= { logbookTxA8 1 }

        
        txA8NetCCULogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 2 }

        
        txA8NetCCULogbookTable OBJECT-TYPE
            SYNTAX SEQUENCE OF TxA8NetCCULogbookEntry
            MAX-ACCESS not-accessible
            STATUS current
            DESCRIPTION
                "NetCCU logbook table."
            ::= { logbookTxA8 3 }

        
        txA8NetCCULogbookEntry OBJECT-TYPE
            SYNTAX TxA8NetCCULogbookEntry
            MAX-ACCESS not-accessible
            STATUS current
            DESCRIPTION
                "This is a entry in the logbook."
            INDEX { txA8NetCCULogbookEntryIdx }
            ::= { txA8NetCCULogbookTable 1 }

        
        TxA8NetCCULogbookEntry ::=
            SEQUENCE { 
                txA8NetCCULogbookEntryIdx
                    LogbookMaxEntryNumber,
                txA8NetCCULogbookEntryNbr
                    LogbookMaxEntryNumber,
                txA8NetCCULogbookType
                    EventClass,
                txA8NetCCULogbookSlope
                    LogbookEntrySlope,
                txA8NetCCULogbookMessage
                    LogbookEntryMessagesNetCCU,
                txA8NetCCULogbookDateTime
                    DateAndTime
             }

        txA8NetCCULogbookEntryIdx OBJECT-TYPE
            SYNTAX LogbookMaxEntryNumber
            MAX-ACCESS not-accessible
            STATUS current
            DESCRIPTION
                "This is an increasing number from 1 to 128. It is used as an index column for SNMP."
            ::= { txA8NetCCULogbookEntry 1 }

        
        txA8NetCCULogbookEntryNbr OBJECT-TYPE
            SYNTAX LogbookMaxEntryNumber
            MAX-ACCESS read-only
            STATUS current
            DESCRIPTION
                "This is the number of the logbook entry. It is an decreasing number from max 128 down to 1."
            ::= { txA8NetCCULogbookEntry 2 }

        
        txA8NetCCULogbookType OBJECT-TYPE
            SYNTAX EventClass
            MAX-ACCESS read-only
            STATUS current
            DESCRIPTION
                "Can either be Fault, Warning or State."
            ::= { txA8NetCCULogbookEntry 3 }

        
        txA8NetCCULogbookSlope OBJECT-TYPE
            SYNTAX LogbookEntrySlope
            MAX-ACCESS read-only
            STATUS current
            DESCRIPTION
                "Either set (event raises) or reset (event disappears)"
            ::= { txA8NetCCULogbookEntry 4 }

        
        txA8NetCCULogbookMessage OBJECT-TYPE
            SYNTAX LogbookEntryMessagesNetCCU
            MAX-ACCESS read-only
            STATUS current
            DESCRIPTION
                "See RS-XX8000-COMMON-MIB - TextualConvention - LogbookEntryMessagesNetCCU for details."
            ::= { txA8NetCCULogbookEntry 5 }

        
        txA8NetCCULogbookDateTime OBJECT-TYPE
            SYNTAX DateAndTime
            MAX-ACCESS read-only
            STATUS current
            DESCRIPTION
                "The time of the logbook entry."
            ::= { txA8NetCCULogbookEntry 6 }

        
        txA8ExciterANumberOfEntries OBJECT-TYPE
            SYNTAX LogbookMaxEntryNumber
            MAX-ACCESS read-only
            STATUS current
            DESCRIPTION
                "The number of entries in logbook."
            ::= { logbookTxA8 4 }

        
        txA8ExciterALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 5 }

        
        txA8ExciterALogbookTable OBJECT-TYPE
            SYNTAX SEQUENCE OF TxA8ExciterALogbookEntry
            MAX-ACCESS not-accessible
            STATUS current
            DESCRIPTION
                "ExciterA logbook table."
            ::= { logbookTxA8 6 }

        
        txA8ExciterALogbookEntry OBJECT-TYPE
            SYNTAX TxA8ExciterALogbookEntry
            MAX-ACCESS not-accessible
            STATUS current
            DESCRIPTION
                "This is a entry in the logbook."
            INDEX { txA8ExcALogbookEntryIdx }
            ::= { txA8ExciterALogbookTable 1 }

        
        TxA8ExciterALogbookEntry ::=
            SEQUENCE { 
                txA8ExcALogbookEntryIdx
                    LogbookMaxEntryNumber,
                txA8ExcALogbookEntryNbr
                    LogbookMaxEntryNumber,
                txA8ExcALogbookType
                    EventClass,
                txA8ExcALogbookSlope
                    LogbookEntrySlope,
                txA8ExcALogbookMessage
                    LogbookEntryMessagesExcFM,
                txA8ExcALogbookDateTime
                    DateAndTime
             }

        txA8ExcALogbookEntryIdx OBJECT-TYPE
            SYNTAX LogbookMaxEntryNumber
            MAX-ACCESS not-accessible
            STATUS current
            DESCRIPTION
                "This is an increasing number from 1 to 128. It is used as an index column for SNMP."
            ::= { txA8ExciterALogbookEntry 1 }

        
        txA8ExcALogbookEntryNbr OBJECT-TYPE
            SYNTAX LogbookMaxEntryNumber
            MAX-ACCESS read-only
            STATUS current
            DESCRIPTION
                "This is the number of the logbook entry. It is an decreasing number from max 128 down to 1."
            ::= { txA8ExciterALogbookEntry 2 }

        
        txA8ExcALogbookType OBJECT-TYPE
            SYNTAX EventClass
            MAX-ACCESS read-only
            STATUS current
            DESCRIPTION
                "Can either be Fault, Warning or State."
            ::= { txA8ExciterALogbookEntry 3 }

        
        txA8ExcALogbookSlope OBJECT-TYPE
            SYNTAX LogbookEntrySlope
            MAX-ACCESS read-only
            STATUS current
            DESCRIPTION
                "Either set (event raises) or reset (event disappears)"
            ::= { txA8ExciterALogbookEntry 4 }

        
        txA8ExcALogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA8ExciterALogbookEntry 5 }

        
        txA8ExcALogbookDateTime OBJECT-TYPE
            SYNTAX DateAndTime
            MAX-ACCESS read-only
            STATUS current
            DESCRIPTION
                "The time of the logbook entry."
            ::= { txA8ExciterALogbookEntry 6 }

        
        txA8OutputstageANumberOfEntries OBJECT-TYPE
            SYNTAX LogbookMaxEntryNumber
            MAX-ACCESS read-only
            STATUS current
            DESCRIPTION
                "The number of entries in logbook."
            ::= { logbookTxA8 7 }

        
        txA8OutputstageALogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 8 }

        
        txA8OutputstageALogbookTable OBJECT-TYPE
            SYNTAX SEQUENCE OF TxA8OutputstageALogbookEntry
            MAX-ACCESS not-accessible
            STATUS current
            DESCRIPTION
                "OutputstageA logbook table."
            ::= { logbookTxA8 9 }

        
        txA8OutputstageALogbookEntry OBJECT-TYPE
            SYNTAX TxA8OutputstageALogbookEntry
            MAX-ACCESS not-accessible
            STATUS current
            DESCRIPTION
                "This is a entry in the logbook."
            INDEX { txA8OstALogbookEntryIdx }
            ::= { txA8OutputstageALogbookTable 1 }

        
        TxA8OutputstageALogbookEntry ::=
            SEQUENCE { 
                txA8OstALogbookEntryIdx
                    LogbookMaxEntryNumber,
                txA8OstALogbookEntryNbr
                    LogbookMaxEntryNumber,
                txA8OstALogbookType
                    EventClass,
                txA8OstALogbookSlope
                    LogbookEntrySlope,
                txA8OstALogbookMessage
                    LogbookEntryMessagesOST,
                txA8OstALogbookDateTime
                    DateAndTime
             }

        txA8OstALogbookEntryIdx OBJECT-TYPE
            SYNTAX LogbookMaxEntryNumber
            MAX-ACCESS not-accessible
            STATUS current
            DESCRIPTION
                "This is an increasing number from 1 to 128. It is used as an index column for SNMP."
            ::= { txA8OutputstageALogbookEntry 1 }

        
        txA8OstALogbookEntryNbr OBJECT-TYPE
            SYNTAX LogbookMaxEntryNumber
            MAX-ACCESS read-only
            STATUS current
            DESCRIPTION
                "This is the number of the logbook entry. It is an decreasing number from max 128 down to 1."
            ::= { txA8OutputstageALogbookEntry 2 }

        
        txA8OstALogbookType OBJECT-TYPE
            SYNTAX EventClass
            MAX-ACCESS read-only
            STATUS current
            DESCRIPTION
                "Can either be Fault, Warning or State."
            ::= { txA8OutputstageALogbookEntry 3 }

        
        txA8OstALogbookSlope OBJECT-TYPE
            SYNTAX LogbookEntrySlope
            MAX-ACCESS read-only
            STATUS current
            DESCRIPTION
                "Either set (event raises) or reset (event disappears)"
            ::= { txA8OutputstageALogbookEntry 4 }

        
        txA8OstALogbookMessage OBJECT-TYPE
            SYNTAX LogbookEntryMessagesOST
            MAX-ACCESS read-only
            STATUS current
            DESCRIPTION
                "See RS-XX8000-COMMON-MIB - TextualConvention for details."
            ::= { txA8OutputstageALogbookEntry 5 }

        
        txA8OstALogbookDateTime OBJECT-TYPE
            SYNTAX DateAndTime
            MAX-ACCESS read-only
            STATUS current
            DESCRIPTION
                "The time of the logbook entry."
            ::= { txA8OutputstageALogbookEntry 6 }

        
        txA8ExciterBNumberOfEntries OBJECT-TYPE
            SYNTAX LogbookMaxEntryNumber
            MAX-ACCESS read-only
            STATUS current
            DESCRIPTION
                "The number of entries in logbook."
            ::= { logbookTxA8 13 }

        
        txA8ExciterBLogbookClear OBJECT-TYPE
            SYNTAX Trigger
            MAX-ACCESS read-write
            STATUS current
            DESCRIPTION
                "Clear the logbook.
                idle(1)    --> ready
                clear(2)   --> do clear now
                
                A GET will always return idle(1). A SET idle(1) will return NO_ERROR without doing anything."
            ::= { logbookTxA8 14 }

        
        txA8ExciterBLogbookTable OBJECT-TYPE
            SYNTAX SEQUENCE OF TxA8ExciterBLogbookEntry
            MAX-ACCESS not-accessible
            STATUS current
            DESCRIPTION
                "ExciterA logbook table."
            ::= { logbookTxA8 15 }

        
        txA8ExciterBLogbookEntry OBJECT-TYPE
            SYNTAX TxA8ExciterBLogbookEntry
            MAX-ACCESS not-accessible
            STATUS current
            DESCRIPTION
                "This is a entry in the logbook."
            INDEX { txA8ExcBLogbookEntryIdx }
            ::= { txA8ExciterBLogbookTable 1 }

        
        TxA8ExciterBLogbookEntry ::=
            SEQUENCE { 
                txA8ExcBLogbookEntryIdx
                    LogbookMaxEntryNumber,
                txA8ExcBLogbookEntryNbr
                    LogbookMaxEntryNumber,
                txA8ExcBLogbookType
                    EventClass,
                txA8ExcBLogbookSlope
                    LogbookEntrySlope,
                txA8ExcBLogbookMessage
                    LogbookEntryMessagesExcFM,
                txA8ExcBLogbookDateTime
                    DateAndTime
             }

        txA8ExcBLogbookEntryIdx OBJECT-TYPE
            SYNTAX LogbookMaxEntryNumber
            MAX-ACCESS not-accessible
            STATUS current
            DESCRIPTION
                "This is an increasing number from 1 to 128. It is used as an index column for SNMP."
            ::= { txA8ExciterBLogbookEntry 1 }

        
        txA8ExcBLogbookEntryNbr OBJECT-TYPE
            SYNTAX LogbookMaxEntryNumber
            MAX-ACCESS read-only
            STATUS current
            DESCRIPTION
                "This is the number of the logbook entry. It is an decreasing number from max 128 down to 1."
            ::= { txA8ExciterBLogbookEntry 2 }

        
        txA8ExcBLogbookType OBJECT-TYPE
            SYNTAX EventClass
            MAX-ACCESS read-only
            STATUS current
            DESCRIPTION
                "Can either be Fault, Warning or State."
            ::= { txA8ExciterBLogbookEntry 3 }

        
        txA8ExcBLogbookSlope OBJECT-TYPE
            SYNTAX LogbookEntrySlope
            MAX-ACCESS read-only
            STATUS current
            DESCRIPTION
                "Either set (event raises) or reset (event disappears)"
            ::= { txA8ExciterBLogbookEntry 4 }

        
        txA8ExcBLogbookMessage OBJECT-TYPE
            SYNTAX LogbookEntryMessagesExcFM
            MAX-ACCESS read-only
            STATUS current
            DESCRIPTION
                "See RS-XX8000-COMMON-MIB - TextualConvention - LogbookEntryMessagesExcDVB for details."
            ::= { txA8ExciterBLogbookEntry 5 }

        
        txA8ExcBLogbookDateTime OBJECT-TYPE
            SYNTAX DateAndTime
            MAX-ACCESS read-only
            STATUS current
            DESCRIPTION
                "The time of the logbook entry."
            ::= { txA8ExciterBLogbookEntry 6 }

        
        outputstageATxA8 OBJECT IDENTIFIER ::= { txA8 2 }

        
        txA8OstARackTable OBJECT-TYPE
            SYNTAX SEQUENCE OF TxA8OstARackEntry
            MAX-ACCESS not-accessible
            STATUS current
            DESCRIPTION
                "The table of racks."
            ::= { outputstageATxA8 1 }

        
        txA8OstARackEntry OBJECT-TYPE
            SYNTAX TxA8OstARackEntry
            MAX-ACCESS not-accessible
            STATUS current
            DESCRIPTION
                "A row (an entry) for one rack."
            INDEX { txA8OstARackIdx }
            ::= { txA8OstARackTable 1 }

        
        TxA8OstARackEntry ::=
            SEQUENCE { 
                txA8OstARackIdx
                    IndexRack,
                txA8OstARackInletTemperature
                    FloatingPoint,
                txA8OstARackOutletTemperature
                    FloatingPoint,
                txA8OstARackAuxPowerSupply
                    FloatingPoint
             }

        txA8OstARackIdx OBJECT-TYPE
            SYNTAX IndexRack
            MAX-ACCESS not-accessible
            STATUS current
            DESCRIPTION
                "The rack number (1..10)."
            ::= { txA8OstARackEntry 1 }

        
        txA8OstARackInletTemperature OBJECT-TYPE
            SYNTAX FloatingPoint
            UNITS "Degree Celsius"
            MAX-ACCESS read-only
            STATUS current
            DESCRIPTION
                "The inlet temperature."
            ::= { txA8OstARackEntry 2 }

        
        txA8OstARackOutletTemperature OBJECT-TYPE
            SYNTAX FloatingPoint
            UNITS "Degree Celsius"
            MAX-ACCESS read-only
            STATUS current
            DESCRIPTION
                "The outlet temperature."
            ::= { txA8OstARackEntry 3 }

        
        txA8OstARackAuxPowerSupply OBJECT-TYPE
            SYNTAX FloatingPoint
            UNITS "Volt"
            MAX-ACCESS read-only
            STATUS current
            DESCRIPTION
                "Control voltage of auxiliary power supply of the designated rack.
                The value should be between 11.1 to 13.2 V."
            ::= { txA8OstARackEntry 4 }

        
        productInfoTable OBJECT-TYPE
            SYNTAX SEQUENCE OF ProductInfoEntry
            MAX-ACCESS not-accessible
            STATUS current
            DESCRIPTION
                "The table for product typeplates."
            ::= { transmitter 100 }

        
        productInfoEntry OBJECT-TYPE
            SYNTAX ProductInfoEntry
            MAX-ACCESS not-accessible
            STATUS current
            DESCRIPTION
                "A row (an entry) for one typeplate."
            INDEX { prodInfoModuleIdx, prodInfoTxIdx, prodInfoDeviceIdx, prodInfoRackIdx, prodInfoAmpIdx
                 }
            ::= { productInfoTable 1 }

        
        ProductInfoEntry ::=
            SEQUENCE { 
                prodInfoModuleIdx
                    ProdInfoModuleNameFm,
                prodInfoTxIdx
                    IndexTransmitter,
                prodInfoDeviceIdx
                    IndexAB,
                prodInfoRackIdx
                    IndexRack,
                prodInfoAmpIdx
                    IndexAmplifier,
                prodInfoModuleName
                    ProdInfoModuleNameFm,
                prodInfoSerialNumber
                    ReadableString,
                prodInfoIdentNumberSW
                    ReadableString,
                prodInfoVersionNumberSW
                    ReadableString,
                prodInfoIdentNumberHW
                    ReadableString,
                prodInfoVersionNumberHW
                    ReadableString,
                productInfoProductDateHW
                    DateAndTime
             }

        prodInfoModuleIdx OBJECT-TYPE
            SYNTAX ProdInfoModuleNameFm
            MAX-ACCESS not-accessible
            STATUS current
            DESCRIPTION
                "The module index."
            ::= { productInfoEntry 1 }

        
        prodInfoTxIdx OBJECT-TYPE
            SYNTAX IndexTransmitter
            MAX-ACCESS not-accessible
            STATUS current
            DESCRIPTION
                "The transmitter index. There are max. 8 main transmitters (transmitterA), if you have an 8+1 system
                and the reserve transmitter (transmitterB(1))."
            ::= { productInfoEntry 2 }

        
        prodInfoDeviceIdx OBJECT-TYPE
            SYNTAX IndexAB
            MAX-ACCESS not-accessible
            STATUS current
            DESCRIPTION
                "The dedicated device (A/B)."
            ::= { productInfoEntry 3 }

        
        prodInfoRackIdx OBJECT-TYPE
            SYNTAX IndexRack
            MAX-ACCESS not-accessible
            STATUS current
            DESCRIPTION
                "The rack number (1..10)."
            ::= { productInfoEntry 4 }

        
        prodInfoAmpIdx OBJECT-TYPE
            SYNTAX IndexAmplifier
            MAX-ACCESS not-accessible
            STATUS current
            DESCRIPTION
                "Amplifier Index"
            ::= { productInfoEntry 5 }

        
        prodInfoModuleName OBJECT-TYPE
            SYNTAX ProdInfoModuleNameFm
            MAX-ACCESS read-only
            STATUS current
            DESCRIPTION
                "The name of the module as a text."
            ::= { productInfoEntry 6 }

        
        prodInfoSerialNumber OBJECT-TYPE
            SYNTAX ReadableString
            MAX-ACCESS read-only
            STATUS current
            DESCRIPTION
                "The serial number of the subdevice."
            ::= { productInfoEntry 7 }

        
        prodInfoIdentNumberSW OBJECT-TYPE
            SYNTAX ReadableString
            MAX-ACCESS read-only
            STATUS current
            DESCRIPTION
                "The Rohde&Schwarz identification number of the software, for example 2094.2090.02."
            ::= { productInfoEntry 8 }

        
        prodInfoVersionNumberSW OBJECT-TYPE
            SYNTAX ReadableString
            MAX-ACCESS read-only
            STATUS current
            DESCRIPTION
                "The Rohde&Schwarz revision number of the software, for example 1.2.1."
            ::= { productInfoEntry 9 }

        
        prodInfoIdentNumberHW OBJECT-TYPE
            SYNTAX ReadableString
            MAX-ACCESS read-only
            STATUS current
            DESCRIPTION
                "The Rohde&Schwarz identification number of the hardware, for example 2095.8007.02 (NetCCU)."
            ::= { productInfoEntry 10 }

        
        prodInfoVersionNumberHW OBJECT-TYPE
            SYNTAX ReadableString
            MAX-ACCESS read-only
            STATUS current
            DESCRIPTION
                "The Rohde&Schwarz revision number (product index) of the hardware, for example 03.03."
            ::= { productInfoEntry 11 }

        
        productInfoProductDateHW OBJECT-TYPE
            SYNTAX DateAndTime
            MAX-ACCESS read-only
            STATUS current
            DESCRIPTION
                "The Rohde&Schwarz production date of the hardware,"
            ::= { productInfoEntry 12 }

        
-- *****************************************************************************
-- **          event definitions
-- *****************************************************************************
        rsXx8000FmNp1Events OBJECT IDENTIFIER ::= { rsXx8000FmNp1 3 }

        
-- *****************************************************************************
-- **          events NetCCU switchoverunit
-- *****************************************************************************
        eventNsu OBJECT IDENTIFIER ::= { rsXx8000FmNp1Events 1 }

        
        eventsNsuV2 OBJECT-IDENTITY
            STATUS current
            DESCRIPTION 
                "Compatibility to SMIv1."
            ::= { eventNsu 0 }

        
        nsuSummaryFault NOTIFICATION-TYPE
            OBJECTS { eventAlarmPriority, eventAlarmClass, eventEvent }
            STATUS current
            DESCRIPTION 
                "NetCCUSwitchoverUnit Summary Fault"
            ::= { eventsNsuV2 1 }

        
        nsuSummaryWarning NOTIFICATION-TYPE
            OBJECTS { eventAlarmPriority, eventAlarmClass, eventEvent }
            STATUS current
            DESCRIPTION 
                "NetCCUSwitchoverUnit Summary Warning"
            ::= { eventsNsuV2 2 }

        
        nsuLocal NOTIFICATION-TYPE
            OBJECTS { eventAlarmPriority, eventAlarmClass, eventEvent }
            STATUS current
            DESCRIPTION 
                "NetCCUSwitchoverUnit Local/Remote"
            ::= { eventsNsuV2 3 }

        
        nsuAutomaticReady NOTIFICATION-TYPE
            OBJECTS { eventAlarmPriority, eventAlarmClass, eventEvent }
            STATUS current
            DESCRIPTION 
                "NetCCUSwitchoverUnit Automatic Ready"
            ::= { eventsNsuV2 4 }

        
        nsuAutomaticChanged NOTIFICATION-TYPE
            OBJECTS { eventAlarmPriority, eventAlarmClass, eventEvent, loadedTx }
            STATUS current
            DESCRIPTION 
                "NetCCUSwitchoverUnit Automatic Changed"
            ::= { eventsNsuV2 5 }

        
        nsuFanWarning NOTIFICATION-TYPE
            OBJECTS { eventAlarmPriority, eventAlarmClass, eventEvent }
            STATUS current
            DESCRIPTION 
                "NetCCUSwitchoverUnit Fan Warning"
            ::= { eventsNsuV2 6 }

        
        nsuBoardTemperatureFault NOTIFICATION-TYPE
            OBJECTS { eventAlarmPriority, eventAlarmClass, eventEvent }
            STATUS deprecated
            DESCRIPTION 
                "NetCCUSwitchoverUnit Mainboard Temperature Fault
                
                deprecated: this information is now handled as a warning
                (nsuBoardTemperatureWarning)"
            ::= { eventsNsuV2 7 }

        
        nsuPowerSupply NOTIFICATION-TYPE
            OBJECTS { eventAlarmPriority, eventAlarmClass, eventEvent }
            STATUS current
            DESCRIPTION 
                "NetCCUSwitchoverUnit Power Supply"
            ::= { eventsNsuV2 8 }

        
        nsuAutomaticFault NOTIFICATION-TYPE
            OBJECTS { eventAlarmPriority, eventAlarmClass, eventEvent }
            STATUS current
            DESCRIPTION 
                "NetCCUSwitchoverUnit Automatic Fault"
            ::= { eventsNsuV2 9 }

        
        nsuInputSwitcherFault NOTIFICATION-TYPE
            OBJECTS { eventAlarmPriority, eventAlarmClass, eventEvent }
            STATUS current
            DESCRIPTION 
                "NetCCUSwitchoverUnit Fault Of Input Switcher"
            ::= { eventsNsuV2 10 }

        
        nsuInternalPowerSupplyWarning NOTIFICATION-TYPE
            OBJECTS { eventAlarmPriority, eventAlarmClass, eventEvent }
            STATUS current
            DESCRIPTION 
                "NetCCU internal Power Supply warning"
            ::= { eventsNsuV2 11 }

        
        nsuExternalPowerSupplyWarning NOTIFICATION-TYPE
            OBJECTS { eventAlarmPriority, eventAlarmClass, eventEvent }
            STATUS current
            DESCRIPTION 
                "NetCCU external Power Supply warning"
            ::= { eventsNsuV2 12 }

        
        nsuBoardTemperatureWarning NOTIFICATION-TYPE
            OBJECTS { eventAlarmPriority, eventAlarmClass, eventEvent }
            STATUS current
            DESCRIPTION 
                "NetCCU Mainboard Temperature Warning"
            ::= { eventsNsuV2 13 }

        
        eventsNsuTable OBJECT-TYPE
            SYNTAX SEQUENCE OF EventsNsuEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventNsu 1 }

        
        eventsNsuEntry OBJECT-TYPE
            SYNTAX EventsNsuEntry
            MAX-ACCESS not-accessible
            STATUS current
            DESCRIPTION
                "An event entry always consists of 4 values:
                - name: an enumerated list of all possible notifications
                - mask: the corresponding mask (enable/disable)
                - priority: the corresponding priority (value in range 0..255)
                - event: the event itself (active/inactive)"
            INDEX { eventNsuIdx }
            ::= { eventsNsuTable 1 }

        
        EventsNsuEntry ::=
            SEQUENCE { 
                eventNsuIdx
                    EventMaxEntryNumber,
                eventNsuName
                    INTEGER,
                eventNsuMask
                    EventMask,
                eventNsuPriority
                    EventPriority,
                eventNsuEvent
                    EventState
             }

        eventNsuIdx OBJECT-TYPE
            SYNTAX EventMaxEntryNumber
            MAX-ACCESS not-accessible
            STATUS current
            DESCRIPTION
                "The event number as integer."
            ::= { eventsNsuEntry 1 }

        
        eventNsuName OBJECT-TYPE
            SYNTAX INTEGER
                {
                nsuSummaryFault(1),
                nsuSummaryWarning(2),
                nsuLocal(3),
                nsuAutomaticReady(4),
                nsuAutomaticChanged(5),
                nsuFanWarning(6),
                nsuBoardTemperatureFault(7),
                nsuPowerSupply(8),
                nsuAutomaticFault(9),
                nsuInputSwitcherFault(10),
                nsuInternalPowerSupplyWarning(11),
                nsuExternalPowerSupplyWarning(12),
                nsuBoardTemperatureWarning(13)
                }
            MAX-ACCESS read-only
            STATUS current
            DESCRIPTION
                "The event number as integer and the value as readable text."
            ::= { eventsNsuEntry 2 }

        
        eventNsuMask OBJECT-TYPE
            SYNTAX EventMask
            MAX-ACCESS read-write
            STATUS current
            DESCRIPTION
                "See TextualConvention for details."
            ::= { eventsNsuEntry 3 }

        
        eventNsuPriority OBJECT-TYPE
            SYNTAX EventPriority
            MAX-ACCESS read-write
            STATUS current
            DESCRIPTION
                "See TextualConvention for details."
            ::= { eventsNsuEntry 4 }

        
        eventNsuEvent OBJECT-TYPE
            SYNTAX EventState
            MAX-ACCESS read-only
            STATUS current
            DESCRIPTION
                "See TextualConvention for details."
            ::= { eventsNsuEntry 5 }

        
-- *****************************************************************************
-- **          events transmitter
-- *****************************************************************************
        eventTx OBJECT IDENTIFIER ::= { rsXx8000FmNp1Events 2 }

        
        eventsTxV2 OBJECT-IDENTITY
            STATUS current
            DESCRIPTION 
                "Compatibility to SMIv1."
            ::= { eventTx 0 }

        
        txSummaryFault NOTIFICATION-TYPE
            OBJECTS { eventAlarmPriority, eventAlarmClass, eventEvent, indexTransmitter }
            STATUS current
            DESCRIPTION 
                "Transmitter Summary Fault"
            ::= { eventsTxV2 1 }

        
        txSummaryWarning NOTIFICATION-TYPE
            OBJECTS { eventAlarmPriority, eventAlarmClass, eventEvent, indexTransmitter }
            STATUS current
            DESCRIPTION 
                "Transmitter Summary Warning"
            ::= { eventsTxV2 2 }

        
        txLocal NOTIFICATION-TYPE
            OBJECTS { eventAlarmPriority, eventAlarmClass, eventEvent, indexTransmitter }
            STATUS current
            DESCRIPTION 
                "Transmitter Local/Remote"
            ::= { eventsTxV2 3 }

        
        txRfOn NOTIFICATION-TYPE
            OBJECTS { eventAlarmPriority, eventAlarmClass, eventEvent, indexTransmitter }
            STATUS current
            DESCRIPTION 
                "Transmitter RF On/Off"
            ::= { eventsTxV2 4 }

        
        txRfOk NOTIFICATION-TYPE
            OBJECTS { eventAlarmPriority, eventAlarmClass, eventEvent, indexTransmitter }
            STATUS current
            DESCRIPTION 
                "Transmitter RF Ok / Not OK"
            ::= { eventsTxV2 5 }

        
        txParamSetSubDeviceDiffers NOTIFICATION-TYPE
            OBJECTS { eventAlarmPriority, eventAlarmClass, eventEvent, indexTransmitter }
            STATUS obsolete
            DESCRIPTION 
                "Parameterset of subdevice is different.
                The currently loaded parameterset is inconsistent because
                a subdevice (e.g. an exciter) has a different configuration than expected.
                To correct this, save settings to the current or save a complete new."
            ::= { eventsTxV2 6 }

        
        txParamSetValuesChanged NOTIFICATION-TYPE
            OBJECTS { eventAlarmPriority, eventAlarmClass, eventEvent, indexTransmitter }
            STATUS current
            DESCRIPTION 
                "Value Of Current Parameterset Changed.
                The currently loaded parameterset is inconsistent because
                there were changes happening since the load/save of it.
                To correct this, save settings to the current or save a complete new."
            ::= { eventsTxV2 7 }

        
        txRfLoopProgram NOTIFICATION-TYPE
            OBJECTS { eventAlarmPriority, eventAlarmClass, eventEvent, indexTransmitter }
            STATUS current
            DESCRIPTION 
                "NetCCU Loop Program"
            ::= { eventsTxV2 8 }

        
        txRfLoopReserve NOTIFICATION-TYPE
            OBJECTS { eventAlarmPriority, eventAlarmClass, eventEvent, indexTransmitter }
            STATUS current
            DESCRIPTION 
                "NetCCU Loop Reserve"
            ::= { eventsTxV2 9 }

        
        txRfWarning NOTIFICATION-TYPE
            OBJECTS { eventAlarmPriority, eventAlarmClass, eventEvent, indexTransmitter }
            STATUS current
            DESCRIPTION 
                "NetCCU RF Warning"
            ::= { eventsTxV2 10 }

        
        txReflectionWarning NOTIFICATION-TYPE
            OBJECTS { eventAlarmPriority, eventAlarmClass, eventEvent, indexTransmitter }
            STATUS current
            DESCRIPTION 
                "NetCCU Reflection Warning"
            ::= { eventsTxV2 11 }

        
        txNetCCUFanFault NOTIFICATION-TYPE
            OBJECTS { eventAlarmPriority, eventAlarmClass, eventEvent, indexTransmitter }
            STATUS current
            DESCRIPTION 
                "NetCCU Fan Fault.
                This is valid, if Fan Control is switched on (see menu NetCCU Setup - Common)."
            ::= { eventsTxV2 12 }

        
        txNetCCUPowerSupply NOTIFICATION-TYPE
            OBJECTS { eventAlarmPriority, eventAlarmClass, eventEvent, indexTransmitter }
            STATUS current
            DESCRIPTION 
                "NetCCU Power Supply"
            ::= { eventsTxV2 13 }

        
        txRfFail NOTIFICATION-TYPE
            OBJECTS { eventAlarmPriority, eventAlarmClass, eventEvent }
            STATUS current
            DESCRIPTION 
                "NetCCU RF Fail"
            ::= { eventsTxV2 14 }

        
        txReflectionFault NOTIFICATION-TYPE
            OBJECTS { eventAlarmPriority, eventAlarmClass, eventEvent, indexTransmitter }
            STATUS current
            DESCRIPTION 
                "NetCCU Reflection Fault"
            ::= { eventsTxV2 15 }

        
        txNetCCUBoardTemperatureFault NOTIFICATION-TYPE
            OBJECTS { eventAlarmPriority, eventAlarmClass, eventEvent, indexTransmitter }
            STATUS deprecated
            DESCRIPTION 
                "NetCCU Board Temperature Fault
                
                deprecated: this information is now handled as a warning
                (txNetCCUBoardTemperatureWarning)"
            ::= { eventsTxV2 16 }

        
        txNetCCUNoConnectionToExcA NOTIFICATION-TYPE
            OBJECTS { eventAlarmPriority, eventAlarmClass, eventEvent, indexTransmitter }
            STATUS current
            DESCRIPTION 
                "NetCCU Connection To ExciterA Faulty"
            ::= { eventsTxV2 17 }

        
        txNetCCUNoConnectionToOstA NOTIFICATION-TYPE
            OBJECTS { eventAlarmPriority, eventAlarmClass, eventEvent, indexTransmitter }
            STATUS current
            DESCRIPTION 
                "NetCCU Connection To OutputstageA Faulty"
            ::= { eventsTxV2 18 }

        
        txNetCCUNoConnectionToExcB NOTIFICATION-TYPE
            OBJECTS { eventAlarmPriority, eventAlarmClass, eventEvent, indexTransmitter }
            STATUS current
            DESCRIPTION 
                "NetCCU Connection To ExciterB Faulty"
            ::= { eventsTxV2 19 }

        
        txAutomaticExcReady NOTIFICATION-TYPE
            OBJECTS { eventAlarmPriority, eventAlarmClass, eventEvent, indexTransmitter }
            STATUS current
            DESCRIPTION 
                "Exciter Automatic Ready."
            ::= { eventsTxV2 21 }

        
        txAutomaticExcChanged NOTIFICATION-TYPE
            OBJECTS { eventAlarmPriority, eventAlarmClass, eventEvent, indexTransmitter }
            STATUS current
            DESCRIPTION 
                "Exciter Automatic Changed."
            ::= { eventsTxV2 22 }

        
        txAutomaticExcFault NOTIFICATION-TYPE
            OBJECTS { eventAlarmPriority, eventAlarmClass, eventEvent, indexTransmitter }
            STATUS current
            DESCRIPTION 
                "Exciter Automatic Fault."
            ::= { eventsTxV2 23 }

        
        txNetCCUBoardTemperatureWarning NOTIFICATION-TYPE
            OBJECTS { eventAlarmPriority, eventAlarmClass, eventEvent, indexTransmitter }
            STATUS current
            DESCRIPTION 
                "NetCCU Board Temperature Warning"
            ::= { eventsTxV2 27 }

        
        txInternalPowerSupplyWarning NOTIFICATION-TYPE
            OBJECTS { eventAlarmPriority, eventAlarmClass, eventEvent, indexTransmitter }
            STATUS current
            DESCRIPTION 
                "NetCCU internal Power Supply warning"
            ::= { eventsTxV2 30 }

        
        txExternalPowerSupplyWarning NOTIFICATION-TYPE
            OBJECTS { eventAlarmPriority, eventAlarmClass, eventEvent, indexTransmitter }
            STATUS current
            DESCRIPTION 
                "NetCCU external (additional) Power Supply warning"
            ::= { eventsTxV2 31 }

        
        txNoConnection NOTIFICATION-TYPE
            OBJECTS { eventAlarmPriority, eventAlarmClass, eventEvent, indexTransmitter }
            STATUS current
            DESCRIPTION 
                "NSU connection to NetCCU faulty."
            ::= { eventsTxV2 32 }

        
        txExcSummaryFault NOTIFICATION-TYPE
            OBJECTS { eventAlarmPriority, eventAlarmClass, eventEvent, indexTransmitter, indexAB
                 }
            STATUS current
            DESCRIPTION 
                "Exciter Summary Fault"
            ::= { eventsTxV2 100 }

        
        txExcSummaryWarning NOTIFICATION-TYPE
            OBJECTS { eventAlarmPriority, eventAlarmClass, eventEvent, indexTransmitter, indexAB
                 }
            STATUS current
            DESCRIPTION 
                "Exciter Summary Warning"
            ::= { eventsTxV2 101 }

        
        txExcOn NOTIFICATION-TYPE
            OBJECTS { eventAlarmPriority, eventAlarmClass, eventEvent, indexTransmitter, indexAB
                 }
            STATUS current
            DESCRIPTION 
                "Exciter On"
            ::= { eventsTxV2 102 }

        
        txExcRfOn NOTIFICATION-TYPE
            OBJECTS { eventAlarmPriority, eventAlarmClass, eventEvent, indexTransmitter, indexAB
                 }
            STATUS current
            DESCRIPTION 
                "Exciter RF On"
            ::= { eventsTxV2 103 }

        
        txExcNoInput NOTIFICATION-TYPE
            OBJECTS { eventAlarmPriority, eventAlarmClass, eventEvent, indexTransmitter, indexAB
                 }
            STATUS current
            DESCRIPTION 
                "Exciter has no valid input signal."
            ::= { eventsTxV2 104 }

        
        txExcRfLoop NOTIFICATION-TYPE
            OBJECTS { eventAlarmPriority, eventAlarmClass, eventEvent, indexTransmitter, indexAB
                 }
            STATUS current
            DESCRIPTION 
                "Exciter RF loop"
            ::= { eventsTxV2 105 }

        
        txExcRfFail NOTIFICATION-TYPE
            OBJECTS { eventAlarmPriority, eventAlarmClass, eventEvent, indexTransmitter, indexAB
                 }
            STATUS current
            DESCRIPTION 
                "Exciter RF Fail"
            ::= { eventsTxV2 106 }

        
        txExcOutputOpen NOTIFICATION-TYPE
            OBJECTS { eventAlarmPriority, eventAlarmClass, eventEvent, indexTransmitter, indexAB
                 }
            STATUS current
            DESCRIPTION 
                "Exciter output open"
            ::= { eventsTxV2 107 }

        
        txExcBoardTemperatureWarning NOTIFICATION-TYPE
            OBJECTS { eventAlarmPriority, eventAlarmClass, eventEvent, indexTransmitter, indexAB
                 }
            STATUS current
            DESCRIPTION 
                "Exciter Board Temperature Warning"
            ::= { eventsTxV2 108 }

        
        txExcBoardTemperatureFailure NOTIFICATION-TYPE
            OBJECTS { eventAlarmPriority, eventAlarmClass, eventEvent, indexTransmitter, indexAB
                 }
            STATUS current
            DESCRIPTION 
                "Exciter Board Temperature Failure"
            ::= { eventsTxV2 109 }

        
        txExcMute NOTIFICATION-TYPE
            OBJECTS { eventAlarmPriority, eventAlarmClass, eventEvent, indexTransmitter, indexAB
                 }
            STATUS current
            DESCRIPTION 
                "Exciter Mute"
            ::= { eventsTxV2 110 }

        
        txExcCh1NotOK NOTIFICATION-TYPE
            OBJECTS { eventAlarmPriority, eventAlarmClass, eventEvent, indexTransmitter, indexAB
                 }
            STATUS current
            DESCRIPTION 
                "Exciter Channel1"
            ::= { eventsTxV2 111 }

        
        txExcCh2NotOK NOTIFICATION-TYPE
            OBJECTS { eventAlarmPriority, eventAlarmClass, eventEvent, indexTransmitter, indexAB
                 }
            STATUS current
            DESCRIPTION 
                "Exciter Channel2"
            ::= { eventsTxV2 112 }

        
        txExcCh1Selected NOTIFICATION-TYPE
            OBJECTS { eventAlarmPriority, eventAlarmClass, eventEvent, indexTransmitter, indexAB
                 }
            STATUS current
            DESCRIPTION 
                "Exciter selected Channel1"
            ::= { eventsTxV2 113 }

        
        txExcCh2Selected NOTIFICATION-TYPE
            OBJECTS { eventAlarmPriority, eventAlarmClass, eventEvent, indexTransmitter, indexAB
                 }
            STATUS current
            DESCRIPTION 
                "Exciter selected Channel2"
            ::= { eventsTxV2 114 }

        
        txExcSelAudioInpError NOTIFICATION-TYPE
            OBJECTS { eventAlarmPriority, eventAlarmClass, eventEvent, indexTransmitter, indexAB
                 }
            STATUS current
            DESCRIPTION 
                "Exciter selected audio input error"
            ::= { eventsTxV2 115 }

        
        txExcDataInputNotOK NOTIFICATION-TYPE
            OBJECTS { eventAlarmPriority, eventAlarmClass, eventEvent, indexTransmitter, indexAB
                 }
            STATUS current
            DESCRIPTION 
                "This is a sum warning for all data inputs. When active, 
                data (auxiliary) inputs will be monitored with this LED."
            ::= { eventsTxV2 116 }

        
        txExcFan1NotOk NOTIFICATION-TYPE
            OBJECTS { eventAlarmPriority, eventAlarmClass, eventEvent, indexTransmitter, indexAB
                 }
            STATUS current
            DESCRIPTION 
                "Indicates the state of Fan1. If yellow the fan should be replaced."
            ::= { eventsTxV2 117 }

        
        txExcFan2NotOk NOTIFICATION-TYPE
            OBJECTS { eventAlarmPriority, eventAlarmClass, eventEvent, indexTransmitter, indexAB
                 }
            STATUS current
            DESCRIPTION 
                "Indicates the state of Fan2. If yellow the fan sould be replaced."
            ::= { eventsTxV2 118 }

        
        txExcFanSupplyNotOk NOTIFICATION-TYPE
            OBJECTS { eventAlarmPriority, eventAlarmClass, eventEvent, indexTransmitter, indexAB
                 }
            STATUS current
            DESCRIPTION 
                "Shows the state of the supply for the fans."
            ::= { eventsTxV2 119 }

        
        txExcHWError NOTIFICATION-TYPE
            OBJECTS { eventAlarmPriority, eventAlarmClass, eventEvent, indexTransmitter, indexAB
                 }
            STATUS current
            DESCRIPTION 
                "If the LED is red a hardware error is occurred and the device must be replaced.
                For detailed information please refer to the logbook and the 'Mainboard' sub-menu."
            ::= { eventsTxV2 120 }

        
        txExcRackControlSupplyNotOk NOTIFICATION-TYPE
            OBJECTS { eventAlarmPriority, eventAlarmClass, eventEvent, indexTransmitter, indexAB
                 }
            STATUS current
            DESCRIPTION 
                "Shows the state of the auxiliary supply for the rack controller. 
                On failure, check if there is a short circuit between Pin1 and Pin9 
                on X6-B ('TX' connector to the rack controller)."
            ::= { eventsTxV2 121 }

        
        txExcExtRefNotOK NOTIFICATION-TYPE
            OBJECTS { eventAlarmPriority, eventAlarmClass, eventEvent, indexTransmitter, indexAB
                 }
            STATUS current
            DESCRIPTION 
                "Indicates the state of the external reference 
                (either PPS or 10MHz, depending on selection)."
            ::= { eventsTxV2 122 }

        
        txExcExtRefNotLocked NOTIFICATION-TYPE
            OBJECTS { eventAlarmPriority, eventAlarmClass, eventEvent, indexTransmitter, indexAB
                 }
            STATUS current
            DESCRIPTION 
                "Indicates the state of the external reference 
                (either PPS or 10MHz, depending on selection)."
            ::= { eventsTxV2 123 }

        
        txLpRfWarning NOTIFICATION-TYPE
            OBJECTS { eventAlarmPriority, eventAlarmClass, eventEvent, indexTransmitter, indexAB
                 }
            STATUS current
            DESCRIPTION 
                "FM Low Power RF Warning.
                For FM Low Power only."
            ::= { eventsTxV2 140 }

        
        txLpFanHealth NOTIFICATION-TYPE
            OBJECTS { eventAlarmPriority, eventAlarmClass, eventEvent, indexTransmitter, indexAB
                 }
            STATUS current
            DESCRIPTION 
                "Fan Health/Fault.
                It is valid if Fan isn't reduced or fail."
            ::= { eventsTxV2 141 }

        
        txLpOstVswrPwrRegulationWarning NOTIFICATION-TYPE
            OBJECTS { eventAlarmPriority, eventAlarmClass, eventEvent, indexTransmitter }
            STATUS current
            DESCRIPTION 
                "Indicates whether the output power is currently reduced or switched off due to high VSWR."
            ::= { eventsTxV2 150 }

        
        txLpOstVswrPwrRegulationFault NOTIFICATION-TYPE
            OBJECTS { eventAlarmPriority, eventAlarmClass, eventEvent, indexTransmitter }
            STATUS current
            DESCRIPTION 
                "Indicates whether the output power is currently switched off due to high VSWR."
            ::= { eventsTxV2 151 }

        
        txLpOstTempRegulationWarning NOTIFICATION-TYPE
            OBJECTS { eventAlarmPriority, eventAlarmClass, eventEvent, indexTransmitter }
            STATUS current
            DESCRIPTION 
                "Indicates whether the output power is currently reduced due to high amplifier temperature."
            ::= { eventsTxV2 152 }

        
        txOstSummaryFault NOTIFICATION-TYPE
            OBJECTS { eventAlarmPriority, eventAlarmClass, eventEvent, indexTransmitter, indexAB
                 }
            STATUS current
            DESCRIPTION 
                "Outputstage Summary Fault"
            ::= { eventsTxV2 200 }

        
        txOstSummaryWarning NOTIFICATION-TYPE
            OBJECTS { eventAlarmPriority, eventAlarmClass, eventEvent, indexTransmitter, indexAB
                 }
            STATUS current
            DESCRIPTION 
                "Outputstage Summary Warning"
            ::= { eventsTxV2 201 }

        
        txOstRfOn NOTIFICATION-TYPE
            OBJECTS { eventAlarmPriority, eventAlarmClass, eventEvent, indexTransmitter, indexAB
                 }
            STATUS current
            DESCRIPTION 
                "Outputstage RF On"
            ::= { eventsTxV2 202 }

        
        txOstRfOk NOTIFICATION-TYPE
            OBJECTS { eventAlarmPriority, eventAlarmClass, eventEvent, indexTransmitter, indexAB
                 }
            STATUS current
            DESCRIPTION 
                "Outputstage RF Ok"
            ::= { eventsTxV2 203 }

        
        txOstNoInput NOTIFICATION-TYPE
            OBJECTS { eventAlarmPriority, eventAlarmClass, eventEvent, indexTransmitter, indexAB
                 }
            STATUS current
            DESCRIPTION 
                "Outputstage no input signal"
            ::= { eventsTxV2 204 }

        
        txOstRfWarning NOTIFICATION-TYPE
            OBJECTS { eventAlarmPriority, eventAlarmClass, eventEvent, indexTransmitter, indexAB
                 }
            STATUS current
            DESCRIPTION 
                "Outputstage RF Warning"
            ::= { eventsTxV2 205 }

        
        txOstReflectionWarning NOTIFICATION-TYPE
            OBJECTS { eventAlarmPriority, eventAlarmClass, eventEvent, indexTransmitter, indexAB
                 }
            STATUS current
            DESCRIPTION 
                "Outputstage Reflection Warning"
            ::= { eventsTxV2 206 }

        
        txOstRackWarning NOTIFICATION-TYPE
            OBJECTS { eventAlarmPriority, eventAlarmClass, eventEvent, indexTransmitter, indexAB
                 }
            STATUS current
            DESCRIPTION 
                "Outputstage Rack Warning. At least one rack has an error pending."
            ::= { eventsTxV2 207 }

        
        txOstCoolingWarning NOTIFICATION-TYPE
            OBJECTS { eventAlarmPriority, eventAlarmClass, eventEvent, indexTransmitter, indexAB
                 }
            STATUS current
            DESCRIPTION 
                "Outputstage Cooling Warning"
            ::= { eventsTxV2 208 }

        
        txOstRfFail NOTIFICATION-TYPE
            OBJECTS { eventAlarmPriority, eventAlarmClass, eventEvent, indexTransmitter, indexAB
                 }
            STATUS current
            DESCRIPTION 
                "Outputstage RF Fail"
            ::= { eventsTxV2 209 }

        
        txOstReflectionFault NOTIFICATION-TYPE
            OBJECTS { eventAlarmPriority, eventAlarmClass, eventEvent, indexTransmitter, indexAB
                 }
            STATUS current
            DESCRIPTION 
                "Outputstage Reflection Fault"
            ::= { eventsTxV2 210 }

        
        txOstACFault NOTIFICATION-TYPE
            OBJECTS { eventAlarmPriority, eventAlarmClass, eventEvent, indexTransmitter, indexAB
                 }
            STATUS current
            DESCRIPTION 
                "Outputstage AC Fault"
            ::= { eventsTxV2 211 }

        
        txOstCoolingFault NOTIFICATION-TYPE
            OBJECTS { eventAlarmPriority, eventAlarmClass, eventEvent, indexTransmitter, indexAB
                 }
            STATUS current
            DESCRIPTION 
                "Outputstage Cooling Fault"
            ::= { eventsTxV2 212 }

        
        txOstCommFault NOTIFICATION-TYPE
            OBJECTS { eventAlarmPriority, eventAlarmClass, eventEvent, indexTransmitter, indexAB
                 }
            STATUS current
            DESCRIPTION 
                "Outputstage Communication Fault"
            ::= { eventsTxV2 213 }

        
        txRackSumFault NOTIFICATION-TYPE
            OBJECTS { eventAlarmPriority, eventAlarmClass, eventEvent, indexTransmitter, indexAB, 
                indexRack }
            STATUS current
            DESCRIPTION 
                "Summary Fault at a designated rack.
                This event automatically leads to txOstRackWarning."
            ::= { eventsTxV2 300 }

        
        txRackSumWarning NOTIFICATION-TYPE
            OBJECTS { eventAlarmPriority, eventAlarmClass, eventEvent, indexTransmitter, indexAB, 
                indexRack }
            STATUS current
            DESCRIPTION 
                "Summary Warning at a designated rack."
            ::= { eventsTxV2 301 }

        
        txRackOn NOTIFICATION-TYPE
            OBJECTS { eventAlarmPriority, eventAlarmClass, eventEvent, indexTransmitter, indexAB, 
                indexRack }
            STATUS current
            DESCRIPTION 
                "The designated racks operation mode is on."
            ::= { eventsTxV2 302 }

        
        txRackGpiWarning NOTIFICATION-TYPE
            OBJECTS { eventAlarmPriority, eventAlarmClass, eventEvent, indexTransmitter, indexAB, 
                indexRack }
            STATUS current
            DESCRIPTION 
                "A warning on the general purpose input occurred.
                This depends on the current configuration of the GPI. (See:Rack Setup/Rack Controller)"
            ::= { eventsTxV2 303 }

        
        txRackFan1Fault NOTIFICATION-TYPE
            OBJECTS { eventAlarmPriority, eventAlarmClass, eventEvent, indexTransmitter, indexAB, 
                indexRack }
            STATUS current
            DESCRIPTION 
                "The designated rack signals a fault of fan 1."
            ::= { eventsTxV2 304 }

        
        txRackFan2Fault NOTIFICATION-TYPE
            OBJECTS { eventAlarmPriority, eventAlarmClass, eventEvent, indexTransmitter, indexAB, 
                indexRack }
            STATUS current
            DESCRIPTION 
                "The designated rack signals a fault of fan 2."
            ::= { eventsTxV2 305 }

        
        txRackCoolingSumWarning NOTIFICATION-TYPE
            OBJECTS { eventAlarmPriority, eventAlarmClass, eventEvent, indexTransmitter, indexAB, 
                indexRack }
            STATUS current
            DESCRIPTION 
                "The designated rack signals a summary cooling warning."
            ::= { eventsTxV2 306 }

        
        txRackAmplifierSumFault NOTIFICATION-TYPE
            OBJECTS { eventAlarmPriority, eventAlarmClass, eventEvent, indexTransmitter, indexAB, 
                indexRack }
            STATUS current
            DESCRIPTION 
                "The designated rack signals at least one faulty amplifier."
            ::= { eventsTxV2 307 }

        
        txRackNoLink NOTIFICATION-TYPE
            OBJECTS { eventAlarmPriority, eventAlarmClass, eventEvent, indexTransmitter, indexAB, 
                indexRack }
            STATUS current
            DESCRIPTION 
                "No communication to the designated rack."
            ::= { eventsTxV2 308 }

        
        txRackGpiFault NOTIFICATION-TYPE
            OBJECTS { eventAlarmPriority, eventAlarmClass, eventEvent, indexTransmitter, indexAB, 
                indexRack }
            STATUS current
            DESCRIPTION 
                "A fault on the general purpose input occurred.
                This depends on the current configuration of the GPI. (See:Rack Setup/Rack Controller)"
            ::= { eventsTxV2 309 }

        
        txRackTemperatureFault NOTIFICATION-TYPE
            OBJECTS { eventAlarmPriority, eventAlarmClass, eventEvent, indexTransmitter, indexAB, 
                indexRack }
            STATUS current
            DESCRIPTION 
                "The designated rack signals a temperature fault - temperature too high."
            ::= { eventsTxV2 310 }

        
        txRackACFault NOTIFICATION-TYPE
            OBJECTS { eventAlarmPriority, eventAlarmClass, eventEvent, indexTransmitter, indexAB, 
                indexRack }
            STATUS current
            DESCRIPTION 
                "The designated rack signals an AC (phase) fault."
            ::= { eventsTxV2 311 }

        
        txRackCoolingSumFault NOTIFICATION-TYPE
            OBJECTS { eventAlarmPriority, eventAlarmClass, eventEvent, indexTransmitter, indexAB, 
                indexRack }
            STATUS current
            DESCRIPTION 
                "The designated rack signals a summary cooling fault."
            ::= { eventsTxV2 312 }

        
        txRackTempFaultAbs1 NOTIFICATION-TYPE
            OBJECTS { eventAlarmPriority, eventAlarmClass, eventEvent, indexTransmitter, indexAB, 
                indexRack }
            STATUS current
            DESCRIPTION 
                "The designated rack signals a temperature fault of absorber 1."
            ::= { eventsTxV2 313 }

        
        txRackTempFaultAbs2 NOTIFICATION-TYPE
            OBJECTS { eventAlarmPriority, eventAlarmClass, eventEvent, indexTransmitter, indexAB, 
                indexRack }
            STATUS current
            DESCRIPTION 
                "The designated rack signals a temperature fault of absorber 2."
            ::= { eventsTxV2 314 }

        
        txRackDCFault NOTIFICATION-TYPE
            OBJECTS { eventAlarmPriority, eventAlarmClass, eventEvent, indexTransmitter, indexAB, 
                indexRack }
            STATUS current
            DESCRIPTION 
                "The designated rack signals a DC fault."
            ::= { eventsTxV2 315 }

        
        txRackRfOn NOTIFICATION-TYPE
            OBJECTS { eventAlarmPriority, eventAlarmClass, eventEvent, indexAB, indexRack
                 }
            STATUS current
            DESCRIPTION 
                "RF power is on."
            ::= { eventsTxV2 318 }

        
        txRackRfOk NOTIFICATION-TYPE
            OBJECTS { eventAlarmPriority, eventAlarmClass, eventEvent, indexAB, indexRack
                 }
            STATUS current
            DESCRIPTION 
                "RF power is ok."
            ::= { eventsTxV2 319 }

        
        txRackRfWarning NOTIFICATION-TYPE
            OBJECTS { eventAlarmPriority, eventAlarmClass, eventEvent, indexTransmitter, indexAB, 
                indexRack }
            STATUS current
            DESCRIPTION 
                "RF power decreased the warning threshold."
            ::= { eventsTxV2 320 }

        
        txRackRfFault NOTIFICATION-TYPE
            OBJECTS { eventAlarmPriority, eventAlarmClass, eventEvent, indexTransmitter, indexAB, 
                indexRack }
            STATUS current
            DESCRIPTION 
                "RF output power decreased the fault threshold."
            ::= { eventsTxV2 321 }

        
        txRackReflectionWarning NOTIFICATION-TYPE
            OBJECTS { eventAlarmPriority, eventAlarmClass, eventEvent, indexTransmitter, indexAB, 
                indexRack }
            STATUS current
            DESCRIPTION 
                "The reflected power increased the warning threshold"
            ::= { eventsTxV2 322 }

        
        txRackReflectionFault NOTIFICATION-TYPE
            OBJECTS { eventAlarmPriority, eventAlarmClass, eventEvent, indexTransmitter, indexAB, 
                indexRack }
            STATUS current
            DESCRIPTION 
                "The reflected power increased the fault threshold."
            ::= { eventsTxV2 323 }

        
        txRackProbeNotCalibrated NOTIFICATION-TYPE
            OBJECTS { eventAlarmPriority, eventAlarmClass, eventEvent, indexTransmitter, indexAB, 
                indexRack }
            STATUS current
            DESCRIPTION 
                "At least one probe is not calibrated."
            ::= { eventsTxV2 330 }

        
        txRackTemperatureWarning NOTIFICATION-TYPE
            OBJECTS { eventAlarmPriority, eventAlarmClass, eventEvent, indexAB, indexRack
                 }
            STATUS current
            DESCRIPTION 
                "Rack temperature exceeded the warning threshold."
            ::= { eventsTxV2 331 }

        
        txRackOvervoltProtectWarning NOTIFICATION-TYPE
            OBJECTS { eventAlarmPriority, eventAlarmClass, eventEvent, indexAB, indexRack
                 }
            STATUS current
            DESCRIPTION 
                "Overvoltage protection is out of order."
            ::= { eventsTxV2 355 }

        
        txAmpSumFault NOTIFICATION-TYPE
            OBJECTS { eventAlarmPriority, eventAlarmClass, eventEvent, indexTransmitter, indexAB, 
                indexRack, indexAmplifier }
            STATUS current
            DESCRIPTION 
                "The designated amplifier signals summary fault."
            ::= { eventsTxV2 400 }

        
        txAmpSumWarning NOTIFICATION-TYPE
            OBJECTS { eventAlarmPriority, eventAlarmClass, eventEvent, indexTransmitter, indexAB, 
                indexRack, indexAmplifier }
            STATUS current
            DESCRIPTION 
                "The designated amplifier signals summary warning."
            ::= { eventsTxV2 401 }

        
        txAmpPowerOn NOTIFICATION-TYPE
            OBJECTS { eventAlarmPriority, eventAlarmClass, eventEvent, indexTransmitter, indexAB, 
                indexRack, indexAmplifier }
            STATUS current
            DESCRIPTION 
                "The designated amplifiers power is on."
            ::= { eventsTxV2 402 }

        
        txAmpDCOk NOTIFICATION-TYPE
            OBJECTS { eventAlarmPriority, eventAlarmClass, eventEvent, indexTransmitter, indexAB, 
                indexRack, indexAmplifier }
            STATUS current
            DESCRIPTION 
                "The designated amplifiers DC is ok."
            ::= { eventsTxV2 403 }

        
        txAmpACOk NOTIFICATION-TYPE
            OBJECTS { eventAlarmPriority, eventAlarmClass, eventEvent, indexTransmitter, indexAB, 
                indexRack, indexAmplifier }
            STATUS current
            DESCRIPTION 
                "The designated amplifiers AC is ok."
            ::= { eventsTxV2 404 }

        
        txAmpRfInFail NOTIFICATION-TYPE
            OBJECTS { eventAlarmPriority, eventAlarmClass, eventEvent, indexTransmitter, indexAB, 
                indexRack, indexAmplifier }
            STATUS current
            DESCRIPTION 
                "The designated amplifier signals RF input fail."
            ::= { eventsTxV2 405 }

        
        txAmpRfFail NOTIFICATION-TYPE
            OBJECTS { eventAlarmPriority, eventAlarmClass, eventEvent, indexTransmitter, indexAB, 
                indexRack, indexAmplifier }
            STATUS current
            DESCRIPTION 
                "The designated amplifier signals RF fail."
            ::= { eventsTxV2 406 }

        
        txAmpReflectionFault NOTIFICATION-TYPE
            OBJECTS { eventAlarmPriority, eventAlarmClass, eventEvent, indexTransmitter, indexAB, 
                indexRack, indexAmplifier }
            STATUS current
            DESCRIPTION 
                "The designated amplifier signals a reflection fault."
            ::= { eventsTxV2 407 }

        
        txAmpTemperatureFault NOTIFICATION-TYPE
            OBJECTS { eventAlarmPriority, eventAlarmClass, eventEvent, indexTransmitter, indexAB, 
                indexRack, indexAmplifier }
            STATUS current
            DESCRIPTION 
                "The designated amplifier signals a temperature fault - temperature is too high."
            ::= { eventsTxV2 408 }

        
        txAmpTransistorFault NOTIFICATION-TYPE
            OBJECTS { eventAlarmPriority, eventAlarmClass, eventEvent, indexTransmitter, indexAB, 
                indexRack, indexAmplifier }
            STATUS current
            DESCRIPTION 
                "The designated amplifier signals at least one faulty transistor."
            ::= { eventsTxV2 409 }

        
        eventsTxTable OBJECT-TYPE
            SYNTAX SEQUENCE OF EventsTxEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventTx 1 }

        
        eventsTxEntry OBJECT-TYPE
            SYNTAX EventsTxEntry
            MAX-ACCESS not-accessible
            STATUS current
            DESCRIPTION
                "An event entry always consists of its indexes
                (used for addressing within redundancy systems) and 3 values:
                - name: an enumerated list of all possible notifications
                - mask: the corresponding mask (enable/disable)
                - priority: the corresponding priority (value in range 0..255)
                - event: the event itself (active/inactive)"
            INDEX { eventTxIdx, eventTxABIdx, eventTxRackIdx, eventTxAmpIdx, eventTxNameIdx
                 }
            ::= { eventsTxTable 1 }

        
        EventsTxEntry ::=
            SEQUENCE { 
                eventTxIdx
                    IndexTransmitter,
                eventTxABIdx
                    IndexAB,
                eventTxRackIdx
                    IndexRack,
                eventTxAmpIdx
                    IndexAmplifier,
                eventTxNameIdx
                    EventMaxEntryNumber,
                eventTxName
                    INTEGER,
                eventTxMask
                    EventMask,
                eventTxPriority
                    EventPriority,
                eventTxEvent
                    EventState
             }

        eventTxIdx OBJECT-TYPE
            SYNTAX IndexTransmitter
            MAX-ACCESS not-accessible
            STATUS current
            DESCRIPTION
                "The transmitter index.
                This is a helper column and therefore not-accessible.."
            ::= { eventsTxEntry 1 }

        
        eventTxABIdx OBJECT-TYPE
            SYNTAX IndexAB
            MAX-ACCESS not-accessible
            STATUS current
            DESCRIPTION
                "The value for the module A (exciterA, outputstageA) or 
                B (exciterB, outputstageB) for alarms.
                This is a helper column and therefore not-accessible."
            ::= { eventsTxEntry 2 }

        
        eventTxRackIdx OBJECT-TYPE
            SYNTAX IndexRack
            MAX-ACCESS not-accessible
            STATUS current
            DESCRIPTION
                "The number of the designated rack.
                This is a helper column and therefore not-accessible."
            ::= { eventsTxEntry 3 }

        
        eventTxAmpIdx OBJECT-TYPE
            SYNTAX IndexAmplifier
            MAX-ACCESS not-accessible
            STATUS current
            DESCRIPTION
                "The number of the designated amplifier.
                This is a helper column and therefore not-accessible."
            ::= { eventsTxEntry 4 }

        
        eventTxNameIdx OBJECT-TYPE
            SYNTAX EventMaxEntryNumber
            MAX-ACCESS not-accessible
            STATUS current
            DESCRIPTION
                "The event number as integer.
                This is a helper column and therefore not-accessible."
            ::= { eventsTxEntry 5 }

        
        eventTxName OBJECT-TYPE
            SYNTAX INTEGER
                {
                txSummaryFault(1),
                txSummaryWarning(2),
                txLocal(3),
                txRfOn(4),
                txRfOk(5),
                txParamSetSubDeviceDiffers(6),
                txParamSetValuesChanged(7),
                txRfLoopProgram(8),
                txRfLoopReserve(9),
                txRfWarning(10),
                txReflectionWarning(11),
                txNetCCUFanFault(12),
                txNetCCUPowerSupply(13),
                txRfFail(14),
                txReflectionFault(15),
                txNetCCUBoardTemperatureFault(16),
                txNetCCUNoConnectionToExcA(17),
                txNetCCUNoConnectionToOstA(18),
                txNetCCUNoConnectionToExcB(19),
                txAutomaticExcReady(21),
                txAutomaticExcChanged(22),
                txAutomaticExcFault(23),
                txNetCCUBoardTemperatureWarning(27),
                txInternalPowerSupplyWarning(30),
                txExternalPowerSupplyWarning(31),
                txNoConnection(32),
                txExcSummaryFault(100),
                txExcSummaryWarning(101),
                txExcOn(102),
                txExcRfOn(103),
                txExcNoInput(104),
                txExcRfLoop(105),
                txExcRfFail(106),
                txExcOutputOpen(107),
                txExcBoardTemperatureWarning(108),
                txExcBoardTemperatureFailure(109),
                txExcMute(110),
                txExcCh1NotOK(111),
                txExcCh2NotOK(112),
                txExcCh1Selected(113),
                txExcCh2Selected(114),
                txExcSelAudioInpError(115),
                txExcDataInputNotOK(116),
                txExcFan1NotOk(117),
                txExcFan2NotOk(118),
                txExcFanSupplyNotOk(119),
                txExcHWError(120),
                txExcRackControlSupplyNotOk(121),
                txExcExtRefNotOK(122),
                txExcExtRefNotLocked(123),
                txOstSummaryFault(200),
                txOstSummaryWarning(201),
                txOstRfOn(202),
                txOstRfOk(203),
                txOstNoInput(204),
                txOstRfWarning(205),
                txOstReflectionWarning(206),
                txOstRackWarning(207),
                txOstCoolingWarning(208),
                txOstRfFail(209),
                txOstReflectionFault(210),
                txOstACFault(211),
                txOstCoolingFault(212),
                txOstCommFault(213),
                txRackSumFault(300),
                txRackSumWarning(301),
                txRackOn(302),
                txRackGpiWarning(303),
                txRackFan1Fault(304),
                txRackFan2Fault(305),
                txRackCoolingSumWarning(306),
                txRackAmplifierSumFault(307),
                txRackNoLink(308),
                txRackGpiFault(309),
                txRackTemperatureFault(310),
                txRackACFault(311),
                txRackCoolingSumFault(312),
                txRackTempFaultAbs1(313),
                txRackTempFaultAbs2(314),
                txRackDCFault(315),
                txRackRfOn(318),
                txRackRfOk(319),
                txRackRfWarning(320),
                txRackRfFault(321),
                txRackReflectionWarning(322),
                txRackReflectionFault(323),
                txRackProbeNotCalibrated(330),
                txRackTemperatureWarning(331),
                txRackOvervoltProtectWarning(335),
                txAmpSumFault(400),
                txAmpSumWarning(401),
                txAmpPowerOn(402),
                txAmpDCOk(403),
                txAmpACOk(404),
                txAmpRfInFail(405),
                txAmpRfFail(406),
                txAmpReflectionFault(407),
                txAmpTemperatureFault(408),
                txAmpTransistorFault(409)
                }
            MAX-ACCESS read-only
            STATUS current
            DESCRIPTION
                "The event number as integer and the value as readable text.
                The enumeration correlates with the notifications under eventsTxV2."
            ::= { eventsTxEntry 6 }

        
        eventTxMask OBJECT-TYPE
            SYNTAX EventMask
            MAX-ACCESS read-write
            STATUS current
            DESCRIPTION
                "See TextualConvention for details."
            ::= { eventsTxEntry 7 }

        
        eventTxPriority OBJECT-TYPE
            SYNTAX EventPriority
            MAX-ACCESS read-write
            STATUS current
            DESCRIPTION
                "See TextualConvention for details."
            ::= { eventsTxEntry 8 }

        
        eventTxEvent OBJECT-TYPE
            SYNTAX EventState
            MAX-ACCESS read-only
            STATUS current
            DESCRIPTION
                "See TextualConvention for details."
            ::= { eventsTxEntry 9 }

        
-- *****************************************************************************
-- **          events program
-- *****************************************************************************
        eventProgram OBJECT IDENTIFIER ::= { rsXx8000FmNp1Events 3 }

        
        eventsProgramV2 OBJECT-IDENTITY
            STATUS current
            DESCRIPTION 
                "Compatibility to SMIv1."
            ::= { eventProgram 0 }

        
        evtProgramRfOn NOTIFICATION-TYPE
            OBJECTS { eventAlarmPriority, eventAlarmClass, eventEvent, indexProgram }
            STATUS current
            DESCRIPTION 
                "The RF is present for the corresponding program 
                (independent of which physical tx is sending out the program)."
            ::= { eventsProgramV2 1 }

        
        eventsProgramTable OBJECT-TYPE
            SYNTAX SEQUENCE OF EventsProgramEntry
            MAX-ACCESS not-accessible
            STATUS current
            DESCRIPTION
                "This table contains necessary information for handling alarms. 
                For each alarm you have the following information: 
                - name (get),
                - mask to enable/disable sending out (set/get),
                - priority (set/get) and 
                - the current state (get only)."
            ::= { eventProgram 1 }

        
        eventsProgramEntry OBJECT-TYPE
            SYNTAX EventsProgramEntry
            MAX-ACCESS not-accessible
            STATUS current
            DESCRIPTION
                "An event entry always consists of 4 values:
                - name: an enumerated list of all possible notifications
                - mask: the corresponding mask (enable/disable)
                - priority: the corresponding priority (value in range 0..255)
                - event: the event itself (active/inactive)"
            INDEX { eventProgramIdx, eventProgramNameIdx }
            ::= { eventsProgramTable 1 }

        
        EventsProgramEntry ::=
            SEQUENCE { 
                eventProgramIdx
                    EventMaxEntryNumber,
                eventProgramNameIdx
                    EventMaxEntryNumber,
                eventProgramName
                    INTEGER,
                eventProgramMask
                    EventMask,
                eventProgramPriority
                    EventPriority,
                eventProgramEvent
                    EventState
             }

        eventProgramIdx OBJECT-TYPE
            SYNTAX EventMaxEntryNumber
            MAX-ACCESS not-accessible
            STATUS current
            DESCRIPTION
                "The event number as integer."
            ::= { eventsProgramEntry 1 }

        
        eventProgramNameIdx OBJECT-TYPE
            SYNTAX EventMaxEntryNumber
            MAX-ACCESS not-accessible
            STATUS current
            DESCRIPTION
                "The event number as integer.
                This is a helper column and therefore not-accessible."
            ::= { eventsProgramEntry 2 }

        
        eventProgramName OBJECT-TYPE
            SYNTAX INTEGER { programRfOn(1) }
            MAX-ACCESS read-only
            STATUS current
            DESCRIPTION
                "The event number as integer and the value as readable text."
            ::= { eventsProgramEntry 3 }

        
        eventProgramMask OBJECT-TYPE
            SYNTAX EventMask
            MAX-ACCESS read-write
            STATUS current
            DESCRIPTION
                "See TextualConvention for details."
            ::= { eventsProgramEntry 4 }

        
        eventProgramPriority OBJECT-TYPE
            SYNTAX EventPriority
            MAX-ACCESS read-write
            STATUS current
            DESCRIPTION
                "See TextualConvention for details."
            ::= { eventsProgramEntry 5 }

        
        eventProgramEvent OBJECT-TYPE
            SYNTAX EventState
            MAX-ACCESS read-only
            STATUS current
            DESCRIPTION
                "See TextualConvention for details."
            ::= { eventsProgramEntry 6 }

        
-- *****************************************************************************
-- **          conformance statements
-- *****************************************************************************
        rsXx8000FmNp1Conf OBJECT IDENTIFIER ::= { rsXx8000FmNp1 5 }

        
        rsXx8000FmNp1Groups OBJECT IDENTIFIER ::= { rsXx8000FmNp1Conf 1 }

        
        groupNsuObjs OBJECT-GROUP
            OBJECTS { operationModeAutomatic, operationModePriority, selectedTxToDummyLoad, selectedInputTxB, selectedParametersetTxB, 
                selectedChannelTxB, resetAllFaults, summaryFaultNSU, summaryWarningNSU, localModeNSU, 
                automaticReady, automaticChanged, automaticFault, nsuNumberOfEntries, nsuLogbookClear, 
                nsuLogbookEntryNbr, nsuLogbookType, nsuLogbookSlope, nsuLogbookMessage, nsuLogbookDateTime, 
                loadedTx, programPriority, programOperationMode, powerSupply, programRfOn, 
                additionalPowerSupply }
            STATUS current
            DESCRIPTION 
                "Group for all objects of the designated NSU (NetCCU Switchover Unit)."
            ::= { rsXx8000FmNp1Groups 1 }

        
        groupNsuEvents NOTIFICATION-GROUP
            NOTIFICATIONS { nsuSummaryFault, nsuSummaryWarning, nsuLocal, nsuAutomaticReady, nsuAutomaticChanged, 
                nsuFanWarning, nsuPowerSupply, nsuAutomaticFault, nsuInputSwitcherFault, nsuBoardTemperatureWarning
                 }
            STATUS current
            DESCRIPTION 
                "Group for all events of the NSU (NetCCU Switchover Unit)."
            ::= { rsXx8000FmNp1Groups 2 }

        
        groupNsuEventsAddPowerSupply NOTIFICATION-GROUP
            NOTIFICATIONS { nsuInternalPowerSupplyWarning, nsuExternalPowerSupplyWarning }
            STATUS current
            DESCRIPTION 
                "Events that are available only when additionalPowerSupply is true."
            ::= { rsXx8000FmNp1Groups 3 }

        
        groupNsuObjsAddPowerSupply OBJECT-GROUP
            OBJECTS { internalPowerSupply, externalPowerSupply }
            STATUS current
            DESCRIPTION 
                "Objects that are available only when additionalPowerSupply is true."
            ::= { rsXx8000FmNp1Groups 4 }

        
        groupTxObjsMp OBJECT-GROUP
            OBJECTS { cmdTxName, cmdTxResetSumFault, cmdTxParametersetLoad, cmdTxParametersetSave, cmdTxOperationModeProgram, 
                cmdOstRefVoltage, cmdOstMaxOutletTempThreshold, statusTxName, statusTxNoConnection, statusTxSummaryFault, 
                statusTxSummaryWarning, statusTxLocalMode, statusTxRfOn, statusTxForwardPower, statusTxReflectedPower, 
                statusTxSummaryFaultExcA, statusTxSummaryFaultOstA, statusTxNoConnectionExcA, statusTxNoConnectionOstA, statusTxAdditionalPowerSupply, 
                statusTxPowerSupply }
            STATUS current
            DESCRIPTION 
                "Group for objects of transmitters in case of MediumPower."
            ::= { rsXx8000FmNp1Groups 11 }

        
        groupTxObjsLpWithNetCCU OBJECT-GROUP
            OBJECTS { cmdTxName, cmdTxResetSumFault, cmdTxParametersetLoad, cmdTxParametersetSave, cmdTxOperationModeProgram, 
                statusTxName, statusTxNoConnection, statusTxSummaryFault, statusTxSummaryWarning, statusTxLocalMode, 
                statusTxRfOn, statusTxForwardPower, statusTxSummaryFaultExcA, statusTxSummaryFaultOstA, statusTxNoConnectionExcA, 
                statusTxNoConnectionOstA, statusTxAdditionalPowerSupply, statusTxPowerSupply }
            STATUS current
            DESCRIPTION 
                "Group for objects of transmitters in case of LowPower with NetCCU."
            ::= { rsXx8000FmNp1Groups 12 }

        
        groupTxObjsLpWithoutNetCCU OBJECT-GROUP
            OBJECTS { cmdTxName, cmdTxResetSumFault, cmdTxParametersetLoad, cmdTxParametersetSave, cmdTxOperationModeProgram, 
                statusTxName, statusTxNoConnection, statusTxSummaryFault, statusTxSummaryWarning, statusTxLocalMode, 
                statusTxRfOn, statusTxForwardPower, statusTxSummaryFaultExcA, statusTxSummaryFaultOstA }
            STATUS current
            DESCRIPTION 
                "Group for objects of transmitters in case of LowPower without NetCCU."
            ::= { rsXx8000FmNp1Groups 13 }

        
        groupTxObjsExc OBJECT-GROUP
            OBJECTS { cmdExcReset, cmdExcRFOnOff, cmdExcNoInputSeverity, cmdExcNoInputFailDelay, cmdExcInputLevelAnalog, 
                cmdExcInputLevelMPX, cmdExcInputLevelAES, cmdExcAnalogImpedance, cmdExcMPXImpedance, cmdExcAFThreshold, 
                cmdExcAFOnTime, cmdExcAFOffTime, cmdExcAFThresholddBu, cmdExcMPXThreshold, cmdExcMPXOnTime, 
                cmdExcMPXOffTime, cmdExcMPXThresholddBu, cmdExcAESThreshold, cmdExcAESOnTime, cmdExcAESOffTime, 
                cmdExcAESThresholddBFs, cmdExcInputLevelAUX1, cmdExcInputLevelAUX2, cmdExcInputLevelAUX3, cmdExcDeviationAUX1, 
                cmdExcDeviationAUX2, cmdExcDeviationAUX3, cmdExcActivateAUX1, cmdExcActivateAUX2, cmdExcActivateAUX3, 
                cmdExcAUX1Threshold, cmdExcAUX1ThresholddB, cmdExcAUX1OnTime, cmdExcAUX1OffTime, cmdExcAUX2Threshold, 
                cmdExcAUX2ThresholddB, cmdExcAUX2OnTime, cmdExcAUX2OffTime, cmdExcAUX3Threshold, cmdExcAUX3ThresholddB, 
                cmdExcAUX3OnTime, cmdExcAUX3OffTime, cmdExcCH1ModType, cmdExcCH2ModType, cmdExcModSelection, 
                cmdExcDeviation, cmdExcDeviationLimit, cmdExcActivateDeviationLimiter, cmdExcPreemphasis, cmdExcActivatePreemphasis, 
                cmdExcPilotDeviation, cmdExcActivatePilot, cmdExcMPXPowerLimit, cmdExcActivateMPXPowerLimiter, cmdExcFrequency, 
                cmdExcRefSource, cmdExcTCXOTrim, excInputAnalogStatusTxName, excInputArrayIdxLabel, excInputExcNominal, 
                excInputCurrentPercent, excInputCurrentdBu, excInputCurrentState, excInputTxName, excInputAFThresholddBuMax, 
                excInputAFThresholddBuMin, excInputMPXThresholddBuMax, excInputMPXThresholddBuMin, excInputAESThresholddBFsMax, excInputAESThresholddBFsMin, 
                excInputAUX1ThresholddBMax, excInputAUX1ThresholddBMin, excInputAUX2ThresholddBMax, excInputAUX2ThresholddBMin, excInputAUX3ThresholddBMax, 
                excInputAUX3ThresholddBMin, excInputCH1State, excInputCH2State, excInputSelectedModType, excInputAudioState, 
                excInputNomAESLLevel, excInputAESLLevel, excInputAESLLeveldBFs, excInputAESLState, excInputNomAESRLevel, 
                excInputAESRLevel, excInputAESRLeveldBFs, excInputAESRState, excInputAESParityERR, excInputAESAudioDetect, 
                excInputAESPreemphasisDetect, excInputAESChannelStatusCRC, excInputAESChannelStatusValid, excInputAESNoClock, excInputAESNonPCM, 
                excInputAESSF, excModStatusTxName, excModStatusCurrentDeviation, excModStatusCurrentMPXPower, excModStatusCurrentClipDeviation, 
                excModStatusLimiterActivity, excDeviceStatusTxName, excDeviceStatusCurrentTemperatur, excDeviceStatus12VRack, excDeviceStatus12VFan
                 }
            STATUS current
            DESCRIPTION 
                "Group for objects of exciter."
            ::= { rsXx8000FmNp1Groups 20 }

        
        groupTxObjsExcLp OBJECT-GROUP
            OBJECTS { cmdLpTxTransmitterId, cmdLpTxRfWarningThreshold, cmdLpTxRfFaultThreshold, lpOstTxName, lpOstOperationMode, 
                lpOstForwardPowerStatus, lpOstVswrPowerRegulation, lpOstTemperatureRegulation, lpOstRfInStatus, lpOstReflectionStatus, 
                lpOstTemperatureStatus, lpOstCommsStatus, lpOstForwardPower, lpOstReflectedPower, lpOstSwr, 
                lpOstDcSupplyVoltage, lpOstDcSupplyControlVoltage, lpOstAttenuatorControlVoltage, lpOstDriverCurrent, lpOstPowerAmplifier1Current, 
                lpOstPowerAmplifier2Current, lpOstPowerAmplifier3Current, lpOstPowerAmplifier4Current, lpOstAlcControlVoltage, lpOstAmplifierHeatsinkTemp, 
                lpOstActualReferenceVoltage, lpOstNominalPower, lpTxCuTxName, lpTxCuTransmitterMode, lpTxCuTemperatureStatus, 
                lpTxCuFanStatus }
            STATUS current
            DESCRIPTION 
                "Group for additional low power objects of exciter."
            ::= { rsXx8000FmNp1Groups 21 }

        
        groupTxObjsLogbookNetCCU OBJECT-GROUP
            OBJECTS { txBNetCCUNumberOfEntries, txBNetCCULogbookClear, txBNetCCULogbookEntryNbr, txBNetCCULogbookType, txBNetCCULogbookSlope, 
                txBNetCCULogbookMessage, txBNetCCULogbookDateTime, txA1NetCCUNumberOfEntries, txA1NetCCULogbookClear, txA1NetCCULogbookEntryNbr, 
                txA1NetCCULogbookType, txA1NetCCULogbookSlope, txA1NetCCULogbookMessage, txA1NetCCULogbookDateTime, txA2NetCCUNumberOfEntries, 
                txA2NetCCULogbookClear, txA2NetCCULogbookEntryNbr, txA2NetCCULogbookType, txA2NetCCULogbookSlope, txA2NetCCULogbookMessage, 
                txA2NetCCULogbookDateTime, txA3NetCCUNumberOfEntries, txA3NetCCULogbookClear, txA3NetCCULogbookEntryNbr, txA3NetCCULogbookType, 
                txA3NetCCULogbookSlope, txA3NetCCULogbookMessage, txA3NetCCULogbookDateTime, txA4NetCCUNumberOfEntries, txA4NetCCULogbookClear, 
                txA4NetCCULogbookEntryNbr, txA4NetCCULogbookType, txA4NetCCULogbookSlope, txA4NetCCULogbookMessage, txA4NetCCULogbookDateTime, 
                txA5NetCCUNumberOfEntries, txA5NetCCULogbookClear, txA5NetCCULogbookEntryNbr, txA5NetCCULogbookType, txA5NetCCULogbookSlope, 
                txA5NetCCULogbookMessage, txA5NetCCULogbookDateTime, txA6NetCCUNumberOfEntries, txA6NetCCULogbookClear, txA6NetCCULogbookEntryNbr, 
                txA6NetCCULogbookType, txA6NetCCULogbookSlope, txA6NetCCULogbookMessage, txA6NetCCULogbookDateTime, txA7NetCCUNumberOfEntries, 
                txA7NetCCULogbookClear, txA7NetCCULogbookEntryNbr, txA7NetCCULogbookType, txA7NetCCULogbookSlope, txA7NetCCULogbookMessage, 
                txA7NetCCULogbookDateTime, txA8NetCCUNumberOfEntries, txA8NetCCULogbookClear, txA8NetCCULogbookEntryNbr, txA8NetCCULogbookType, 
                txA8NetCCULogbookSlope, txA8NetCCULogbookMessage, txA8NetCCULogbookDateTime }
            STATUS current
            DESCRIPTION 
                "Group for objects of logbooks of NetCCU."
            ::= { rsXx8000FmNp1Groups 30 }

        
        groupTxObjsLogbookExcA OBJECT-GROUP
            OBJECTS { txBExciterANumberOfEntries, txBExciterALogbookClear, txBExcALogbookEntryNbr, txBExcALogbookType, txBExcALogbookSlope, 
                txBExcALogbookMessage, txBExcALogbookDateTime, txA1ExciterANumberOfEntries, txA1ExciterALogbookClear, txA1ExcALogbookEntryNbr, 
                txA1ExcALogbookType, txA1ExcALogbookSlope, txA1ExcALogbookMessage, txA1ExcALogbookDateTime, txA2ExciterANumberOfEntries, 
                txA2ExciterALogbookClear, txA2ExcALogbookEntryNbr, txA2ExcALogbookType, txA2ExcALogbookSlope, txA2ExcALogbookMessage, 
                txA2ExcALogbookDateTime, txA3ExciterANumberOfEntries, txA3ExciterALogbookClear, txA3ExcALogbookEntryNbr, txA3ExcALogbookType, 
                txA3ExcALogbookSlope, txA3ExcALogbookMessage, txA3ExcALogbookDateTime, txA4ExciterANumberOfEntries, txA4ExciterALogbookClear, 
                txA4ExcALogbookEntryNbr, txA4ExcALogbookType, txA4ExcALogbookSlope, txA4ExcALogbookMessage, txA4ExcALogbookDateTime, 
                txA5ExciterANumberOfEntries, txA5ExciterALogbookClear, txA5ExcALogbookEntryNbr, txA5ExcALogbookType, txA5ExcALogbookSlope, 
                txA5ExcALogbookMessage, txA5ExcALogbookDateTime, txA6ExciterANumberOfEntries, txA6ExciterALogbookClear, txA6ExcALogbookEntryNbr, 
                txA6ExcALogbookType, txA6ExcALogbookSlope, txA6ExcALogbookMessage, txA6ExcALogbookDateTime, txA7ExciterANumberOfEntries, 
                txA7ExciterALogbookClear, txA7ExcALogbookEntryNbr, txA7ExcALogbookType, txA7ExcALogbookSlope, txA7ExcALogbookMessage, 
                txA7ExcALogbookDateTime, txA8ExciterANumberOfEntries, txA8ExciterALogbookClear, txA8ExcALogbookEntryNbr, txA8ExcALogbookType, 
                txA8ExcALogbookSlope, txA8ExcALogbookMessage, txA8ExcALogbookDateTime }
            STATUS current
            DESCRIPTION 
                "Group for objects of logbooks of exciters A."
            ::= { rsXx8000FmNp1Groups 31 }

        
        groupTxObjsLogbookOstA OBJECT-GROUP
            OBJECTS { txBOutputstageANumberOfEntries, txBOutputstageALogbookClear, txBOstALogbookEntryNbr, txBOstALogbookType, txBOstALogbookSlope, 
                txBOstALogbookMessage, txBOstALogbookDateTime, txA1OutputstageANumberOfEntries, txA1OutputstageALogbookClear, txA1OstALogbookEntryNbr, 
                txA1OstALogbookType, txA1OstALogbookSlope, txA1OstALogbookMessage, txA1OstALogbookDateTime, txA2OutputstageANumberOfEntries, 
                txA2OutputstageALogbookClear, txA2OstALogbookEntryNbr, txA2OstALogbookType, txA2OstALogbookSlope, txA2OstALogbookMessage, 
                txA2OstALogbookDateTime, txA3OutputstageANumberOfEntries, txA3OutputstageALogbookClear, txA3OstALogbookEntryNbr, txA3OstALogbookType, 
                txA3OstALogbookSlope, txA3OstALogbookMessage, txA3OstALogbookDateTime, txA4OutputstageANumberOfEntries, txA4OutputstageALogbookClear, 
                txA4OstALogbookEntryNbr, txA4OstALogbookType, txA4OstALogbookSlope, txA4OstALogbookMessage, txA4OstALogbookDateTime, 
                txA5OutputstageANumberOfEntries, txA5OutputstageALogbookClear, txA5OstALogbookEntryNbr, txA5OstALogbookType, txA5OstALogbookSlope, 
                txA5OstALogbookMessage, txA5OstALogbookDateTime, txA6OutputstageANumberOfEntries, txA6OutputstageALogbookClear, txA6OstALogbookEntryNbr, 
                txA6OstALogbookType, txA6OstALogbookSlope, txA6OstALogbookMessage, txA6OstALogbookDateTime, txA7OutputstageANumberOfEntries, 
                txA7OutputstageALogbookClear, txA7OstALogbookEntryNbr, txA7OstALogbookType, txA7OstALogbookSlope, txA7OstALogbookMessage, 
                txA7OstALogbookDateTime, txA8OutputstageANumberOfEntries, txA8OutputstageALogbookClear, txA8OstALogbookEntryNbr, txA8OstALogbookType, 
                txA8OstALogbookSlope, txA8OstALogbookMessage, txA8OstALogbookDateTime }
            STATUS current
            DESCRIPTION 
                "Group for objects of logbooks of outputstages A."
            ::= { rsXx8000FmNp1Groups 32 }

        
        groupTxObjsLogbookExcB OBJECT-GROUP
            OBJECTS { txBExciterBNumberOfEntries, txBExciterBLogbookClear, txBExcBLogbookEntryNbr, txBExcBLogbookType, txBExcBLogbookSlope, 
                txBExcBLogbookMessage, txBExcBLogbookDateTime, txA1ExciterBNumberOfEntries, txA1ExciterBLogbookClear, txA1ExcBLogbookEntryNbr, 
                txA1ExcBLogbookType, txA1ExcBLogbookSlope, txA1ExcBLogbookMessage, txA1ExcBLogbookDateTime, txA2ExciterBNumberOfEntries, 
                txA2ExciterBLogbookClear, txA2ExcBLogbookEntryNbr, txA2ExcBLogbookType, txA2ExcBLogbookSlope, txA2ExcBLogbookMessage, 
                txA2ExcBLogbookDateTime, txA3ExciterBNumberOfEntries, txA3ExciterBLogbookClear, txA3ExcBLogbookEntryNbr, txA3ExcBLogbookType, 
                txA3ExcBLogbookSlope, txA3ExcBLogbookMessage, txA3ExcBLogbookDateTime, txA4ExciterBNumberOfEntries, txA4ExciterBLogbookClear, 
                txA4ExcBLogbookEntryNbr, txA4ExcBLogbookType, txA4ExcBLogbookSlope, txA4ExcBLogbookMessage, txA4ExcBLogbookDateTime, 
                txA5ExciterBNumberOfEntries, txA5ExciterBLogbookClear, txA5ExcBLogbookEntryNbr, txA5ExcBLogbookType, txA5ExcBLogbookSlope, 
                txA5ExcBLogbookMessage, txA5ExcBLogbookDateTime, txA6ExciterBNumberOfEntries, txA6ExciterBLogbookClear, txA6ExcBLogbookEntryNbr, 
                txA6ExcBLogbookType, txA6ExcBLogbookSlope, txA6ExcBLogbookMessage, txA6ExcBLogbookDateTime, txA7ExciterBNumberOfEntries, 
                txA7ExciterBLogbookClear, txA7ExcBLogbookEntryNbr, txA7ExcBLogbookType, txA7ExcBLogbookSlope, txA7ExcBLogbookMessage, 
                txA7ExcBLogbookDateTime, txA8ExciterBNumberOfEntries, txA8ExciterBLogbookClear, txA8ExcBLogbookEntryNbr, txA8ExcBLogbookType, 
                txA8ExcBLogbookSlope, txA8ExcBLogbookMessage, txA8ExcBLogbookDateTime }
            STATUS current
            DESCRIPTION 
                "Group for objects of logbooks of exciters B."
            ::= { rsXx8000FmNp1Groups 33 }

        
        groupTxObjsOstARack OBJECT-GROUP
            OBJECTS { txBOstARackInletTemperature, txBOstARackOutletTemperature, txBOstARackAuxPowerSupply, txA1OstARackInletTemperature, txA1OstARackOutletTemperature, 
                txA1OstARackAuxPowerSupply, txA2OstARackInletTemperature, txA2OstARackOutletTemperature, txA2OstARackAuxPowerSupply, txA3OstARackInletTemperature, 
                txA3OstARackOutletTemperature, txA3OstARackAuxPowerSupply, txA4OstARackInletTemperature, txA4OstARackOutletTemperature, txA4OstARackAuxPowerSupply, 
                txA5OstARackInletTemperature, txA5OstARackOutletTemperature, txA5OstARackAuxPowerSupply, txA6OstARackInletTemperature, txA6OstARackOutletTemperature, 
                txA6OstARackAuxPowerSupply, txA7OstARackInletTemperature, txA7OstARackOutletTemperature, txA7OstARackAuxPowerSupply, txA8OstARackInletTemperature, 
                txA8OstARackOutletTemperature, txA8OstARackAuxPowerSupply, amplifiersPerRack, rackRfEventSignalling, rackGeneralPurposeInput, 
                rfProbePresent, rfProbeConfigurationNominalValue, rfProbeThresholdRfFailLimit, rfProbeThresholdTimeoutRfFailCtr, rfProbeThresholdWarningLimit, 
                rfProbeCalibrationGain, rfProbeCalibrationOffset, rfProbeCalibrationSetGain, rfProbeCalibrationSetOffset, rfProbeMeasuredValue
                 }
            STATUS current
            DESCRIPTION 
                "Group for objects of OstARackTable."
            ::= { rsXx8000FmNp1Groups 40 }

        
        groupIndependentRacks OBJECT-GROUP
            OBJECTS { rackReferenceVoltage, amplifiersPowerSupply, rackOnOff }
            STATUS current
            DESCRIPTION 
                "object types that are relevant for NX variants with independent racks only"
            ::= { rsXx8000FmNp1Groups 42 }

        
        groupTxObjsProductInfo OBJECT-GROUP
            OBJECTS { prodInfoModuleName, prodInfoSerialNumber, prodInfoIdentNumberSW, prodInfoVersionNumberSW, prodInfoIdentNumberHW, 
                prodInfoVersionNumberHW, productInfoProductDateHW, nsuProdInfoModuleName, nsuProdInfoSerialNumber, nsuProdInfoIdentNumberSW, 
                nsuProdInfoVersionNumberSW, nsuProdInfoIdentNumberHW, nsuProdInfoVersionNumberHW, nsuProductInfoProductDateHW }
            STATUS current
            DESCRIPTION 
                "Group for ProductInfoTable of transmitters."
            ::= { rsXx8000FmNp1Groups 50 }

        
        groupTxObjsDualDrive OBJECT-GROUP
            OBJECTS { cmdTxOperationModeReserve, cmdTxOpModeExcAutomatic, cmdTxPreselectExciter, cmdTxDelayTimeExcAutomatic, statusTxSummaryFaultExcB, 
                statusTxExciterAutomaticReady, statusTxExciterAutomaticChanged, statusTxExciterAutomaticFault, statusTxNoConnectionExcB, statusTxActiveExcA, 
                statusTxActiveExcB }
            STATUS current
            DESCRIPTION 
                "Group for objects of transmitters in case of DualDrive."
            ::= { rsXx8000FmNp1Groups 60 }

        
        groupTxObjsSimple OBJECT-GROUP
            OBJECTS { cmdTxName, cmdTxResetSumFault, cmdTxParametersetLoad, cmdTxParametersetSave, cmdTxOperationModeProgram, 
                statusTxName, statusTxNoConnection, statusTxSummaryFault, statusTxSummaryWarning, statusTxLocalMode, 
                statusTxRfOn }
            STATUS current
            DESCRIPTION 
                "Group for all objects of simple transmitters."
            ::= { rsXx8000FmNp1Groups 80 }

        
        groupObjsObsoleted OBJECT-GROUP
            OBJECTS { cmdTxParametersetReSave, rfProbeConfigurationLabel }
            STATUS obsolete
            DESCRIPTION 
                "group for obsoleted object types"
            ::= { rsXx8000FmNp1Groups 99 }

        
        groupTxEventsMp NOTIFICATION-GROUP
            NOTIFICATIONS { txSummaryFault, txSummaryWarning, txLocal, txRfOn, txRfOk, 
                txParamSetValuesChanged, txRfLoopProgram, txRfWarning, txReflectionWarning, txNetCCUFanFault, 
                txNetCCUPowerSupply, txRfFail, txReflectionFault, txNetCCUNoConnectionToExcA, txNetCCUNoConnectionToOstA, 
                txOstSummaryFault, txOstSummaryWarning, txOstRfOn, txOstRfOk, txOstNoInput, 
                txOstRfWarning, txOstReflectionWarning, txOstRackWarning, txOstCoolingWarning, txOstRfFail, 
                txOstReflectionFault, txOstACFault, txOstCoolingFault, txOstCommFault, txRackSumFault, 
                txRackSumWarning, txRackOn, txRackGpiWarning, txRackFan1Fault, txRackFan2Fault, 
                txRackCoolingSumWarning, txRackAmplifierSumFault, txRackNoLink, txRackGpiFault, txRackTemperatureFault, 
                txRackACFault, txRackCoolingSumFault, txRackTempFaultAbs1, txRackTempFaultAbs2, txRackDCFault, 
                txRackRfWarning, txRackRfFault, txRackReflectionWarning, txRackReflectionFault, txAmpSumFault, 
                txAmpSumWarning, txAmpPowerOn, txAmpDCOk, txAmpACOk, txAmpRfInFail, 
                txAmpRfFail, txAmpReflectionFault, txAmpTemperatureFault, txRackRfOk, txRackRfOn, 
                txRackTemperatureWarning, txRackOvervoltProtectWarning, txNoConnection, txAmpTransistorFault, txNetCCUBoardTemperatureWarning, 
                txRackProbeNotCalibrated }
            STATUS current
            DESCRIPTION 
                "Group for events of transmitters in case of MediumPower."
            ::= { rsXx8000FmNp1Groups 201 }

        
        groupTxEventsLpWithNetCCU NOTIFICATION-GROUP
            NOTIFICATIONS { txSummaryFault, txSummaryWarning, txLocal, txRfOn, txRfOk, 
                txParamSetValuesChanged, txRfLoopProgram, txNetCCUFanFault, txNetCCUPowerSupply, txRfFail, 
                txNetCCUNoConnectionToExcA, txNetCCUNoConnectionToOstA, txOstSummaryFault, txOstSummaryWarning, txRfWarning, 
                txNoConnection, txOstRfOn, txNetCCUBoardTemperatureWarning }
            STATUS current
            DESCRIPTION 
                "Group for events of transmitters in case of LowPower with NetCCU."
            ::= { rsXx8000FmNp1Groups 202 }

        
        groupTxEventsLpWithoutNetCCU NOTIFICATION-GROUP
            NOTIFICATIONS { txSummaryFault, txSummaryWarning, txLocal, txRfOn, txParamSetValuesChanged, 
                txRfFail, txOstSummaryFault, txOstSummaryWarning, txRfOk, txNoConnection, 
                txOstRfOn, txRfWarning }
            STATUS current
            DESCRIPTION 
                "Group for events of transmitters in case of LowPower without NetCCU."
            ::= { rsXx8000FmNp1Groups 203 }

        
        groupTxEventsAddPowerSupply NOTIFICATION-GROUP
            NOTIFICATIONS { txInternalPowerSupplyWarning, txExternalPowerSupplyWarning }
            STATUS current
            DESCRIPTION 
                "Events that are available only when statusTxAdditionalPowerSupply is true."
            ::= { rsXx8000FmNp1Groups 204 }

        
        groupTxObjsAddPowerSupply OBJECT-GROUP
            OBJECTS { statusTxInternalPowerSupply, statusTxExternalPowerSupply }
            STATUS current
            DESCRIPTION 
                "Objects that are available only when statusTxAdditionalPowerSupply is true."
            ::= { rsXx8000FmNp1Groups 205 }

        
        groupTxEventsExc NOTIFICATION-GROUP
            NOTIFICATIONS { txExcSummaryFault, txExcSummaryWarning, txExcOn, txExcRfOn, txExcNoInput, 
                txExcRfLoop, txExcRfFail, txExcOutputOpen, txExcBoardTemperatureWarning, txExcBoardTemperatureFailure, 
                txExcMute, txExcCh1NotOK, txExcCh2NotOK, txExcCh1Selected, txExcCh2Selected, 
                txExcSelAudioInpError, txExcDataInputNotOK, txExcFan1NotOk, txExcFan2NotOk, txExcFanSupplyNotOk, 
                txExcHWError, txExcRackControlSupplyNotOk, txExcExtRefNotOK, txExcExtRefNotLocked }
            STATUS current
            DESCRIPTION 
                "Group for all events of exciter."
            ::= { rsXx8000FmNp1Groups 210 }

        
        groupTxEventsExcLp NOTIFICATION-GROUP
            NOTIFICATIONS { txLpRfWarning, txLpFanHealth, txLpOstVswrPwrRegulationWarning, txLpOstVswrPwrRegulationFault, txLpOstTempRegulationWarning
                 }
            STATUS current
            DESCRIPTION 
                "Group for additional events in case of low power exciter."
            ::= { rsXx8000FmNp1Groups 211 }

        
        groupTxEventsDualDrive NOTIFICATION-GROUP
            NOTIFICATIONS { txRfLoopReserve, txAutomaticExcReady, txAutomaticExcChanged, txAutomaticExcFault, txNetCCUNoConnectionToExcB
                 }
            STATUS current
            DESCRIPTION 
                "Group for events of transmitters in case of DualDrive."
            ::= { rsXx8000FmNp1Groups 220 }

        
        groupTxEventsSimple NOTIFICATION-GROUP
            NOTIFICATIONS { txSummaryFault, txSummaryWarning, txLocal, txRfOn, txParamSetValuesChanged
                 }
            STATUS current
            DESCRIPTION 
                "Group for all events of simple transmitters."
            ::= { rsXx8000FmNp1Groups 240 }

        
        groupEventTable OBJECT-GROUP
            OBJECTS { eventNsuName, eventNsuMask, eventNsuPriority, eventNsuEvent, eventTxName, 
                eventTxMask, eventTxPriority, eventTxEvent, eventProgramName, eventProgramMask, 
                eventProgramPriority, eventProgramEvent }
            STATUS current
            DESCRIPTION 
                "Group for all objects of event tables."
            ::= { rsXx8000FmNp1Groups 400 }

        
        groupRfProbes OBJECT-GROUP
            OBJECTS { rfProbesNetCCURfProbe1, rfProbesNetCCURfProbe2, rfProbesAntFwdNominal, rfProbesAntFwdWarningLimit, rfProbesAntFwdFailLimit, 
                rfProbesAntFwdDelayTimeRfFail, rfProbesAntFwdSetOffset, rfProbesAntFwdSetGain, rfProbesAntReflWarningLimit, rfProbesAntReflSetOffset, 
                rfProbesAntReflSetGain }
            STATUS current
            DESCRIPTION 
                "This group includes all OIDs regarding RF Probes."
            ::= { rsXx8000FmNp1Groups 401 }

        
        groupAmpMeasureValues OBJECT-GROUP
            OBJECTS { ampI1A, ampI2A, ampI3A, ampI4A, ampI1B, 
                ampI2B, ampI3B, ampI4B, ampIDrv, ampUDc, 
                ampIDc, ampUDcControl, ampUReg, ampPowerA, ampPowerB, 
                ampPowerOut, ampPowerReflection, ampPowerReference, ampDeltaPhase, ampCmdDeltaPhase
                 }
            STATUS current
            DESCRIPTION 
                "Group for objects of amplifierTable"
            ::= { rsXx8000FmNp1Groups 402 }

        
        groupEventsObsoleted NOTIFICATION-GROUP
            NOTIFICATIONS { txNetCCUBoardTemperatureFault, txParamSetSubDeviceDiffers, nsuBoardTemperatureFault }
            STATUS obsolete
            DESCRIPTION 
                "group for obsoleted and deprecated events"
            ::= { rsXx8000FmNp1Groups 403 }

        
        groupDummyLoadRF OBJECT-GROUP
            OBJECTS { rfProbesDLFwdNominal, rfProbesDLFwdWarningLimit, rfProbesDLFwdFailLimit, rfProbesDLFwdDelayTimeRfFail, rfProbesDLFwdSetOffset, 
                rfProbesDLFwdSetGain, rfProbesDLReflWarningLimit, rfProbesDLReflSetOffset, rfProbesDLReflSetGain }
            STATUS current
            DESCRIPTION 
                "This group includes all object types regarding probes from dummy load.
                The object types in this group are defined only when a dummy load measure point exists.
                This can occur in reserve concept active reserve only.
                "
            ::= { rsXx8000FmNp1Groups 404 }

        
        groupProgramEvents NOTIFICATION-GROUP
            NOTIFICATIONS { evtProgramRfOn }
            STATUS current
            DESCRIPTION 
                "Group for all events of the program information."
            ::= { rsXx8000FmNp1Groups 405 }

        
        rsXx8000FmNp1Compl OBJECT IDENTIFIER ::= { rsXx8000FmNp1Conf 2 }

        
        rsXx8000FMNplus1MP MODULE-COMPLIANCE
            STATUS current
            DESCRIPTION 
                "This reserve concept (Nplus1 MediumPower) consists of a switchover unit (NSU-MediumPower) and MediumPower transmitters."
            MODULE -- this module
                MANDATORY-GROUPS { groupNsuObjs, groupNsuEvents, groupTxObjsMp, groupTxObjsExc, groupTxObjsLogbookNetCCU, 
                    groupTxObjsLogbookExcA, groupTxObjsLogbookOstA, groupTxObjsOstARack, groupTxObjsProductInfo, groupTxEventsMp, 
                    groupTxEventsExc, groupEventTable, groupRfProbes, groupAmpMeasureValues, groupProgramEvents
                     }
                GROUP groupTxObjsDualDrive
                    DESCRIPTION 
                        "In case of DualDrive transmitters."
                GROUP groupTxObjsLogbookExcB
                    DESCRIPTION 
                        "In case of DualDrive transmitters."
                GROUP groupTxEventsDualDrive
                    DESCRIPTION 
                        "In case of DualDrive transmitters."
                GROUP groupIndependentRacks
                    DESCRIPTION 
                        "for variant with independent racks only"
                OBJECT cmdOstRefVoltage
                    MIN-ACCESS not-accessible
                    DESCRIPTION 
                        "not accessible in variant with independent racks"
                GROUP groupTxEventsAddPowerSupply
                    DESCRIPTION 
                        "only when statusTxAdditionalPowerSupply is true"
                GROUP groupNsuEventsAddPowerSupply
                    DESCRIPTION 
                        "only when additionalPowerSupply is true"
                GROUP groupNsuObjsAddPowerSupply
                    DESCRIPTION 
                        "only when additionalPowerSupply is true"
                GROUP groupTxObjsAddPowerSupply
                    DESCRIPTION 
                        "only when statusTxAdditionalPowerSupply is true"
                GROUP groupDummyLoadRF
                    DESCRIPTION 
                        "only when a dummy load measure point exists"
            ::= { rsXx8000FmNp1Compl 2 }

        
        rsXx8000FMNplus1LpWithNetCCU MODULE-COMPLIANCE
            STATUS current
            DESCRIPTION 
                "This reserve concept (Nplus1 LowPower with NetCCU) consists of a switchover unit (NSU-LowPower) and LowPower transmitters with NetCCUs."
            MODULE -- this module
                MANDATORY-GROUPS { groupNsuObjs, groupNsuEvents, groupTxObjsLpWithNetCCU, groupTxObjsExc, groupTxObjsExcLp, 
                    groupTxObjsLogbookNetCCU, groupTxObjsLogbookExcA, groupTxObjsProductInfo, groupTxEventsLpWithNetCCU, groupTxEventsExc, 
                    groupTxEventsExcLp, groupEventTable, groupRfProbes, groupAmpMeasureValues, groupProgramEvents
                     }
                GROUP groupTxObjsDualDrive
                    DESCRIPTION 
                        "In case of DualDrive transmitters."
                GROUP groupTxObjsLogbookExcB
                    DESCRIPTION 
                        "In case of DualDrive transmitters."
                GROUP groupTxEventsDualDrive
                    DESCRIPTION 
                        "In case of DualDrive transmitters."
                GROUP groupTxEventsAddPowerSupply
                    DESCRIPTION 
                        "only when statusTxAdditionalPowerSupply is true"
                GROUP groupNsuEventsAddPowerSupply
                    DESCRIPTION 
                        "only when additionalPowerSupply is true"
                GROUP groupNsuObjsAddPowerSupply
                    DESCRIPTION 
                        "only when additionalPowerSupply is true"
                GROUP groupTxObjsAddPowerSupply
                    DESCRIPTION 
                        "only when statusTxAdditionalPowerSupply is true"
            ::= { rsXx8000FmNp1Compl 3 }

        
        rsXx8000FMNplus1LpWithoutNetCCU MODULE-COMPLIANCE
            STATUS current
            DESCRIPTION 
                "This reserve concept (Nplus1 LowPower with NetCCU) consists of a switchover unit (NSU-LowPower) and LowPower transmitters with NetCCUs."
            MODULE -- this module
                MANDATORY-GROUPS { groupNsuObjs, groupNsuEvents, groupTxObjsLpWithoutNetCCU, groupTxObjsExc, groupTxObjsExcLp, 
                    groupTxObjsLogbookExcA, groupTxObjsProductInfo, groupTxEventsLpWithoutNetCCU, groupTxEventsExc, groupTxEventsExcLp, 
                    groupEventTable, groupProgramEvents }
                GROUP groupNsuEventsAddPowerSupply
                    DESCRIPTION 
                        "only when additionalPowerSupply is true"
                GROUP groupNsuObjsAddPowerSupply
                    DESCRIPTION 
                        "only when additionalPowerSupply is true"
            ::= { rsXx8000FmNp1Compl 4 }

        
        rsXx8000FMNplus1Simple MODULE-COMPLIANCE
            STATUS current
            DESCRIPTION 
                "This reserve concept consists of a switchover unit (NSU-LowPower) and simple transmitters."
            MODULE -- this module
                MANDATORY-GROUPS { groupNsuObjs, groupNsuEvents, groupTxObjsSimple, groupTxEventsSimple, groupEventTable, 
                    groupProgramEvents }
                GROUP groupNsuEventsAddPowerSupply
                    DESCRIPTION 
                        "only when additionalPowerSupply is true"
                GROUP groupNsuObjsAddPowerSupply
                    DESCRIPTION 
                        "only when additionalPowerSupply is true"
            ::= { rsXx8000FmNp1Compl 20 }

        
    
    END
