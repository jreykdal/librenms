-- www.devavroadcast.com DB7007 MIB File.
--
-- Author                   Date        Comment
-- ==================================================================
-- Alexander Petrov         24/11/2025  DB7007
--

DB7007-MIB DEFINITIONS ::= BEGIN

IMPORTS
  DisplayString, TEXTUAL-CONVENTION FROM SNMPv2-TC
  OBJECT-GROUP FROM SNMPv2-CONF
  MODULE-IDENTITY,
  OBJECT-TYPE,
  OBJECT-IDENTITY,
  enterprises,
  IpAddress,
  Integer32,
  NOTIFICATION-TYPE  FROM SNMPv2-SMI;

devabroadcast MODULE-IDENTITY
       LAST-UPDATED "202511241500Z"
       ORGANIZATION "Deva Broadcast LTD"
       CONTACT-INFO
               "        Alexander Petrov

                E-mail: support@devabroadcast.com"

       DESCRIPTION
               "The MIB module for entities implementing the SNMPv2c
               protocol."
       REVISION     "202511241500Z"
       DESCRIPTION
               "The latest version of this MIB module."
       REVISION     "202511241400Z"
       DESCRIPTION
               " "
       ::= { enterprises 35833 }

Fr8p8 ::= TEXTUAL-CONVENTION
  STATUS      current
  DESCRIPTION 
  "Fixed point 16-bit signed value.
   Higher 8 bits represent integer part and
   Lower 8 bits represent fractional part.
  
   Fr8p8 to float conversion:
  
   float = Fr8p8 / 256;
   Fr8p8 = Round( float * 256 );

   Examples:
    Fr8p8    float
   -32768   -128.0
        .        .
     -256     -1.0
        .        .
       -1     -0.00390625
        0      0.0
        1      0.00390625
        .        .
      256      1.0
        .        .
    32767    127.99609375"
  SYNTAX      Integer32 (-32768..32767)

Fr1p15 ::= TEXTUAL-CONVENTION
  STATUS      current
  DESCRIPTION 
 "Fixed point 16-bit signed value.
   Lower 15 bits represent fractional part.
  
   Fr1p15 to float conversion:
  
   float = Fr1p15 / 32768;
   Fr1p15 = Round( float * 32768 );

   Examples:
   Fr1p15    float
   -32768     -1.0
        .        .
   -16384     -0.5
        .        .
       -1     -0.000030517578125
        0      0.0
        1      0.000030517578125
        .        .
    16384      0.5
        .        .
    32767      0.999969482421875"
  SYNTAX      Integer32 (-32768..32767)

Ix10 ::= TEXTUAL-CONVENTION
  STATUS      current
  DESCRIPTION 
 "Fixed point 16-bit signed value.
        
   Ix10 to float conversion:
  
   float = Ix10 / 10;
   Ix10 = Round( float * 10 );

   Examples:
   Ix10    float
   -32768  -3276.8
        .       .
   -16384  -1638.4
        .       .
       -1     -0.1
        0      0.0
        1      0.1
        .       .
    16384   1638.4
        .       .
    32767   3276.8"
  SYNTAX      Integer32 (-32768..32767)

Ix1000 ::= TEXTUAL-CONVENTION
  STATUS      current
  DESCRIPTION 
 "Fixed point 16-bit signed value.
        
   Ix1000 to float conversion:
  
   float = Ix1000 / 1000;
   Ix1000 = Round( float * 1000 );

   Examples:
   Ix10    float
   -32768    -32.768
        .       .
   -16384    -16.384
        .       .
       -1     -0.001
        0      0.0
        1      0.001
        .       .
    16384     16.384
        .       .
    32767     32.768"
  SYNTAX      Integer32 (-32768..32767)

db7007 OBJECT-IDENTITY
  STATUS current
  DESCRIPTION
      "DB7007 FM Radio Re-Broadcast Receiver"
    ::=  { devabroadcast 18 }

product OBJECT IDENTIFIER ::= { db7007 1 }

fwrev OBJECT-TYPE
  SYNTAX DisplayString (SIZE(0..31)) 
  MAX-ACCESS read-only
  STATUS current
  DESCRIPTION
    "Firmware revision"
  ::= { product 1 }

sernum OBJECT-TYPE
  SYNTAX DisplayString (SIZE(0..31)) 
  MAX-ACCESS read-only
  STATUS current
  DESCRIPTION
    "Serial number"
  ::= { product 2 }

settings OBJECT IDENTIFIER ::= { db7007 2 }

tuner OBJECT IDENTIFIER  ::= { settings 1 }

mainStation OBJECT IDENTIFIER  ::= { tuner 1 }

freq OBJECT-TYPE
  SYNTAX Integer32 (87100..108000)
  MAX-ACCESS read-only
  STATUS current
  DESCRIPTION
    "Currently set frequency"
  ::= { mainStation 1 }

att OBJECT-TYPE
  SYNTAX INTEGER {attAuto(0),attOFF(1),att10dB(2),att20dB(3),att30dB(4)}
  MAX-ACCESS read-write
  STATUS current
  DESCRIPTION
    "Attenuator setting for antenna input 1"
  ::= { mainStation 2 }

rflossth OBJECT-TYPE
  SYNTAX Integer32 (0..110)
  MAX-ACCESS read-write
  STATUS current
  DESCRIPTION
    "RF threshold level"
  ::= { mainStation 3 }

rflosstout OBJECT-TYPE
  SYNTAX Integer32 (1..60)
  MAX-ACCESS read-write
  STATUS current
  DESCRIPTION
    "RF timeout"
  ::= { mainStation 4 }

piproten OBJECT-TYPE
  SYNTAX INTEGER {altEnable(3),altDisable(4)}
  MAX-ACCESS read-write
  STATUS current
  DESCRIPTION
    "PI Protection Enable"
  ::= { mainStation 5 }

piprot OBJECT-TYPE
  SYNTAX Integer32 (0..65535)
  MAX-ACCESS read-write
  STATUS current
  DESCRIPTION
    "PI Protection code"
  ::= { mainStation 6 }

rfgain OBJECT-TYPE
  SYNTAX Integer32 (-100..100)
  MAX-ACCESS read-write
  STATUS current
  DESCRIPTION
    "Audio Gain adjust"
  ::= { mainStation 7 }

backupStation OBJECT IDENTIFIER  ::= { tuner 2 }

altsfreq OBJECT-TYPE
  SYNTAX Integer32 (87100..108000)
  MAX-ACCESS read-write
  STATUS current
  DESCRIPTION
    "Alternative station frequency"
  ::= { backupStation 1 }

altsatt OBJECT-TYPE
  SYNTAX INTEGER {attAuto(0),attOFF(1),att10dB(2),att20dB(3),att30dB(4)}
  MAX-ACCESS read-write
  STATUS current
  DESCRIPTION
    "Attenuator setting for antenna input 2"
  ::= { backupStation 2 }

altsrflossth OBJECT-TYPE
  SYNTAX Integer32 (0..110)
  MAX-ACCESS read-write
  STATUS current
  DESCRIPTION
    "RF threshold level"
  ::= { backupStation 3 }

altsrflosstout OBJECT-TYPE
  SYNTAX Integer32 (1..60)
  MAX-ACCESS read-write
  STATUS current
  DESCRIPTION
    "RF timeout"
  ::= { backupStation 4 }

altspiproten OBJECT-TYPE
  SYNTAX INTEGER {altEnable(3),altDisable(4)}
  MAX-ACCESS read-write
  STATUS current
  DESCRIPTION
    "PI Protection Enable"
  ::= { backupStation 5 }

altspiprot OBJECT-TYPE
  SYNTAX Integer32 (0..65535)
  MAX-ACCESS read-write
  STATUS current
  DESCRIPTION
    "PI Protection code"
  ::= { backupStation 6 }

altsgain OBJECT-TYPE
  SYNTAX Integer32 (-100..100)
  MAX-ACCESS read-write
  STATUS current
  DESCRIPTION
    "Audio Gain adjust"
  ::= { backupStation 7 }

freqstep OBJECT-TYPE
  SYNTAX INTEGER {freqstep10kHz(0),freqstep20kHz(1),freqstep50kHz(2),freqstep100kHz(3),freqstep200kHz(4)}
  MAX-ACCESS read-write
  STATUS current
  DESCRIPTION
    "Step for frequency tuning"
  ::= { tuner 3 }

deemph OBJECT-TYPE
  SYNTAX INTEGER {deemphFLAT(0),deemph50uS(1),deemph75uS(2)}
  MAX-ACCESS read-write
  STATUS current
  DESCRIPTION
    "De-emphasis settings"
  ::= { tuner 4 }

rdsmode OBJECT-TYPE
  SYNTAX INTEGER {rdsmodeRDS(0),rdsmodeRBDS(1)}
  MAX-ACCESS read-write
  STATUS current
  DESCRIPTION
    "RDS decoder mode"
  ::= { tuner 5 }

ifbw OBJECT-TYPE
  SYNTAX INTEGER {ifbw27kHz(0),ifbw36kHz(1),ifbw45kHz(2),ifbw53kHz(3),ifbw62kHz(4),ifbw71kHz(5),ifbw79kHz(6),ifbw88kHz(7),ifbw97kHz(8),ifbw105kHz(9),ifbw114kHz(10),ifbw123kHz(11),ifbw131kHz(12),ifbw140kHz(13),ifbw149kHz(14),ifbw157kHz(15),ifbwAuto(16)}
  MAX-ACCESS read-write
  STATUS current
  DESCRIPTION
    "IF filter bandwidth"
  ::= { tuner 6 }

stblend OBJECT-TYPE
  SYNTAX INTEGER {altAuto(0),altOff(1)}
  MAX-ACCESS read-write
  STATUS current
  DESCRIPTION
    "Stereo blend level"
  ::= { tuner 7 }

hicut OBJECT-TYPE
  SYNTAX INTEGER {altAuto(0),altOff(1)}
  MAX-ACCESS read-write
  STATUS current
  DESCRIPTION
    "High cut level"
  ::= { tuner 8 }

hiblend OBJECT-TYPE
  SYNTAX INTEGER {altAuto(0),altOff(1)}
  MAX-ACCESS read-write
  STATUS current
  DESCRIPTION
    "High blend level"
  ::= { tuner 9 }

smute OBJECT-TYPE
  SYNTAX INTEGER {altAuto(0),altOff(1)}
  MAX-ACCESS read-write
  STATUS current
  DESCRIPTION
    "Soft mute level"
  ::= { tuner 10 }

averageAndPeak OBJECT IDENTIFIER  ::= { tuner 12 }

avratck OBJECT-TYPE
  SYNTAX Integer32 (0..500)
  MAX-ACCESS read-write
  STATUS current
  DESCRIPTION
    "Attack time for signal measuring"
  ::= { averageAndPeak 1 }

avrrel OBJECT-TYPE
  SYNTAX Integer32 (50..1000)
  MAX-ACCESS read-write
  STATUS current
  DESCRIPTION
    "Release time for signal measuring"
  ::= { averageAndPeak 2 }

peakhold OBJECT-TYPE
  SYNTAX Integer32 (500..5000)
  MAX-ACCESS read-write
  STATUS current
  DESCRIPTION
    "Peak hold time"
  ::= { averageAndPeak 3 }

backup OBJECT IDENTIFIER  ::= { settings 2 }

srcmain OBJECT-TYPE
  SYNTAX INTEGER {inselMainStation(1)}
  MAX-ACCESS read-write
  STATUS current
  DESCRIPTION
    "Main audio source"
  ::= { backup 1 }

backup1 OBJECT-TYPE
  SYNTAX INTEGER {inselNotUsed(0),inselMainStation(1),inselBackupStation(2),inselMP3Player(3),inselRTPAudioReceiver(4),inselIPAudioClient1(5)}
  MAX-ACCESS read-write
  STATUS current
  DESCRIPTION
    "Backup audio source 1"
  ::= { backup 2 }

backup2 OBJECT-TYPE
  SYNTAX INTEGER {inselNotUsed(0),inselMainStation(1),inselBackupStation(2),inselMP3Player(3),inselRTPAudioReceiver(4),inselIPAudioClient1(5)}
  MAX-ACCESS read-write
  STATUS current
  DESCRIPTION
    "Backup audio source 2"
  ::= { backup 3 }

backup3 OBJECT-TYPE
  SYNTAX INTEGER {inselNotUsed(0),inselMainStation(1),inselBackupStation(2),inselMP3Player(3),inselRTPAudioReceiver(4),inselIPAudioClient1(5)}
  MAX-ACCESS read-write
  STATUS current
  DESCRIPTION
    "Backup audio source 3"
  ::= { backup 4 }

aulossth OBJECT-TYPE
  SYNTAX Integer32 (-900..0)
  MAX-ACCESS read-write
  STATUS current
  DESCRIPTION
    "Audio Loss Threshold"
  ::= { backup 5 }

aulosstout OBJECT-TYPE
  SYNTAX Integer32 (1..240)
  MAX-ACCESS read-write
  STATUS current
  DESCRIPTION
    "Audio Loss Timeout"
  ::= { backup 6 }

aurecth OBJECT-TYPE
  SYNTAX Integer32 (-900..0)
  MAX-ACCESS read-write
  STATUS current
  DESCRIPTION
    "Audio Recover Threshold"
  ::= { backup 7 }

aurectout OBJECT-TYPE
  SYNTAX Integer32 (1..240)
  MAX-ACCESS read-write
  STATUS current
  DESCRIPTION
    "Audio Recoder Timeout"
  ::= { backup 8 }

ipAudioClient OBJECT IDENTIFIER  ::= { backup 9 }

strmurl1 OBJECT-TYPE
  SYNTAX DisplayString (SIZE(0..255)) 
  MAX-ACCESS read-write
  STATUS current
  DESCRIPTION
    "Server URL and port"
  ::= { ipAudioClient 1 }

strmdec1 OBJECT-TYPE
  SYNTAX INTEGER {decAuto(1),decMP3Auto(2),decHEAACAuto(3),decPCM32kHz(4),decPCM441kHz(5),decPCM48kHz(6)}
  MAX-ACCESS read-write
  STATUS current
  DESCRIPTION
    "Decoder"
  ::= { ipAudioClient 2 }

strmgain1 OBJECT-TYPE
  SYNTAX Integer32 (-100..100)
  MAX-ACCESS read-write
  STATUS current
  DESCRIPTION
    "Audio Gain adjust"
  ::= { ipAudioClient 3 }

strmprebuf1 OBJECT-TYPE
  SYNTAX Integer32 (500..10000)
  MAX-ACCESS read-write
  STATUS current
  DESCRIPTION
    "Data pre-buffer"
  ::= { ipAudioClient 4 }

strmconn1 OBJECT-TYPE
  SYNTAX INTEGER {connectionAlwaysON(0),connectionOnDemand(1)}
  MAX-ACCESS read-write
  STATUS current
  DESCRIPTION
    "Connection"
  ::= { ipAudioClient 5 }

rtpReceiver OBJECT IDENTIFIER  ::= { backup 10 }

rtprcvport OBJECT-TYPE
  SYNTAX Integer32 (1..65535)
  MAX-ACCESS read-write
  STATUS current
  DESCRIPTION
    "Receiver Port"
  ::= { rtpReceiver 1 }

rtprcvmcast OBJECT-TYPE
  SYNTAX IpAddress 
  MAX-ACCESS read-write
  STATUS current
  DESCRIPTION
    "Multicast group"
  ::= { rtpReceiver 2 }

rtprcvdec OBJECT-TYPE
  SYNTAX INTEGER {decMP3Auto(2),decHEAACAuto(3),decPCM32kHz(4),decPCM441kHz(5),decPCM48kHz(6)}
  MAX-ACCESS read-write
  STATUS current
  DESCRIPTION
    "Decoder"
  ::= { rtpReceiver 3 }

rtprcvgain OBJECT-TYPE
  SYNTAX Integer32 (-100..100)
  MAX-ACCESS read-write
  STATUS current
  DESCRIPTION
    "Audio Gain adjust"
  ::= { rtpReceiver 4 }

rtprcvprebuf OBJECT-TYPE
  SYNTAX Integer32 (0..1000)
  MAX-ACCESS read-write
  STATUS current
  DESCRIPTION
    "Data pre-buffer"
  ::= { rtpReceiver 5 }

fporder OBJECT-TYPE
  SYNTAX INTEGER {playerAZ(0),playerZA(1),playerShuffle(2),playerPlaylist(3),playerShuffledPlaylist(4)}
  MAX-ACCESS read-write
  STATUS current
  DESCRIPTION
    "Backup file player order"
  ::= { backup 11 }

mpxGenerator OBJECT IDENTIFIER  ::= { settings 3 }

mpxsrc OBJECT-TYPE
  SYNTAX INTEGER {mpxsrcRAWMPX(0),mpxsrcStereoGen(1),mpxsrcTestTone400Hz(2)}
  MAX-ACCESS read-write
  STATUS current
  DESCRIPTION
    "MPX Source"
  ::= { mpxGenerator 1 }

stmode OBJECT-TYPE
  SYNTAX INTEGER {altMono(8),altStereo(9)}
  MAX-ACCESS read-write
  STATUS current
  DESCRIPTION
    "Stereo mode"
  ::= { mpxGenerator 2 }

preemph OBJECT-TYPE
  SYNTAX INTEGER {deemphFLAT(0),deemph50uS(1),deemph75uS(2)}
  MAX-ACCESS read-write
  STATUS current
  DESCRIPTION
    "Pre Emphasis"
  ::= { mpxGenerator 3 }

injaudio OBJECT-TYPE
  SYNTAX Fr8p8 (-3072..768)
  MAX-ACCESS read-write
  STATUS current
  DESCRIPTION
    "Audio gain for MPX"
  ::= { mpxGenerator 4 }

injpilot OBJECT-TYPE
  SYNTAX Fr8p8 (0..2560)
  MAX-ACCESS read-write
  STATUS current
  DESCRIPTION
    "Pilot injection level"
  ::= { mpxGenerator 5 }

injrds OBJECT-TYPE
  SYNTAX Fr8p8 (0..2560)
  MAX-ACCESS read-write
  STATUS current
  DESCRIPTION
    "RDS injection level"
  ::= { mpxGenerator 6 }

phpilot OBJECT-TYPE
  SYNTAX Ix10 (-100..100)
  MAX-ACCESS read-write
  STATUS current
  DESCRIPTION
    "Pilot phase adjustment"
  ::= { mpxGenerator 7 }

mpxlimen OBJECT-TYPE
  SYNTAX INTEGER {altEnable(3),altDisable(4)}
  MAX-ACCESS read-write
  STATUS current
  DESCRIPTION
    "MPX Limiter"
  ::= { mpxGenerator 8 }

mpxlimth OBJECT-TYPE
  SYNTAX Integer32 (-1280..2560)
  MAX-ACCESS read-write
  STATUS current
  DESCRIPTION
    "MPX Limiter threshold"
  ::= { mpxGenerator 9 }

rdsEncoder OBJECT IDENTIFIER  ::= { settings 4 }

rdssrc OBJECT-TYPE
  SYNTAX INTEGER {rdssrcOriginal(0),rdssrcLocalFallback(1),rdssrcLocal(2),rdssrcReplace(3)}
  MAX-ACCESS read-write
  STATUS current
  DESCRIPTION
    "RDS Data Source"
  ::= { rdsEncoder 1 }

rdspi OBJECT-TYPE
  SYNTAX Integer32 (0..65535)
  MAX-ACCESS read-write
  STATUS current
  DESCRIPTION
    "Local PI"
  ::= { rdsEncoder 2 }

rdsps OBJECT-TYPE
  SYNTAX DisplayString (SIZE(0..31)) 
  MAX-ACCESS read-write
  STATUS current
  DESCRIPTION
    "Local PS"
  ::= { rdsEncoder 3 }

rdsrt OBJECT-TYPE
  SYNTAX DisplayString (SIZE(0..67)) 
  MAX-ACCESS read-write
  STATUS current
  DESCRIPTION
    "Local Radio Text"
  ::= { rdsEncoder 4 }

rdspty OBJECT-TYPE
  SYNTAX INTEGER {rdsptyNone(0),rdsptyNews(1),rdsptyCurrentAffairs(2),rdsptyInfo(3),rdsptySport(4),rdsptyEducation(5),rdsptyDrama(6),rdsptyCultures(7),rdsptyScience(8),rdsptyVariedSpeech(9),rdsptyPopMusic(10),rdsptyRockMusic(11),rdsptyEasyListening(12),rdsptyLightClassicsM(13),rdsptySeriousClassics(14),rdsptyOtherMusic(15),rdsptyWeather(16),rdsptyFinance(17),rdsptyChildrensProgs(18),rdsptySocialAffairs(19),rdsptyReligion(20),rdsptyPhoneIn(21),rdsptyTravelTouring(22),rdsptyLeisureHobby(23),rdsptyJazzMusic(24),rdsptyCountryMusic(25),rdsptyNationalMusic(26),rdsptyOldiesMusic(27),rdsptyFolkMusic(28),rdsptyDocumentary(29),rdsptyAlarmTest(30),rdsptyAlarmAlarm(31)}
  MAX-ACCESS read-write
  STATUS current
  DESCRIPTION
    "Local PTY"
  ::= { rdsEncoder 5 }

rdsms OBJECT-TYPE
  SYNTAX INTEGER {altSpeech(10),altMusic(11)}
  MAX-ACCESS read-write
  STATUS current
  DESCRIPTION
    "Local MS flag"
  ::= { rdsEncoder 6 }

rdstp OBJECT-TYPE
  SYNTAX INTEGER {altOff(1),altOn(2)}
  MAX-ACCESS read-write
  STATUS current
  DESCRIPTION
    "Local TP flag"
  ::= { rdsEncoder 7 }

rdsta OBJECT-TYPE
  SYNTAX INTEGER {altOff(1),altOn(2)}
  MAX-ACCESS read-write
  STATUS current
  DESCRIPTION
    "Local TA flag"
  ::= { rdsEncoder 8 }

diFlags OBJECT IDENTIFIER  ::= { rdsEncoder 9 }

rdsdi0 OBJECT-TYPE
  SYNTAX INTEGER {altOff(1),altOn(2)}
  MAX-ACCESS read-write
  STATUS current
  DESCRIPTION
    "DI Flag Stereo"
  ::= { diFlags 1 }

rdsdi1 OBJECT-TYPE
  SYNTAX INTEGER {altOff(1),altOn(2)}
  MAX-ACCESS read-write
  STATUS current
  DESCRIPTION
    "DI Flag Artificial Head"
  ::= { diFlags 2 }

rdsdi2 OBJECT-TYPE
  SYNTAX INTEGER {altOff(1),altOn(2)}
  MAX-ACCESS read-write
  STATUS current
  DESCRIPTION
    "DI Flag Compressed"
  ::= { diFlags 3 }

rdsdi3 OBJECT-TYPE
  SYNTAX INTEGER {altOff(1),altOn(2)}
  MAX-ACCESS read-write
  STATUS current
  DESCRIPTION
    "DI Flag Dynamic PTY"
  ::= { diFlags 4 }

afList OBJECT IDENTIFIER  ::= { rdsEncoder 10 }

rdsafcount OBJECT-TYPE
  SYNTAX Integer32 (0..25)
  MAX-ACCESS read-write
  STATUS current
  DESCRIPTION
    "Local AF List length"
  ::= { afList 1 }

rdsaf1 OBJECT-TYPE
  SYNTAX Integer32 (87600..107900)
  MAX-ACCESS read-write
  STATUS current
  DESCRIPTION
    "Local AF 1"
  ::= { afList 2 }

rdsaf2 OBJECT-TYPE
  SYNTAX Integer32 (87600..107900)
  MAX-ACCESS read-write
  STATUS current
  DESCRIPTION
    "Local AF 2"
  ::= { afList 3 }

rdsaf3 OBJECT-TYPE
  SYNTAX Integer32 (87600..107900)
  MAX-ACCESS read-write
  STATUS current
  DESCRIPTION
    "Local AF 3"
  ::= { afList 4 }

rdsaf4 OBJECT-TYPE
  SYNTAX Integer32 (87600..107900)
  MAX-ACCESS read-write
  STATUS current
  DESCRIPTION
    "Local AF 4"
  ::= { afList 5 }

rdsaf5 OBJECT-TYPE
  SYNTAX Integer32 (87600..107900)
  MAX-ACCESS read-write
  STATUS current
  DESCRIPTION
    "Local AF 5"
  ::= { afList 6 }

rdsaf6 OBJECT-TYPE
  SYNTAX Integer32 (87600..107900)
  MAX-ACCESS read-write
  STATUS current
  DESCRIPTION
    "Local AF 6"
  ::= { afList 7 }

rdsaf7 OBJECT-TYPE
  SYNTAX Integer32 (87600..107900)
  MAX-ACCESS read-write
  STATUS current
  DESCRIPTION
    "Local AF 7"
  ::= { afList 8 }

rdsaf8 OBJECT-TYPE
  SYNTAX Integer32 (87600..107900)
  MAX-ACCESS read-write
  STATUS current
  DESCRIPTION
    "Local AF 8"
  ::= { afList 9 }

rdsaf9 OBJECT-TYPE
  SYNTAX Integer32 (87600..107900)
  MAX-ACCESS read-write
  STATUS current
  DESCRIPTION
    "Local AF 9"
  ::= { afList 10 }

rdsaf10 OBJECT-TYPE
  SYNTAX Integer32 (87600..107900)
  MAX-ACCESS read-write
  STATUS current
  DESCRIPTION
    "Local AF 10"
  ::= { afList 11 }

rdsaf11 OBJECT-TYPE
  SYNTAX Integer32 (87600..107900)
  MAX-ACCESS read-write
  STATUS current
  DESCRIPTION
    "Local AF 11"
  ::= { afList 12 }

rdsaf12 OBJECT-TYPE
  SYNTAX Integer32 (87600..107900)
  MAX-ACCESS read-write
  STATUS current
  DESCRIPTION
    "Local AF 12"
  ::= { afList 13 }

rdsaf13 OBJECT-TYPE
  SYNTAX Integer32 (87600..107900)
  MAX-ACCESS read-write
  STATUS current
  DESCRIPTION
    "Local AF 13"
  ::= { afList 14 }

rdsaf14 OBJECT-TYPE
  SYNTAX Integer32 (87600..107900)
  MAX-ACCESS read-write
  STATUS current
  DESCRIPTION
    "Local AF 14"
  ::= { afList 15 }

rdsaf15 OBJECT-TYPE
  SYNTAX Integer32 (87600..107900)
  MAX-ACCESS read-write
  STATUS current
  DESCRIPTION
    "Local AF 15"
  ::= { afList 16 }

rdsaf16 OBJECT-TYPE
  SYNTAX Integer32 (87600..107900)
  MAX-ACCESS read-write
  STATUS current
  DESCRIPTION
    "Local AF 16"
  ::= { afList 17 }

rdsaf17 OBJECT-TYPE
  SYNTAX Integer32 (87600..107900)
  MAX-ACCESS read-write
  STATUS current
  DESCRIPTION
    "Local AF 17"
  ::= { afList 18 }

rdsaf18 OBJECT-TYPE
  SYNTAX Integer32 (87600..107900)
  MAX-ACCESS read-write
  STATUS current
  DESCRIPTION
    "Local AF 18"
  ::= { afList 19 }

rdsaf19 OBJECT-TYPE
  SYNTAX Integer32 (87600..107900)
  MAX-ACCESS read-write
  STATUS current
  DESCRIPTION
    "Local AF 19"
  ::= { afList 20 }

rdsaf20 OBJECT-TYPE
  SYNTAX Integer32 (87600..107900)
  MAX-ACCESS read-write
  STATUS current
  DESCRIPTION
    "Local AF 20"
  ::= { afList 21 }

rdsaf21 OBJECT-TYPE
  SYNTAX Integer32 (87600..107900)
  MAX-ACCESS read-write
  STATUS current
  DESCRIPTION
    "Local AF 21"
  ::= { afList 22 }

rdsaf22 OBJECT-TYPE
  SYNTAX Integer32 (87600..107900)
  MAX-ACCESS read-write
  STATUS current
  DESCRIPTION
    "Local AF 22"
  ::= { afList 23 }

rdsaf23 OBJECT-TYPE
  SYNTAX Integer32 (87600..107900)
  MAX-ACCESS read-write
  STATUS current
  DESCRIPTION
    "Local AF 23"
  ::= { afList 24 }

rdsaf24 OBJECT-TYPE
  SYNTAX Integer32 (87600..107900)
  MAX-ACCESS read-write
  STATUS current
  DESCRIPTION
    "Local AF 24"
  ::= { afList 25 }

rdsaf25 OBJECT-TYPE
  SYNTAX Integer32 (87600..107900)
  MAX-ACCESS read-write
  STATUS current
  DESCRIPTION
    "Local AF 25"
  ::= { afList 26 }

rdsreplpi OBJECT-TYPE
  SYNTAX INTEGER {altEnable(3),altDisable(4)}
  MAX-ACCESS read-write
  STATUS current
  DESCRIPTION
    "Replace PI with local"
  ::= { rdsEncoder 11 }

rdsreplps OBJECT-TYPE
  SYNTAX INTEGER {altEnable(3),altDisable(4)}
  MAX-ACCESS read-write
  STATUS current
  DESCRIPTION
    "Replace PS with local"
  ::= { rdsEncoder 12 }

rdsreplrt OBJECT-TYPE
  SYNTAX INTEGER {altEnable(3),altDisable(4)}
  MAX-ACCESS read-write
  STATUS current
  DESCRIPTION
    "Replace Radio text with local"
  ::= { rdsEncoder 13 }

rdsreplpty OBJECT-TYPE
  SYNTAX INTEGER {altEnable(3),altDisable(4)}
  MAX-ACCESS read-write
  STATUS current
  DESCRIPTION
    "Replace PTY with local"
  ::= { rdsEncoder 14 }

rdsreplms OBJECT-TYPE
  SYNTAX INTEGER {altEnable(3),altDisable(4)}
  MAX-ACCESS read-write
  STATUS current
  DESCRIPTION
    "Replace MS with local"
  ::= { rdsEncoder 15 }

rdsrepltp OBJECT-TYPE
  SYNTAX INTEGER {altEnable(3),altDisable(4)}
  MAX-ACCESS read-write
  STATUS current
  DESCRIPTION
    "Replace TP with local"
  ::= { rdsEncoder 16 }

rdsreplta OBJECT-TYPE
  SYNTAX INTEGER {altEnable(3),altDisable(4)}
  MAX-ACCESS read-write
  STATUS current
  DESCRIPTION
    "Replace TA with local"
  ::= { rdsEncoder 17 }

rdsrepldi OBJECT-TYPE
  SYNTAX INTEGER {altEnable(3),altDisable(4)}
  MAX-ACCESS read-write
  STATUS current
  DESCRIPTION
    "Replace DI with local"
  ::= { rdsEncoder 18 }

rdsreplaf OBJECT-TYPE
  SYNTAX INTEGER {altEnable(3),altDisable(4)}
  MAX-ACCESS read-write
  STATUS current
  DESCRIPTION
    "Replace AF with local"
  ::= { rdsEncoder 19 }

communication OBJECT IDENTIFIER  ::= { settings 5 }

generalSetup OBJECT IDENTIFIER  ::= { communication 1 }

ethen OBJECT-TYPE
  SYNTAX INTEGER {altEnable(3),altDisable(4)}
  MAX-ACCESS read-write
  STATUS current
  DESCRIPTION
    "Ethernet port (general)"
  ::= { generalSetup 1 }

snmpen OBJECT-TYPE
  SYNTAX INTEGER {altEnable(3),altDisable(4)}
  MAX-ACCESS read-write
  STATUS current
  DESCRIPTION
    "SNMP protocol"
  ::= { generalSetup 2 }

appen OBJECT-TYPE
  SYNTAX INTEGER {altEnable(3),altDisable(4)}
  MAX-ACCESS read-write
  STATUS current
  DESCRIPTION
    "Application proprietary protocol"
  ::= { generalSetup 3 }

httpen OBJECT-TYPE
  SYNTAX INTEGER {altEnable(3),altDisable(4)}
  MAX-ACCESS read-write
  STATUS current
  DESCRIPTION
    "HTTP protocol (WEB server)"
  ::= { generalSetup 4 }

ftpen OBJECT-TYPE
  SYNTAX INTEGER {altEnable(3),altDisable(4)}
  MAX-ACCESS read-write
  STATUS current
  DESCRIPTION
    "FTP protocol"
  ::= { generalSetup 5 }

emailen OBJECT-TYPE
  SYNTAX INTEGER {smtpconnDEVAAccount(3),smtpconnSMTPAccount(4),smtpconnDisabled(5)}
  MAX-ACCESS read-write
  STATUS current
  DESCRIPTION
    "SMTP protocol (email)"
  ::= { generalSetup 6 }

sntpen OBJECT-TYPE
  SYNTAX INTEGER {altEnable(3),altDisable(4)}
  MAX-ACCESS read-write
  STATUS current
  DESCRIPTION
    "SNTP protocol (Internet time)"
  ::= { generalSetup 7 }

streamen OBJECT-TYPE
  SYNTAX INTEGER {altEnable(3),altDisable(4)}
  MAX-ACCESS read-write
  STATUS current
  DESCRIPTION
    "Audio streaming"
  ::= { generalSetup 8 }

syslogen OBJECT-TYPE
  SYNTAX INTEGER {altEnable(3),altDisable(4)}
  MAX-ACCESS read-write
  STATUS current
  DESCRIPTION
    "SYSLOG protocol"
  ::= { generalSetup 9 }

uecpsrven OBJECT-TYPE
  SYNTAX INTEGER {altEnable(3),altDisable(4)}
  MAX-ACCESS read-write
  STATUS current
  DESCRIPTION
    "UECP TCP Server"
  ::= { generalSetup 10 }

uecprelen OBJECT-TYPE
  SYNTAX INTEGER {altEnable(3),altDisable(4)}
  MAX-ACCESS read-write
  STATUS current
  DESCRIPTION
    "UECP UDP Relay"
  ::= { generalSetup 11 }

usben OBJECT-TYPE
  SYNTAX INTEGER {altEnable(3),altDisable(4)}
  MAX-ACCESS read-write
  STATUS current
  DESCRIPTION
    "USB port"
  ::= { generalSetup 12 }

upnpen OBJECT-TYPE
  SYNTAX INTEGER {altEnable(3),altDisable(4)}
  MAX-ACCESS read-write
  STATUS current
  DESCRIPTION
    "UPnP protocol"
  ::= { generalSetup 13 }

ethernet OBJECT IDENTIFIER  ::= { communication 2 }

dhcpen OBJECT-TYPE
  SYNTAX INTEGER {altEnable(3),altDisable(4)}
  MAX-ACCESS read-write
  STATUS current
  DESCRIPTION
    "DHCP Client"
  ::= { ethernet 1 }

ip OBJECT-TYPE
  SYNTAX IpAddress 
  MAX-ACCESS read-write
  STATUS current
  DESCRIPTION
    "IP address (static)"
  ::= { ethernet 2 }

netmask OBJECT-TYPE
  SYNTAX IpAddress 
  MAX-ACCESS read-write
  STATUS current
  DESCRIPTION
    "Network mask  (static)"
  ::= { ethernet 3 }

gwip OBJECT-TYPE
  SYNTAX IpAddress 
  MAX-ACCESS read-write
  STATUS current
  DESCRIPTION
    "Gateway address (static)"
  ::= { ethernet 4 }

dns1ip OBJECT-TYPE
  SYNTAX IpAddress 
  MAX-ACCESS read-write
  STATUS current
  DESCRIPTION
    "Primary DNS IP address (static)"
  ::= { ethernet 5 }

dns2ip OBJECT-TYPE
  SYNTAX IpAddress 
  MAX-ACCESS read-write
  STATUS current
  DESCRIPTION
    "Secondary DNS IP address (static)"
  ::= { ethernet 6 }

snmp OBJECT IDENTIFIER  ::= { communication 3 }

snmpmip OBJECT-TYPE
  SYNTAX IpAddress 
  MAX-ACCESS read-write
  STATUS current
  DESCRIPTION
    "Manager IP address"
  ::= { snmp 1 }

snmpmport OBJECT-TYPE
  SYNTAX Integer32 (1..65535)
  MAX-ACCESS read-write
  STATUS current
  DESCRIPTION
    "Manager port"
  ::= { snmp 2 }

snmpaport OBJECT-TYPE
  SYNTAX Integer32 (1..65535)
  MAX-ACCESS read-write
  STATUS current
  DESCRIPTION
    "Agent port"
  ::= { snmp 3 }

snmpaid OBJECT-TYPE
  SYNTAX Integer32 (0..255)
  MAX-ACCESS read-write
  STATUS current
  DESCRIPTION
    "Agent ID for the device"
  ::= { snmp 4 }

snmprcomm OBJECT-TYPE
  SYNTAX DisplayString (SIZE(0..31)) 
  MAX-ACCESS read-write
  STATUS current
  DESCRIPTION
    "Read community password"
  ::= { snmp 5 }

snmpwcomm OBJECT-TYPE
  SYNTAX DisplayString (SIZE(0..31)) 
  MAX-ACCESS read-write
  STATUS current
  DESCRIPTION
    "Write community password"
  ::= { snmp 6 }

snmptout OBJECT-TYPE
  SYNTAX Integer32 (10..3600)
  MAX-ACCESS read-write
  STATUS current
  DESCRIPTION
    "Inactivity timeout - for SNMP write only"
  ::= { snmp 7 }

application OBJECT IDENTIFIER  ::= { communication 4 }

appport OBJECT-TYPE
  SYNTAX Integer32 (1..65535)
  MAX-ACCESS read-write
  STATUS current
  DESCRIPTION
    "Application port"
  ::= { application 1 }

apptout OBJECT-TYPE
  SYNTAX Integer32 (10..3600)
  MAX-ACCESS read-write
  STATUS current
  DESCRIPTION
    "Application inactivity timeout"
  ::= { application 2 }

http OBJECT IDENTIFIER  ::= { communication 5 }

httpport OBJECT-TYPE
  SYNTAX Integer32 (1..65535)
  MAX-ACCESS read-write
  STATUS current
  DESCRIPTION
    "WEB server port"
  ::= { http 1 }

httptout OBJECT-TYPE
  SYNTAX Integer32 (0..3600)
  MAX-ACCESS read-write
  STATUS current
  DESCRIPTION
    "WEB session timeout"
  ::= { http 2 }

ftp OBJECT IDENTIFIER  ::= { communication 6 }

ftpdport OBJECT-TYPE
  SYNTAX Integer32 (1..65535)
  MAX-ACCESS read-write
  STATUS current
  DESCRIPTION
    "FTP data port"
  ::= { ftp 1 }

ftpcport OBJECT-TYPE
  SYNTAX Integer32 (1..65535)
  MAX-ACCESS read-write
  STATUS current
  DESCRIPTION
    "FTP command port"
  ::= { ftp 2 }

sntp OBJECT IDENTIFIER  ::= { communication 7 }

sntpsrv OBJECT-TYPE
  SYNTAX DisplayString (SIZE(0..255)) 
  MAX-ACCESS read-write
  STATUS current
  DESCRIPTION
    "Time server host name"
  ::= { sntp 1 }

sntpport OBJECT-TYPE
  SYNTAX Integer32 (1..65535)
  MAX-ACCESS read-write
  STATUS current
  DESCRIPTION
    "Time server port"
  ::= { sntp 2 }

email OBJECT IDENTIFIER  ::= { communication 8 }

smtpsrv OBJECT-TYPE
  SYNTAX DisplayString (SIZE(0..255)) 
  MAX-ACCESS read-write
  STATUS current
  DESCRIPTION
    "Outgoing server host name"
  ::= { email 1 }

smtpport OBJECT-TYPE
  SYNTAX Integer32 (1..65535)
  MAX-ACCESS read-write
  STATUS current
  DESCRIPTION
    "Outgoing server port"
  ::= { email 2 }

email1 OBJECT-TYPE
  SYNTAX DisplayString (SIZE(0..63)) 
  MAX-ACCESS read-write
  STATUS current
  DESCRIPTION
    "First recipient email address"
  ::= { email 3 }

email2 OBJECT-TYPE
  SYNTAX DisplayString (SIZE(0..63)) 
  MAX-ACCESS read-write
  STATUS current
  DESCRIPTION
    "Second recipient email address"
  ::= { email 4 }

smtpsender OBJECT-TYPE
  SYNTAX DisplayString (SIZE(0..31)) 
  MAX-ACCESS read-write
  STATUS current
  DESCRIPTION
    "Sender name"
  ::= { email 5 }

smtpuname OBJECT-TYPE
  SYNTAX DisplayString (SIZE(0..31)) 
  MAX-ACCESS read-write
  STATUS current
  DESCRIPTION
    "Outgoing server user name"
  ::= { email 6 }

smtpupass OBJECT-TYPE
  SYNTAX DisplayString (SIZE(0..31)) 
  MAX-ACCESS read-write
  STATUS current
  DESCRIPTION
    "Outgoing server password"
  ::= { email 7 }

smtphostname OBJECT-TYPE
  SYNTAX DisplayString (SIZE(0..255)) 
  MAX-ACCESS read-write
  STATUS current
  DESCRIPTION
    "Client Hostname"
  ::= { email 8 }

smtpconntype OBJECT-TYPE
  SYNTAX INTEGER {smtpconnRegular(0),smtpconnSTARTTLS(1),smtpconnEncrypted(2)}
  MAX-ACCESS read-write
  STATUS current
  DESCRIPTION
    "Connection Type"
  ::= { email 9 }

streamer OBJECT IDENTIFIER  ::= { communication 9 }

strmport OBJECT-TYPE
  SYNTAX Integer32 (1..65535)
  MAX-ACCESS read-write
  STATUS current
  DESCRIPTION
    "Audio streamer server port"
  ::= { streamer 1 }

strmbps OBJECT-TYPE
  SYNTAX Integer32 (64..256)
  MAX-ACCESS read-write
  STATUS current
  DESCRIPTION
    "Audio bitrate"
  ::= { streamer 2 }

syslog OBJECT IDENTIFIER  ::= { communication 10 }

slogsrv OBJECT-TYPE
  SYNTAX DisplayString (SIZE(0..255)) 
  MAX-ACCESS read-write
  STATUS current
  DESCRIPTION
    "Server host name"
  ::= { syslog 1 }

slogport OBJECT-TYPE
  SYNTAX Integer32 (1..65535)
  MAX-ACCESS read-write
  STATUS current
  DESCRIPTION
    "Server port"
  ::= { syslog 2 }

uecpTpcServer OBJECT IDENTIFIER  ::= { communication 11 }

uecpsrvport OBJECT-TYPE
  SYNTAX Integer32 (1..65535)
  MAX-ACCESS read-write
  STATUS current
  DESCRIPTION
    "UECP TCP server port"
  ::= { uecpTpcServer 1 }

uecpUdpRelay OBJECT IDENTIFIER  ::= { communication 12 }

uecprelsrv OBJECT-TYPE
  SYNTAX DisplayString (SIZE(0..255)) 
  MAX-ACCESS read-write
  STATUS current
  DESCRIPTION
    "UDP server host name"
  ::= { uecpUdpRelay 1 }

uecprelport OBJECT-TYPE
  SYNTAX Integer32 (1..65535)
  MAX-ACCESS read-write
  STATUS current
  DESCRIPTION
    "UDP server port"
  ::= { uecpUdpRelay 2 }

gsmModem OBJECT IDENTIFIER  ::= { communication 13 }

mdmtype OBJECT-TYPE
  SYNTAX INTEGER {mdmGeneric(0)}
  MAX-ACCESS read-write
  STATUS current
  DESCRIPTION
    "Denotes used GSM modem type"
  ::= { gsmModem 1 }

mdmbrate OBJECT-TYPE
  SYNTAX INTEGER {gsmbrate4800bps(0),gsmbrate9600bps(1),gsmbrate19200bps(2),gsmbrate38400bps(3),gsmbrate57600bps(4)}
  MAX-ACCESS read-write
  STATUS current
  DESCRIPTION
    "GSM modem communication speed"
  ::= { gsmModem 2 }

mdmnum1 OBJECT-TYPE
  SYNTAX DisplayString (SIZE(0..63)) 
  MAX-ACCESS read-write
  STATUS current
  DESCRIPTION
    "First allowed phone number"
  ::= { gsmModem 3 }

mdmnum2 OBJECT-TYPE
  SYNTAX DisplayString (SIZE(0..63)) 
  MAX-ACCESS read-write
  STATUS current
  DESCRIPTION
    "Second allowed phone number"
  ::= { gsmModem 4 }

mdmnum3 OBJECT-TYPE
  SYNTAX DisplayString (SIZE(0..63)) 
  MAX-ACCESS read-write
  STATUS current
  DESCRIPTION
    "Third allowed phone number"
  ::= { gsmModem 5 }

mdmnum4 OBJECT-TYPE
  SYNTAX DisplayString (SIZE(0..63)) 
  MAX-ACCESS read-write
  STATUS current
  DESCRIPTION
    "Fourth allowed phone number"
  ::= { gsmModem 6 }

mdmnum5 OBJECT-TYPE
  SYNTAX DisplayString (SIZE(0..63)) 
  MAX-ACCESS read-write
  STATUS current
  DESCRIPTION
    "Fifth allowed phone number"
  ::= { gsmModem 7 }

security OBJECT IDENTIFIER  ::= { settings 6 }

panel OBJECT IDENTIFIER  ::= { security 1 }

locken OBJECT-TYPE
  SYNTAX INTEGER {altEnable(3),altDisable(4)}
  MAX-ACCESS read-write
  STATUS current
  DESCRIPTION
    "Front panel access control"
  ::= { panel 1 }

lockcode OBJECT-TYPE
  SYNTAX Integer32 (0..9999)
  MAX-ACCESS read-write
  STATUS current
  DESCRIPTION
    "Front panel access code"
  ::= { panel 2 }

locktout OBJECT-TYPE
  SYNTAX Integer32 (60..3600)
  MAX-ACCESS read-write
  STATUS current
  DESCRIPTION
    "Access is granted timeout"
  ::= { panel 3 }

remoteAccess OBJECT IDENTIFIER  ::= { security 2 }

accaname OBJECT-TYPE
  SYNTAX DisplayString (SIZE(0..31)) 
  MAX-ACCESS read-write
  STATUS current
  DESCRIPTION
    "Admin access level name"
  ::= { remoteAccess 1 }

accapass OBJECT-TYPE
  SYNTAX DisplayString (SIZE(0..31)) 
  MAX-ACCESS read-write
  STATUS current
  DESCRIPTION
    "Admin access level password"
  ::= { remoteAccess 2 }

accuname OBJECT-TYPE
  SYNTAX DisplayString (SIZE(0..31)) 
  MAX-ACCESS read-write
  STATUS current
  DESCRIPTION
    "User access level name"
  ::= { remoteAccess 3 }

accupass OBJECT-TYPE
  SYNTAX DisplayString (SIZE(0..31)) 
  MAX-ACCESS read-write
  STATUS current
  DESCRIPTION
    "User access level password"
  ::= { remoteAccess 4 }

alarms OBJECT IDENTIFIER  ::= { settings 7 }

alarmEvents OBJECT IDENTIFIER  ::= { alarms 1 }

alsmtpen OBJECT-TYPE
  SYNTAX INTEGER {altEnable(3),altDisable(4)}
  MAX-ACCESS read-write
  STATUS current
  DESCRIPTION
    "Alarm through email"
  ::= { alarmEvents 1 }

alsmsen OBJECT-TYPE
  SYNTAX INTEGER {altEnable(3),altDisable(4)}
  MAX-ACCESS read-write
  STATUS current
  DESCRIPTION
    "Alarm through SMS"
  ::= { alarmEvents 2 }

alsnmpen OBJECT-TYPE
  SYNTAX INTEGER {altEnable(3),altDisable(4)}
  MAX-ACCESS read-write
  STATUS current
  DESCRIPTION
    "Alarm through SNMP trap"
  ::= { alarmEvents 3 }

algpoen OBJECT-TYPE
  SYNTAX INTEGER {altEnable(3),altDisable(4)}
  MAX-ACCESS read-write
  STATUS current
  DESCRIPTION
    "Alarm through GPO pin"
  ::= { alarmEvents 4 }

gpOutputs OBJECT IDENTIFIER  ::= { settings 8 }

gpofunc1 OBJECT-TYPE
  SYNTAX INTEGER {gpoAlarmGPOutput(8),gpoRDSLock(9),gpoTAFlag(10),gpoTPFlag(11)}
  MAX-ACCESS read-write
  STATUS current
  DESCRIPTION
    "GPO pin 1 function"
  ::= { gpOutputs 1 }

gpotype1 OBJECT-TYPE
  SYNTAX INTEGER {gpoLevelHigh(0),gpoLevelLow(1),gpoPulseHigh(2),gpoPulseLow(3)}
  MAX-ACCESS read-write
  STATUS current
  DESCRIPTION
    "GPO pin 1 active level"
  ::= { gpOutputs 2 }

gpotout1 OBJECT-TYPE
  SYNTAX Integer32 (1..120)
  MAX-ACCESS read-write
  STATUS current
  DESCRIPTION
    "GPO pin 1 pulse duration"
  ::= { gpOutputs 3 }

gpofunc2 OBJECT-TYPE
  SYNTAX INTEGER {gpoAlarmGPOutput(8),gpoRDSLock(9),gpoTAFlag(10),gpoTPFlag(11)}
  MAX-ACCESS read-write
  STATUS current
  DESCRIPTION
    "GPO pin 2 function"
  ::= { gpOutputs 4 }

gpotype2 OBJECT-TYPE
  SYNTAX INTEGER {gpoLevelHigh(0),gpoLevelLow(1),gpoPulseHigh(2),gpoPulseLow(3)}
  MAX-ACCESS read-write
  STATUS current
  DESCRIPTION
    "GPO pin 2 active level"
  ::= { gpOutputs 5 }

gpotout2 OBJECT-TYPE
  SYNTAX Integer32 (1..120)
  MAX-ACCESS read-write
  STATUS current
  DESCRIPTION
    "GPO pin 2 pulse duration"
  ::= { gpOutputs 6 }

gpofunc3 OBJECT-TYPE
  SYNTAX INTEGER {gpoAlarmGPOutput(8),gpoRDSLock(9),gpoTAFlag(10),gpoTPFlag(11)}
  MAX-ACCESS read-write
  STATUS current
  DESCRIPTION
    "GPO pin 3 function"
  ::= { gpOutputs 7 }

gpotype3 OBJECT-TYPE
  SYNTAX INTEGER {gpoLevelHigh(0),gpoLevelLow(1),gpoPulseHigh(2),gpoPulseLow(3)}
  MAX-ACCESS read-write
  STATUS current
  DESCRIPTION
    "GPO pin 3 active level"
  ::= { gpOutputs 8 }

gpotout3 OBJECT-TYPE
  SYNTAX Integer32 (1..120)
  MAX-ACCESS read-write
  STATUS current
  DESCRIPTION
    "GPO pin 3 pulse duration"
  ::= { gpOutputs 9 }

gpofunc4 OBJECT-TYPE
  SYNTAX INTEGER {gpoAlarmGPOutput(8),gpoRDSLock(9),gpoTAFlag(10),gpoTPFlag(11)}
  MAX-ACCESS read-write
  STATUS current
  DESCRIPTION
    "GPO pin 4 function"
  ::= { gpOutputs 10 }

gpotype4 OBJECT-TYPE
  SYNTAX INTEGER {gpoLevelHigh(0),gpoLevelLow(1),gpoPulseHigh(2),gpoPulseLow(3)}
  MAX-ACCESS read-write
  STATUS current
  DESCRIPTION
    "GPO pin 4 active level"
  ::= { gpOutputs 11 }

gpotout4 OBJECT-TYPE
  SYNTAX Integer32 (1..120)
  MAX-ACCESS read-write
  STATUS current
  DESCRIPTION
    "GPO pin 4 pulse duration"
  ::= { gpOutputs 12 }

gpofunc5 OBJECT-TYPE
  SYNTAX INTEGER {gpoAlarmGPOutput(8),gpoRDSLock(9),gpoTAFlag(10),gpoTPFlag(11)}
  MAX-ACCESS read-write
  STATUS current
  DESCRIPTION
    "GPO pin 5 function"
  ::= { gpOutputs 13 }

gpotype5 OBJECT-TYPE
  SYNTAX INTEGER {gpoLevelHigh(0),gpoLevelLow(1),gpoPulseHigh(2),gpoPulseLow(3)}
  MAX-ACCESS read-write
  STATUS current
  DESCRIPTION
    "GPO pin 5 active level"
  ::= { gpOutputs 14 }

gpotout5 OBJECT-TYPE
  SYNTAX Integer32 (1..120)
  MAX-ACCESS read-write
  STATUS current
  DESCRIPTION
    "GPO pin 5 pulse duration"
  ::= { gpOutputs 15 }

gpofunc6 OBJECT-TYPE
  SYNTAX INTEGER {gpoAlarmGPOutput(8),gpoRDSLock(9),gpoTAFlag(10),gpoTPFlag(11)}
  MAX-ACCESS read-write
  STATUS current
  DESCRIPTION
    "GPO pin 6 function"
  ::= { gpOutputs 16 }

gpotype6 OBJECT-TYPE
  SYNTAX INTEGER {gpoLevelHigh(0),gpoLevelLow(1),gpoPulseHigh(2),gpoPulseLow(3)}
  MAX-ACCESS read-write
  STATUS current
  DESCRIPTION
    "GPO pin 6 active level"
  ::= { gpOutputs 17 }

gpotout6 OBJECT-TYPE
  SYNTAX Integer32 (1..120)
  MAX-ACCESS read-write
  STATUS current
  DESCRIPTION
    "GPO pin 6 pulse duration"
  ::= { gpOutputs 18 }

gpofunc7 OBJECT-TYPE
  SYNTAX INTEGER {gpoAlarmGPOutput(8),gpoRDSLock(9),gpoTAFlag(10),gpoTPFlag(11)}
  MAX-ACCESS read-write
  STATUS current
  DESCRIPTION
    "GPO pin 7 function"
  ::= { gpOutputs 19 }

gpotype7 OBJECT-TYPE
  SYNTAX INTEGER {gpoLevelHigh(0),gpoLevelLow(1),gpoPulseHigh(2),gpoPulseLow(3)}
  MAX-ACCESS read-write
  STATUS current
  DESCRIPTION
    "GPO pin 7 active level"
  ::= { gpOutputs 20 }

gpotout7 OBJECT-TYPE
  SYNTAX Integer32 (1..120)
  MAX-ACCESS read-write
  STATUS current
  DESCRIPTION
    "GPO pin 7 pulse duration"
  ::= { gpOutputs 21 }

audioMpxOutputs OBJECT IDENTIFIER  ::= { settings 9 }

volph OBJECT-TYPE
  SYNTAX Ix10 (-300..0)
  MAX-ACCESS read-write
  STATUS current
  DESCRIPTION
    "Head phones audio level"
  ::= { audioMpxOutputs 1 }

volaudio OBJECT-TYPE
  SYNTAX Ix10 (-600..60)
  MAX-ACCESS read-write
  STATUS current
  DESCRIPTION
    "Audio output level"
  ::= { audioMpxOutputs 2 }

volmpx OBJECT-TYPE
  SYNTAX Ix10 (-600..120)
  MAX-ACCESS read-write
  STATUS current
  DESCRIPTION
    "MPX output level"
  ::= { audioMpxOutputs 3 }

volgsm OBJECT-TYPE
  SYNTAX Ix10 (-600..0)
  MAX-ACCESS read-write
  STATUS current
  DESCRIPTION
    "GSM audio level"
  ::= { audioMpxOutputs 4 }

digout OBJECT-TYPE
  SYNTAX INTEGER {altEnable(3),altDisable(4)}
  MAX-ACCESS read-write
  STATUS current
  DESCRIPTION
    "Digital audio output control"
  ::= { audioMpxOutputs 5 }

device OBJECT IDENTIFIER  ::= { settings 10 }

alias OBJECT-TYPE
  SYNTAX DisplayString (SIZE(0..31)) 
  MAX-ACCESS read-write
  STATUS current
  DESCRIPTION
    "Alias name for device"
  ::= { device 1 }

region OBJECT-TYPE
  SYNTAX INTEGER {regEurope(0),regJapan(1),regUSA(2),regOIRT(3)}
  MAX-ACCESS read-write
  STATUS current
  DESCRIPTION
    "Region"
  ::= { device 2 }

dateTime OBJECT IDENTIFIER  ::= { device 3 }

date OBJECT-TYPE
  SYNTAX Integer32
  MAX-ACCESS read-write
  STATUS current
  DESCRIPTION
    "Manual set Date"
  ::= { dateTime 1 }

time OBJECT-TYPE
  SYNTAX Integer32 (0..86399)
  MAX-ACCESS read-write
  STATUS current
  DESCRIPTION
    "Manual set Time"
  ::= { dateTime 2 }

tzone OBJECT-TYPE
  SYNTAX Integer32 (-43200..50400)
  MAX-ACCESS read-write
  STATUS current
  DESCRIPTION
    "Time zone"
  ::= { dateTime 3 }

dsten OBJECT-TYPE
  SYNTAX INTEGER {dstNotused(0),dstEUDSTChange(1),dstUSADSTChange(2),dstAUSDSTChange(3),dstNZDSTChange(4)}
  MAX-ACCESS read-write
  STATUS current
  DESCRIPTION
    "Daylight Saving Time"
  ::= { dateTime 4 }

fanctrl OBJECT-TYPE
  SYNTAX INTEGER {fanAuto(0),fan25perc(1),fan50perc(2),fan75perc(3),fan100perc(4)}
  MAX-ACCESS read-write
  STATUS current
  DESCRIPTION
    "Fan speed control"
  ::= { device 4 }

slogmage OBJECT-TYPE
  SYNTAX INTEGER {slogInfinite(0),slog5days(1),slog10days(2),slog15days(3),slog20days(4),slog25days(5),slog30days(6)}
  MAX-ACCESS read-write
  STATUS current
  DESCRIPTION
    "Maximum age of WEB system log"
  ::= { device 5 }


-- Alarms
 
alarmRfMin OBJECT-TYPE
  SYNTAX Fr8p8 (5120..28160)
  MAX-ACCESS read-write
  STATUS current
  DESCRIPTION
    "Alarm RF Min"
  ::= { alarms 3 }

alarmRfMax OBJECT-TYPE
  SYNTAX Fr8p8 (5120..28160)
  MAX-ACCESS read-write
  STATUS current
  DESCRIPTION
    "Alarm RF Max"
  ::= { alarms 4 }

alarmRfTrigger OBJECT-TYPE
  SYNTAX Integer32 (1..3600)
  MAX-ACCESS read-write
  STATUS current
  DESCRIPTION
    "Alarm RF Trigger"
  ::= { alarms 5 }

alarmRfRelease OBJECT-TYPE
  SYNTAX Integer32 (1..3600)
  MAX-ACCESS read-write
  STATUS current
  DESCRIPTION
    "Alarm RF Release"
  ::= { alarms 6 }

alarmRfEvents OBJECT-TYPE
  SYNTAX Integer32 (0..255)
  MAX-ACCESS read-write
  STATUS current
  DESCRIPTION
    "Alarm RF Events"
  ::= { alarms 7 }

alarmMpxMin OBJECT-TYPE
  SYNTAX Fr8p8 (0..32000)
  MAX-ACCESS read-write
  STATUS current
  DESCRIPTION
    "Alarm MPX Min"
  ::= { alarms 8 }

alarmMpxMax OBJECT-TYPE
  SYNTAX Fr8p8 (0..32000)
  MAX-ACCESS read-write
  STATUS current
  DESCRIPTION
    "Alarm MPX Max"
  ::= { alarms 9 }

alarmMpxTrigger OBJECT-TYPE
  SYNTAX Integer32 (1..3600)
  MAX-ACCESS read-write
  STATUS current
  DESCRIPTION
    "Alarm MPX Trigger"
  ::= { alarms 10 }

alarmMpxRelease OBJECT-TYPE
  SYNTAX Integer32 (1..3600)
  MAX-ACCESS read-write
  STATUS current
  DESCRIPTION
    "Alarm MPX Release"
  ::= { alarms 11 }

alarmMpxEvents OBJECT-TYPE
  SYNTAX Integer32 (0..255)
  MAX-ACCESS read-write
  STATUS current
  DESCRIPTION
    "Alarm MPX Events"
  ::= { alarms 12 }

alarmPilotMin OBJECT-TYPE
  SYNTAX Fr8p8 (0..3840)
  MAX-ACCESS read-write
  STATUS current
  DESCRIPTION
    "Alarm PILOT Min"
  ::= { alarms 13 }

alarmPilotMax OBJECT-TYPE
  SYNTAX Fr8p8 (0..3840)
  MAX-ACCESS read-write
  STATUS current
  DESCRIPTION
    "Alarm PILOT Max"
  ::= { alarms 14 }

alarmPilotTrigger OBJECT-TYPE
  SYNTAX Integer32 (1..3600)
  MAX-ACCESS read-write
  STATUS current
  DESCRIPTION
    "Alarm PILOT Trigger"
  ::= { alarms 15 }

alarmPilotRelease OBJECT-TYPE
  SYNTAX Integer32 (1..3600)
  MAX-ACCESS read-write
  STATUS current
  DESCRIPTION
    "Alarm PILOT Release"
  ::= { alarms 16 }

alarmPilotEvents OBJECT-TYPE
  SYNTAX Integer32 (0..255)
  MAX-ACCESS read-write
  STATUS current
  DESCRIPTION
    "Alarm PILOT Events"
  ::= { alarms 17 }

alarmRdsMin OBJECT-TYPE
  SYNTAX Fr8p8 (0..3840)
  MAX-ACCESS read-write
  STATUS current
  DESCRIPTION
    "Alarm RDS Min"
  ::= { alarms 18 }

alarmRdsMax OBJECT-TYPE
  SYNTAX Fr8p8 (0..3840)
  MAX-ACCESS read-write
  STATUS current
  DESCRIPTION
    "Alarm RDS Max"
  ::= { alarms 19 }

alarmRdsTrigger OBJECT-TYPE
  SYNTAX Integer32 (1..3600)
  MAX-ACCESS read-write
  STATUS current
  DESCRIPTION
    "Alarm RDS Trigger"
  ::= { alarms 20 }

alarmRdsRelease OBJECT-TYPE
  SYNTAX Integer32 (1..3600)
  MAX-ACCESS read-write
  STATUS current
  DESCRIPTION
    "Alarm RDS Release"
  ::= { alarms 21 }

alarmRdsEvents OBJECT-TYPE
  SYNTAX Integer32 (0..255)
  MAX-ACCESS read-write
  STATUS current
  DESCRIPTION
    "Alarm RDS Events"
  ::= { alarms 22 }

alarmLeftMin OBJECT-TYPE
  SYNTAX Fr8p8 (-12800..1280)
  MAX-ACCESS read-write
  STATUS current
  DESCRIPTION
    "Alarm LEFT Min"
  ::= { alarms 23 }

alarmLeftMax OBJECT-TYPE
  SYNTAX Fr8p8 (-12800..1280)
  MAX-ACCESS read-write
  STATUS current
  DESCRIPTION
    "Alarm LEFT Max"
  ::= { alarms 24 }

alarmLeftTrigger OBJECT-TYPE
  SYNTAX Integer32 (1..3600)
  MAX-ACCESS read-write
  STATUS current
  DESCRIPTION
    "Alarm LEFT Trigger"
  ::= { alarms 25 }

alarmLeftRelease OBJECT-TYPE
  SYNTAX Integer32 (1..3600)
  MAX-ACCESS read-write
  STATUS current
  DESCRIPTION
    "Alarm LEFT Release"
  ::= { alarms 26 }

alarmLeftEvents OBJECT-TYPE
  SYNTAX Integer32 (0..255)
  MAX-ACCESS read-write
  STATUS current
  DESCRIPTION
    "Alarm LEFT Events"
  ::= { alarms 27 }

alarmRightMin OBJECT-TYPE
  SYNTAX Fr8p8 (-12800..1280)
  MAX-ACCESS read-write
  STATUS current
  DESCRIPTION
    "Alarm RIGHT Min"
  ::= { alarms 28 }

alarmRightMax OBJECT-TYPE
  SYNTAX Fr8p8 (-12800..1280)
  MAX-ACCESS read-write
  STATUS current
  DESCRIPTION
    "Alarm RIGHT Max"
  ::= { alarms 29 }

alarmRightTrigger OBJECT-TYPE
  SYNTAX Integer32 (1..3600)
  MAX-ACCESS read-write
  STATUS current
  DESCRIPTION
    "Alarm RIGHT Trigger"
  ::= { alarms 30 }

alarmRightRelease OBJECT-TYPE
  SYNTAX Integer32 (1..3600)
  MAX-ACCESS read-write
  STATUS current
  DESCRIPTION
    "Alarm RIGHT Release"
  ::= { alarms 31 }

alarmRightEvents OBJECT-TYPE
  SYNTAX Integer32 (0..255)
  MAX-ACCESS read-write
  STATUS current
  DESCRIPTION
    "Alarm RIGHT Events"
  ::= { alarms 32 }

alarmTempMin OBJECT-TYPE
  SYNTAX Fr8p8 (0..20480)
  MAX-ACCESS read-write
  STATUS current
  DESCRIPTION
    "Alarm TEMP Min"
  ::= { alarms 33 }

alarmTempMax OBJECT-TYPE
  SYNTAX Fr8p8 (0..20480)
  MAX-ACCESS read-write
  STATUS current
  DESCRIPTION
    "Alarm TEMP Max"
  ::= { alarms 34 }

alarmTempTrigger OBJECT-TYPE
  SYNTAX Integer32 (1..3600)
  MAX-ACCESS read-write
  STATUS current
  DESCRIPTION
    "Alarm TEMP Trigger"
  ::= { alarms 35 }

alarmTempRelease OBJECT-TYPE
  SYNTAX Integer32 (1..3600)
  MAX-ACCESS read-write
  STATUS current
  DESCRIPTION
    "Alarm TEMP Release"
  ::= { alarms 36 }

alarmTempEvents OBJECT-TYPE
  SYNTAX Integer32 (0..255)
  MAX-ACCESS read-write
  STATUS current
  DESCRIPTION
    "Alarm TEMP Events"
  ::= { alarms 37 }

alarmFanMin OBJECT-TYPE
  SYNTAX Integer32 (500..10000)
  MAX-ACCESS read-write
  STATUS current
  DESCRIPTION
    "Alarm FAN Min"
  ::= { alarms 38 }

alarmFanMax OBJECT-TYPE
  SYNTAX Integer32 (500..10000)
  MAX-ACCESS read-write
  STATUS current
  DESCRIPTION
    "Alarm FAN Max"
  ::= { alarms 39 }

alarmFanTrigger OBJECT-TYPE
  SYNTAX Integer32 (1..3600)
  MAX-ACCESS read-write
  STATUS current
  DESCRIPTION
    "Alarm FAN Trigger"
  ::= { alarms 40 }

alarmFanRelease OBJECT-TYPE
  SYNTAX Integer32 (1..3600)
  MAX-ACCESS read-write
  STATUS current
  DESCRIPTION
    "Alarm FAN Release"
  ::= { alarms 41 }

alarmFanEvents OBJECT-TYPE
  SYNTAX Integer32 (0..255)
  MAX-ACCESS read-write
  STATUS current
  DESCRIPTION
    "Alarm FAN Events"
  ::= { alarms 42 }

status OBJECT IDENTIFIER  ::= { db7007 3 }

statusSource OBJECT-TYPE
  SYNTAX INTEGER {inselNotUsed(0),inselMainStation(1),inselBackupStation(2),inselMP3Player(3),inselRTPAudioReceiver(4),inselIPAudioClient1(5)}
  MAX-ACCESS read-only
  STATUS current
  DESCRIPTION
    "status source "
  ::= { status 1 }

statusSourceAppliedby OBJECT-TYPE
  SYNTAX INTEGER {appliedbyAutoselected(0),appliedbyForcedoverWEB(1),appliedbyForcedoverSNMP(2)}
  MAX-ACCESS read-only
  STATUS current
  DESCRIPTION
    "status source AppliedBy"
  ::= { status 2 }

statusFreq OBJECT-TYPE
  SYNTAX Integer32 (87100..108000)
  MAX-ACCESS read-only
  STATUS current
  DESCRIPTION
    "status  Freq"
  ::= { status 3 }

statusRflvlValue OBJECT-TYPE
  SYNTAX Fr8p8 (0..28160)
  MAX-ACCESS read-only
  STATUS current
  DESCRIPTION
    "status RFLVL Value"
  ::= { status 4 }

statusRflvlValueAvr OBJECT-TYPE
  SYNTAX Fr8p8 (0..28160)
  MAX-ACCESS read-only
  STATUS current
  DESCRIPTION
    "status RFLVL Value Avr"
  ::= { status 5 }

statusRflvlPeakMax OBJECT-TYPE
  SYNTAX Fr8p8 (0..28160)
  MAX-ACCESS read-only
  STATUS current
  DESCRIPTION
    "status RFLVL Peak Max"
  ::= { status 6 }

statusMpathValue OBJECT-TYPE
  SYNTAX Fr8p8 (0..25600)
  MAX-ACCESS read-only
  STATUS current
  DESCRIPTION
    "status MPATH Value"
  ::= { status 7 }

statusMpathValueAvr OBJECT-TYPE
  SYNTAX Fr8p8 (0..25600)
  MAX-ACCESS read-only
  STATUS current
  DESCRIPTION
    "status MPATH Value Avr"
  ::= { status 8 }

statusMpathPeakMax OBJECT-TYPE
  SYNTAX Fr8p8 (0..25600)
  MAX-ACCESS read-only
  STATUS current
  DESCRIPTION
    "status MPATH Peak Max"
  ::= { status 9 }

statusMpxtValue OBJECT-TYPE
  SYNTAX Fr8p8 (0..32000)
  MAX-ACCESS read-only
  STATUS current
  DESCRIPTION
    "status MPXT Value"
  ::= { status 10 }

statusMpxtValueAvr OBJECT-TYPE
  SYNTAX Fr8p8 (0..32000)
  MAX-ACCESS read-only
  STATUS current
  DESCRIPTION
    "status MPXT Value Avr"
  ::= { status 11 }

statusMpxtPeakMax OBJECT-TYPE
  SYNTAX Fr8p8 (0..32000)
  MAX-ACCESS read-only
  STATUS current
  DESCRIPTION
    "status MPXT Peak Max"
  ::= { status 12 }

statusPilotValue OBJECT-TYPE
  SYNTAX Fr8p8 (0..3840)
  MAX-ACCESS read-only
  STATUS current
  DESCRIPTION
    "status PILOT Value"
  ::= { status 13 }

statusPilotValueAvr OBJECT-TYPE
  SYNTAX Fr8p8 (0..3840)
  MAX-ACCESS read-only
  STATUS current
  DESCRIPTION
    "status PILOT Value Avr"
  ::= { status 14 }

statusPilotPeakMax OBJECT-TYPE
  SYNTAX Fr8p8 (0..3840)
  MAX-ACCESS read-only
  STATUS current
  DESCRIPTION
    "status PILOT Peak Max"
  ::= { status 15 }

statusRdsValue OBJECT-TYPE
  SYNTAX Fr8p8 (0..3840)
  MAX-ACCESS read-only
  STATUS current
  DESCRIPTION
    "status RDS Value"
  ::= { status 16 }

statusRdsValueAvr OBJECT-TYPE
  SYNTAX Fr8p8 (0..3840)
  MAX-ACCESS read-only
  STATUS current
  DESCRIPTION
    "status RDS Value Avr"
  ::= { status 17 }

statusRdsPeakMax OBJECT-TYPE
  SYNTAX Fr8p8 (0..3840)
  MAX-ACCESS read-only
  STATUS current
  DESCRIPTION
    "status RDS Peak Max"
  ::= { status 18 }

statusLeftValue OBJECT-TYPE
  SYNTAX Fr8p8 (-15360..1280)
  MAX-ACCESS read-only
  STATUS current
  DESCRIPTION
    "status LEFT Value"
  ::= { status 19 }

statusLeftValueAvr OBJECT-TYPE
  SYNTAX Fr8p8 (-15360..1280)
  MAX-ACCESS read-only
  STATUS current
  DESCRIPTION
    "status LEFT Value Avr"
  ::= { status 20 }

statusLeftPeakMax OBJECT-TYPE
  SYNTAX Fr8p8 (-15360..1280)
  MAX-ACCESS read-only
  STATUS current
  DESCRIPTION
    "status LEFT Peak Max"
  ::= { status 21 }

statusRightValue OBJECT-TYPE
  SYNTAX Fr8p8 (-15360..1280)
  MAX-ACCESS read-only
  STATUS current
  DESCRIPTION
    "status RIGHT Value"
  ::= { status 22 }

statusRightValueAvr OBJECT-TYPE
  SYNTAX Fr8p8 (-15360..1280)
  MAX-ACCESS read-only
  STATUS current
  DESCRIPTION
    "status RIGHT Value Avr"
  ::= { status 23 }

statusRightPeakMax OBJECT-TYPE
  SYNTAX Fr8p8 (-15360..1280)
  MAX-ACCESS read-only
  STATUS current
  DESCRIPTION
    "status RIGHT Peak Max"
  ::= { status 24 }

statusAudioStereo OBJECT-TYPE
  SYNTAX INTEGER {altMono(8),altStereo(9)}
  MAX-ACCESS read-only
  STATUS current
  DESCRIPTION
    "status Audio Stereo"
  ::= { status 25 }

statusTempcValue OBJECT-TYPE
  SYNTAX Fr8p8 (0..25600)
  MAX-ACCESS read-only
  STATUS current
  DESCRIPTION
    "status TEMPC Value"
  ::= { status 26 }

statusTempcValueAvr OBJECT-TYPE
  SYNTAX Fr8p8 (0..25600)
  MAX-ACCESS read-only
  STATUS current
  DESCRIPTION
    "status TEMPC Value Avr"
  ::= { status 27 }

statusTempcPeakMax OBJECT-TYPE
  SYNTAX Fr8p8 (0..25600)
  MAX-ACCESS read-only
  STATUS current
  DESCRIPTION
    "status TEMPC Peak Max"
  ::= { status 28 }

statusFanrpmValue OBJECT-TYPE
  SYNTAX Integer32 (0..100000)
  MAX-ACCESS read-only
  STATUS current
  DESCRIPTION
    "status FANRPM Value"
  ::= { status 29 }

statusFanrpmValueAvr OBJECT-TYPE
  SYNTAX Integer32 (0..100000)
  MAX-ACCESS read-only
  STATUS current
  DESCRIPTION
    "status FANRPM Value Avr"
  ::= { status 30 }

statusFanrpmPeakMax OBJECT-TYPE
  SYNTAX Integer32 (0..100000)
  MAX-ACCESS read-only
  STATUS current
  DESCRIPTION
    "status FANRPM Peak Max"
  ::= { status 31 }

statusRdsLock OBJECT-TYPE
  SYNTAX INTEGER {altOff(1),altOn(2)}
  MAX-ACCESS read-only
  STATUS current
  DESCRIPTION
    "status RDS Lock"
  ::= { status 32 }

statusRdsPi OBJECT-TYPE
  SYNTAX DisplayString (SIZE(0..4)) 
  MAX-ACCESS read-only
  STATUS current
  DESCRIPTION
    "status RDS PI"
  ::= { status 33 }

statusRdsPs OBJECT-TYPE
  SYNTAX DisplayString (SIZE(0..8)) 
  MAX-ACCESS read-only
  STATUS current
  DESCRIPTION
    "status RDS PS"
  ::= { status 34 }

statusRdsRt OBJECT-TYPE
  SYNTAX DisplayString (SIZE(0..68)) 
  MAX-ACCESS read-only
  STATUS current
  DESCRIPTION
    "status RDS RT"
  ::= { status 35 }

statusRdsTa OBJECT-TYPE
  SYNTAX INTEGER {altNotRecived(0),altOff(1),altOn(2)}
  MAX-ACCESS read-only
  STATUS current
  DESCRIPTION
    "status RDS TA"
  ::= { status 36 }

statusRdsTp OBJECT-TYPE
  SYNTAX INTEGER {altNotRecived(0),altOff(1),altOn(2)}
  MAX-ACCESS read-only
  STATUS current
  DESCRIPTION
    "status RDS TP"
  ::= { status 37 }

statusRdsMusicspeech OBJECT-TYPE
  SYNTAX INTEGER {altNotRecived(0),altSpeech(10),altMusic(11)}
  MAX-ACCESS read-only
  STATUS current
  DESCRIPTION
    "status RDS MusicSpeech"
  ::= { status 38 }

statusRdsPty OBJECT-TYPE
  SYNTAX INTEGER {rdsptyNone(0),rdsptyNews(1),rdsptyCurrentAffairs(2),rdsptyInfo(3),rdsptySport(4),rdsptyEducation(5),rdsptyDrama(6),rdsptyCultures(7),rdsptyScience(8),rdsptyVariedSpeech(9),rdsptyPopMusic(10),rdsptyRockMusic(11),rdsptyEasyListening(12),rdsptyLightClassicsM(13),rdsptySeriousClassics(14),rdsptyOtherMusic(15),rdsptyWeather(16),rdsptyFinance(17),rdsptyChildrensProgs(18),rdsptySocialAffairs(19),rdsptyReligion(20),rdsptyPhoneIn(21),rdsptyTravelTouring(22),rdsptyLeisureHobby(23),rdsptyJazzMusic(24),rdsptyCountryMusic(25),rdsptyNationalMusic(26),rdsptyOldiesMusic(27),rdsptyFolkMusic(28),rdsptyDocumentary(29),rdsptyAlarmTest(30),rdsptyAlarmAlarm(31)}
  MAX-ACCESS read-only
  STATUS current
  DESCRIPTION
    "status RDS PTY"
  ::= { status 39 }

statusRdsBer OBJECT-TYPE
  SYNTAX Fr1p15 (0..32767)
  MAX-ACCESS read-only
  STATUS current
  DESCRIPTION
    "status RDS BER"
  ::= { status 40 }

statusAlarmRf OBJECT-TYPE
  SYNTAX INTEGER {alarmDisabled(0),alarmOK(1),alarmLow(2),alarmHigh(3)}
  MAX-ACCESS read-only
  STATUS current
  DESCRIPTION
    "status Alarm RF"
  ::= { status 41 }

statusAlarmMpx OBJECT-TYPE
  SYNTAX INTEGER {alarmDisabled(0),alarmOK(1),alarmLow(2),alarmHigh(3)}
  MAX-ACCESS read-only
  STATUS current
  DESCRIPTION
    "status Alarm MPX"
  ::= { status 42 }

statusAlarmPilot OBJECT-TYPE
  SYNTAX INTEGER {alarmDisabled(0),alarmOK(1),alarmLow(2),alarmHigh(3)}
  MAX-ACCESS read-only
  STATUS current
  DESCRIPTION
    "status Alarm Pilot"
  ::= { status 43 }

statusAlarmRds OBJECT-TYPE
  SYNTAX INTEGER {alarmDisabled(0),alarmOK(1),alarmLow(2),alarmHigh(3)}
  MAX-ACCESS read-only
  STATUS current
  DESCRIPTION
    "status Alarm RDS"
  ::= { status 44 }

statusAlarmLeft OBJECT-TYPE
  SYNTAX INTEGER {alarmDisabled(0),alarmOK(1),alarmLow(2),alarmHigh(3)}
  MAX-ACCESS read-only
  STATUS current
  DESCRIPTION
    "status Alarm Left"
  ::= { status 45 }

statusAlarmRight OBJECT-TYPE
  SYNTAX INTEGER {alarmDisabled(0),alarmOK(1),alarmLow(2),alarmHigh(3)}
  MAX-ACCESS read-only
  STATUS current
  DESCRIPTION
    "status Alarm Right"
  ::= { status 46 }

statusAlarmTemp OBJECT-TYPE
  SYNTAX INTEGER {alarmDisabled(0),alarmOK(1),alarmLow(2),alarmHigh(3)}
  MAX-ACCESS read-only
  STATUS current
  DESCRIPTION
    "status Alarm Temp"
  ::= { status 47 }

statusAlarmFan OBJECT-TYPE
  SYNTAX INTEGER {alarmDisabled(0),alarmOK(1),alarmLow(2),alarmHigh(3)}
  MAX-ACCESS read-only
  STATUS current
  DESCRIPTION
    "status Alarm Fan"
  ::= { status 48 }

traps OBJECT IDENTIFIER  ::= { db7007 254 }

notification OBJECT IDENTIFIER  ::= { traps 0 }

notifTest NOTIFICATION-TYPE
  OBJECTS { alias, snmpaid }
  STATUS current
  DESCRIPTION
    "notif  test"
  ::= { notification 1 }

notifSourceChange NOTIFICATION-TYPE
  OBJECTS { statusSource, statusSourceAppliedby, alias, snmpaid }
  STATUS current
  DESCRIPTION
    "notif source Change"
  ::= { notification 2 }

notifRflossActive NOTIFICATION-TYPE
  OBJECTS { statusSource, alias, snmpaid }
  STATUS current
  DESCRIPTION
    "notif RFLoss Active"
  ::= { notification 3 }

notifRflossInactive NOTIFICATION-TYPE
  OBJECTS { statusSource, alias, snmpaid }
  STATUS current
  DESCRIPTION
    "notif RFLoss Inactive"
  ::= { notification 4 }

notifPiprotectionActive NOTIFICATION-TYPE
  OBJECTS { statusSource, alias, snmpaid }
  STATUS current
  DESCRIPTION
    "notif PIProtection Active"
  ::= { notification 5 }

notifPiprotectionInactive NOTIFICATION-TYPE
  OBJECTS { statusSource, alias, snmpaid }
  STATUS current
  DESCRIPTION
    "notif PIProtection Inactive"
  ::= { notification 6 }

notifAudiomuteActive NOTIFICATION-TYPE
  OBJECTS { statusSource, alias, snmpaid }
  STATUS current
  DESCRIPTION
    "notif AudioMute Active"
  ::= { notification 7 }

notifAudiomuteInactive NOTIFICATION-TYPE
  OBJECTS { statusSource, alias, snmpaid }
  STATUS current
  DESCRIPTION
    "notif AudioMute Inactive"
  ::= { notification 8 }

notifRflvlOk NOTIFICATION-TYPE
  OBJECTS { statusRflvlValue, alias, snmpaid }
  STATUS current
  DESCRIPTION
    "notif RFLVL OK"
  ::= { notification 9 }

notifRflvlLow NOTIFICATION-TYPE
  OBJECTS { statusRflvlValue, alias, snmpaid }
  STATUS current
  DESCRIPTION
    "notif RFLVL Low"
  ::= { notification 10 }

notifRflvlHigh NOTIFICATION-TYPE
  OBJECTS { statusRflvlValue, alias, snmpaid }
  STATUS current
  DESCRIPTION
    "notif RFLVL High"
  ::= { notification 11 }

notifMpxtOk NOTIFICATION-TYPE
  OBJECTS { statusMpxtValue, alias, snmpaid }
  STATUS current
  DESCRIPTION
    "notif MPXT OK"
  ::= { notification 12 }

notifMpxtLow NOTIFICATION-TYPE
  OBJECTS { statusMpxtValue, alias, snmpaid }
  STATUS current
  DESCRIPTION
    "notif MPXT Low"
  ::= { notification 13 }

notifMpxtHigh NOTIFICATION-TYPE
  OBJECTS { statusMpxtValue, alias, snmpaid }
  STATUS current
  DESCRIPTION
    "notif MPXT High"
  ::= { notification 14 }

notifPilotOk NOTIFICATION-TYPE
  OBJECTS { statusPilotValue, alias, snmpaid }
  STATUS current
  DESCRIPTION
    "notif PILOT OK"
  ::= { notification 15 }

notifPilotLow NOTIFICATION-TYPE
  OBJECTS { statusPilotValue, alias, snmpaid }
  STATUS current
  DESCRIPTION
    "notif PILOT Low"
  ::= { notification 16 }

notifPilotHigh NOTIFICATION-TYPE
  OBJECTS { statusPilotValue, alias, snmpaid }
  STATUS current
  DESCRIPTION
    "notif PILOT High"
  ::= { notification 17 }

notifRdsOk NOTIFICATION-TYPE
  OBJECTS { statusRdsValue, alias, snmpaid }
  STATUS current
  DESCRIPTION
    "notif RDS OK"
  ::= { notification 18 }

notifRdsLow NOTIFICATION-TYPE
  OBJECTS { statusRdsValue, alias, snmpaid }
  STATUS current
  DESCRIPTION
    "notif RDS Low"
  ::= { notification 19 }

notifRdsHigh NOTIFICATION-TYPE
  OBJECTS { statusRdsValue, alias, snmpaid }
  STATUS current
  DESCRIPTION
    "notif RDS High"
  ::= { notification 20 }

notifLeftOk NOTIFICATION-TYPE
  OBJECTS { statusLeftValue, alias, snmpaid }
  STATUS current
  DESCRIPTION
    "notif LEFT OK"
  ::= { notification 21 }

notifLeftLow NOTIFICATION-TYPE
  OBJECTS { statusLeftValue, alias, snmpaid }
  STATUS current
  DESCRIPTION
    "notif LEFT Low"
  ::= { notification 22 }

notifLeftHigh NOTIFICATION-TYPE
  OBJECTS { statusLeftValue, alias, snmpaid }
  STATUS current
  DESCRIPTION
    "notif LEFT High"
  ::= { notification 23 }

notifRightOk NOTIFICATION-TYPE
  OBJECTS { statusRightValue, alias, snmpaid }
  STATUS current
  DESCRIPTION
    "notif RIGHT OK"
  ::= { notification 24 }

notifRightLow NOTIFICATION-TYPE
  OBJECTS { statusRightValue, alias, snmpaid }
  STATUS current
  DESCRIPTION
    "notif RIGHT Low"
  ::= { notification 25 }

notifRightHigh NOTIFICATION-TYPE
  OBJECTS { statusRightValue, alias, snmpaid }
  STATUS current
  DESCRIPTION
    "notif RIGHT High"
  ::= { notification 26 }

notifTempcOk NOTIFICATION-TYPE
  OBJECTS { statusTempcValue, alias, snmpaid }
  STATUS current
  DESCRIPTION
    "notif TEMPC OK"
  ::= { notification 27 }

notifTempcLow NOTIFICATION-TYPE
  OBJECTS { statusTempcValue, alias, snmpaid }
  STATUS current
  DESCRIPTION
    "notif TEMPC Low"
  ::= { notification 28 }

notifTempcHigh NOTIFICATION-TYPE
  OBJECTS { statusTempcValue, alias, snmpaid }
  STATUS current
  DESCRIPTION
    "notif TEMPC High"
  ::= { notification 29 }

notifFanrpmOk NOTIFICATION-TYPE
  OBJECTS { statusFanrpmValue, alias, snmpaid }
  STATUS current
  DESCRIPTION
    "notif FANRPM OK"
  ::= { notification 30 }

notifFanrpmLow NOTIFICATION-TYPE
  OBJECTS { statusFanrpmValue, alias, snmpaid }
  STATUS current
  DESCRIPTION
    "notif FANRPM Low"
  ::= { notification 31 }

notifFanrpmHigh NOTIFICATION-TYPE
  OBJECTS { statusFanrpmValue, alias, snmpaid }
  STATUS current
  DESCRIPTION
    "notif FANRPM High"
  ::= { notification 32 }

notifAudioLoss NOTIFICATION-TYPE
  OBJECTS { statusSource, alias, snmpaid }
  STATUS current
  DESCRIPTION
    "notif Audio Loss"
  ::= { notification 33 }

notifAudioRecover NOTIFICATION-TYPE
  OBJECTS { statusSource, alias, snmpaid }
  STATUS current
  DESCRIPTION
    "notif Audio Recover"
  ::= { notification 34 }

END
